------------------------------------------------------------------------------
--
-- (c) Copyright 2001-2005 mBalance.
-- 
--  This MIB is proprietary to and embodies the confidential technology of
--  mBalance. Possession, use, duplication or dissemination of this MIB is 
--  authorized only pursuant to a valid written license from mBalance.
--
------------------------------------------------------------------------------
--
-- File    : textpass-ss7-mib.my
-- Release : R03.02
-- $Id: textpass-ss7-mib.my,v 1.49.14.1 2010/12/13 12:35:14 tjeger Exp $
--
------------------------------------------------------------------------------


    TEXTPASS-SS7-MIB DEFINITIONS ::= BEGIN

    IMPORTS
        Gauge, Counter, TimeTicks
            FROM RFC1155-SMI         
        TEXTUAL-CONVENTION
            FROM SNMPv2-TC
        textpass
            FROM MBALANCE-MIB
        deviceType, DateTime
            FROM TEXTPASS-GEN-MIB
        OBJECT-TYPE
            FROM RFC-1212
        TRAP-TYPE
            FROM RFC-1215;

    Boolean ::=
        INTEGER {
            false(0),
            true(1)
        }

    Trunk ::= 
        Gauge(0..1)
    
    NameString ::= TEXTUAL-CONVENTION
        DISPLAY-HINT "31a"
        STATUS mandatory
        DESCRIPTION "Represent names to identify objects"
        SYNTAX OCTET STRING (SIZE (1..31))

    Priority ::=
        Gauge(0..7)

    E164AddressString ::=
        OCTET STRING (SIZE (1..15))

    E164AddressLen ::=
        Gauge(1..15)

    NationalInternationalIndication ::=
        INTEGER {
            international(0),
            national(1)
        }
        
    RoutingIndicator ::=
        INTEGER {
            routeOnGlobalTitle(0),
            routeOnSubSystemNumber(1)
        }
        
    GlobalTitleIndicator ::=
        Gauge(0 | 4)

    TranslationType ::=
        Gauge(0..255)

    NatureOfAddressIndication ::=
        INTEGER {
            unknown(0),
            subscriberNumber(1),
            reservedForNationalUse(2),
            nationalSignificantNumber(3),
            internationalNumber(4)
        }

    NumberingPlan ::=
        INTEGER {
            unknown(0),
            isdnTelephone(1),
            generic(2),
            data(3),
            telex(4),
            maritime(5),
            landMobile(6),
            isdnMobile(7),
            private(14)
        }

    TimeSlot ::=
        Gauge(0..31)

    SignallingLinkCode ::=
        Gauge(0..15)
    
    ----------------------------------------------------------------------------
    --
    --  PointCode defines a point code specification as commonly used in ITU-T.
    --  This specification defines a point code as a field with a (single) 
    --  decimal value (e.g. 1656).
    --
    ----------------------------------------------------------------------------

    PointCode ::=
        Gauge(0..16777215)

    ----------------------------------------------------------------------------
    --
    --  PointCodeString defines a point code specification as commonly used in 
    --  ANSI. This specification defines a pointcode as a field consisting of 
    --  three sub-fields. These subfields are network, cluster and member.
    --
    --  For the values of these subfields, the following applies:
    --  - network is a number in range of 1-255 (ANSI) or 0-7 (ITU-T) 
    --  - cluster is a number in range of 0-255 
    --  - member is a number in range of 0-255 (ANSI) or 0-7 (ITU-T) 
    --
    --  This specification supports two formats:
    --  1. a format that uses a dash (-) to seperate network, cluster and member:
    --        network.cluster.member
    --     e.g. 6-232-1, with 6 being the network, 232 being the cluster and 1 
    --     being the member
    --  2. a format that uses a period (-) to seperate network, cluster and member:
    --        network.cluster.member
    --     e.g. 6.232.1, with 6 being the network, 232 being the cluster and 1 
    --     being the member
    --
    ------------------------------------------------------------------------------ 

    PointCodeString ::=
        OCTET STRING (SIZE (5..11))

    SubSystemNumber ::=
        Gauge(0..255)

    Weight ::=
        Gauge(1..100)

    Throughput ::=
        Gauge(1..10000)

    AdminState ::=
        INTEGER {
            inactive(0),
            active(1),
            destroy(2)
        }

    TrunkType ::=
        INTEGER {
            e1WithCrc120Ohm(0),
            e1WithoutCrc120Ohm(1),
            e1WithCrc75Ohm(2),
            e1WithoutCrc75Ohm(3)
        }
        
    TrunkOperationalState ::=
        INTEGER {
            adminDisabled(0),
            lossOfSignal(1),
            lossOfFraming(2),
            receivingAisCondition(3),
            receivingRaiCondition(4),
            available(5)
        }
        
    LinkSetOperationalState ::=
        INTEGER {        
            adminDisabled(0),
            unavailable(1),
            available(2)
        }
    
    LinkOperationalState ::=
        INTEGER {
            adminDisabled(0),
            outOfService(1),
            aligning(2),
            proving(3),
            aligned(4),
            inService(5),
            remoteProcessorOutage(6),
            congested(7),
            throughputExceeded(8),
            available(9)
        } 
    
    SscopOperationalState ::=
        INTEGER {
            idle(1),
            outgoingConnectionPending(2),
            incomingConnectionPending(3),
            outgoingDisconnectionPending(4),
            outgoingResynchronisationPending(5),
            incomingResynchronisationPending(6),
            outgoingRecoveryPending(7),
            recoveryResponsePending(8),
            incomingRecoveryPending(9),
            dataTransferReady(10)
        }
    
    SscfOperationalState ::=
        INTEGER {
            outOfServiceAndIdle(111),
            outOfServiceAndOutgoingConnectionPending(141),
            alignmentAndIdle(212),
            alignmentAndOutgoingConnectionPending(222),
            alignmentAndOutgoingDisconnectionPending(242),
            inServiceAndDataTransferReady(3105),
            provingAndDataTransferReady(2103),
            alignedReadyAndDataTransferReady(2104)
        }
        
    AtmOperationalState ::=
        INTEGER {
            lossOfCellDelineation(0),
            available(1)
        }
        
    DestinationOperationalState ::=
        INTEGER {
            adminDisabled(0),
            inaccessible(1),
            throughputExceeded(2),
            accessible(3)
        } 

    RouteOperationalState ::=
        INTEGER {
            adminDisabled(0),
            unavailable(1),
            collecting(2),
            prohibited(3),
            restricted(4),
            congested(5),
            throughputExceeded(6),
            available(7)
        } 

    StpOperationalState ::=
        INTEGER {
            adminDisabled(0),
            pcProhibited(1),
            sccpProhibited(2),
            throughputExceeded(3),
            allowed(4)
        }
        
    NetworkIndicator ::=
        INTEGER {
            internationalNetwork(0),
            reservedForInternationalUse(1),
            nationalNetwork(2),
            reservedForNationalUse(3)                        
        }
        
    EmergencyProvingMode ::=
        INTEGER {
            never(0),
            firstLinkOnly(1),
            always(2)
        }
        
    ErrorString ::=
        OCTET STRING (SIZE (0..127))
         
    Percentage ::= 
        Gauge(0..100)

    BufferSize ::=
        INTEGER(0..2147483647)

    ----------------------------------------------------------------------------
    --
    --  AspIdentifier defines the ASP identifier used in an ASP-UP message to
    --  identify an ASP
    --
    ----------------------------------------------------------------------------

    AspIdentifier ::=
        Gauge(0..4294967295)

    ----------------------------------------------------------------------------
    --
    --  IpAddressSpec is a specification for a IPv4 or IPv6 address.
    --
    ----------------------------------------------------------------------------

    IpAddressSpec ::=
        OCTET STRING (SIZE (0..23))
            
    ----------------------------------------------------------------------------
    --
    --  M3uaAsInstanceOperationalState describes the operational state of an AS
    --  instance within a M3UA ASP.
    --
    ----------------------------------------------------------------------------

    M3uaAsInstanceOperationalState ::=
        INTEGER {
            adminDisabled(0),
            blocked(1),
            activating(2),
            active(3)
        }

    ----------------------------------------------------------------------------
    --
    --  M3uaAsOperationalState describes the operational state of an M3UA AS.
    --
    ----------------------------------------------------------------------------

    M3uaAsOperationalState ::=
        INTEGER {
            adminDisabled(0),
            blocked(1),
            activating(2),
            active(3)
        }

    ----------------------------------------------------------------------------
    --
    --  M3uaAsTableIndex defines the index for the m3uaAsTable.
    --
    ----------------------------------------------------------------------------

    M3uaAsTableIndex ::=
        Gauge(1..128)

    ----------------------------------------------------------------------------
    --
    --  M3uaAspOperationalState describes the operational state of an M3UA ASP.
    --
    ----------------------------------------------------------------------------

    M3uaAspOperationalState ::=
        INTEGER {
            adminDisabled(0),
            blocked(1),
            down(2),
            up(3),
            congested(4)
        }
                
    ----------------------------------------------------------------------------
    --
    --  M3uaAspTableIndex defines the index for the m3uaAspTable.
    --
    ----------------------------------------------------------------------------

    M3uaAspTableIndex ::=
        Gauge(1..128)

    ----------------------------------------------------------------------------
    --
    --  M3uaSgpOperationalState describes the operational state of an M3UA SGP.
    --
    ----------------------------------------------------------------------------

    M3uaSgpOperationalState ::=
        INTEGER {
            adminDisabled(0),
            blocked(1),
            down(2),
            up(3),
            congested(4)
        }
        
    ----------------------------------------------------------------------------
    --
    --  M3uaSgpSpcOperationalState describes the operational state of an M3UA 
    --  SGP for a singalling point code of TextPass
    --
    ----------------------------------------------------------------------------

    M3uaSgpSpcOperationalState ::=
        INTEGER {
            inactive(0),
            activating(1),
            active(2),
            deactivating(3)
        }
        
    ----------------------------------------------------------------------------
    --
    --  M3uaSgpTrafficMode describes the traffic mode setting advertised
    --  by the ASP to an SGP.
    --
    ----------------------------------------------------------------------------

    M3uaSgpTrafficMode ::=
        INTEGER {
            unconfigured(0),
            override(1),
            loadshare(2),
            broadcast(3)
        }
                
    ----------------------------------------------------------------------------
    --
    --  M3uaSgpTableIndex defines the index for the m3uaSgpTable.
    --
    ----------------------------------------------------------------------------

    M3uaSgpTableIndex ::=
        Gauge(1..128)

    ----------------------------------------------------------------------------
    --
    --  M3uaLocalAddressTableIndex defines the index for the 
    --  M3uaLocalAddressTable.
    --
    ----------------------------------------------------------------------------

    M3uaLocalAddressTableIndex ::=
        Gauge(1..16)

    ----------------------------------------------------------------------------
    --
    --  M3uaRemoteAddressTableIndex defines the index for the 
    --  M3uaRemoteAddressTable.
    --
    ----------------------------------------------------------------------------

    M3uaRemoteAddressTableIndex ::=
        Gauge(1..16)

    ----------------------------------------------------------------------------
    --
    --  RemoteAddressOperationalState describes the operational state of an IP 
    --  address of a remote ASP.
    --
    ----------------------------------------------------------------------------

    RemoteAddressOperationalState ::=
        INTEGER {
            adminDisabled(0),
            blocked(1),
            notRegistered(2),
            actingAsPrimary(3),
            actingAsSecondary(4)
        }

    ----------------------------------------------------------------------------
    --
    --  RoutingContext defines the routing context that identifies a particular
    --  AS.
    --
    ----------------------------------------------------------------------------

    RoutingContext ::=
        Gauge(0..4294967295)

    ----------------------------------------------------------------------------
    --
    --  NetworkAppearance defines the network appearance used for SIGTRAN. 
    --
    ----------------------------------------------------------------------------

    NetworkAppearance ::=
        Gauge(0..4294967295)

    ----------------------------------------------------------------------------
    --
    --  SctpMaxConnectAttempts defines the maximum number of attempts to establish an 
    --  SCTP association.
    --
    ----------------------------------------------------------------------------

    SctpMaxConnectAttempts ::=
        Gauge(8..65535)    

    ----------------------------------------------------------------------------
    --
    --  SctpMaxPduSize specifies the maximum PDU size that is used in a SCTP
    --  association.
    --
    ----------------------------------------------------------------------------

    SctpMaxPduSize ::=
        Gauge(0..8108)

    ----------------------------------------------------------------------------
    --
    --  SctpOperationalState describes the operational state of an SCTP 
    --  association.
    --
    ----------------------------------------------------------------------------

    SctpOperationalState ::=
        INTEGER {
            adminDisabled(0),
            closed(1),
            cookieWait(2),
            cookieEchoed(3),
            established(4),
            shutdownPending(5),
            shutdownSent(6),
            shutdownReceived(7),
            shutdownAckSent(8),
            expectingConnectFromPeer(9)
        }

    ----------------------------------------------------------------------------
    --
    --  SctpPort specifies an SCTP port number that is used at one of the two
    --  ends of an SCTP association.
    --
    ----------------------------------------------------------------------------

    SctpPort ::=
        Gauge(0..65535)

    ----------------------------------------------------------------------------
    --
    --  SctpRetransmitTimeout defines the value for the SCTP retransmit timeout.
    --
    ----------------------------------------------------------------------------

    SctpRetransmitTimeout ::=
        Gauge(1000..30000)    
        
    ----------------------------------------------------------------------------
    --
    --  SctpRetransmits defines the maximum number of attempts that an SCTP 
    --  DATA chunk is retransmitted before a failure results.
    --
    ----------------------------------------------------------------------------

    SctpRetransmits ::=    
        Gauge(5..65535)    
        
    ----------------------------------------------------------------------------
    --
    --  SctpRoundTripTime defines the SCTP Round Trip Time (RTT)
    --
    ----------------------------------------------------------------------------

    SctpRoundTripTime ::=
        Gauge(0..60000)

    ----------------------------------------------------------------------------
    --
    --  SctpSackDelay defines the delay for selective ACK chunks in ms units.
    --
    ----------------------------------------------------------------------------

    SctpSackDelay ::=
        INTEGER (0..3000)

    ----------------------------------------------------------------------------
    --
    --  SctpSmoothedLinkQuality defines the value resulting from a proprietary
    --  measurement for the quality of a link.
    --
    ----------------------------------------------------------------------------

    SctpSmoothedLinkQuality ::=
        Gauge(0..2000)              -- to-be-checked with Adax
        
    ----------------------------------------------------------------------------
    --
    --  SctpStreams specifies the number of SCTP streams within an SCTP 
    --  association.
    --
    ----------------------------------------------------------------------------

    SctpStreams ::=
        Gauge(1..255)

    ----------------------------------------------------------------------------
    --
    --  SctpTimerHeartbeat defines the value for the SCTP heartbeat interval.
    --
    ----------------------------------------------------------------------------

    SctpTimerHeartbeat ::=
        Gauge(100..30000)    

    ----------------------------------------------------------------------------
    --
    --  SctpTimerT1Cookie defines the value for the SCTP T1-cookie timer.
    --
    ----------------------------------------------------------------------------

    SctpTimerT1Cookie ::=
        Gauge(100..30000)              -- to-be-checked with Adax
            
    ----------------------------------------------------------------------------
    --
    --  SctpTimerT1Init defines the value for the SCTP T1-init timer.
    --
    ----------------------------------------------------------------------------

    SctpTimerT1Init ::=
        Gauge(1..10000)    

    ----------------------------------------------------------------------------
    --
    --  SctpTimerT3Rtx defines the value for the SCTP T3-rtx timer.
    --
    ----------------------------------------------------------------------------

    SctpTimerT3Rtx ::=
        Gauge(200..10000)    

    ----------------------------------------------------------------------------
    --
    --  SctpTsn defines the SCTP Transmit Sequence Number
    --
    ----------------------------------------------------------------------------

    SctpTsn ::=
        Gauge(0..4294967295)

    ----------------------------------------------------------------------------
    --
    --  SctpWindowSize defines the SCTP Window Size
    --
    ----------------------------------------------------------------------------

    SctpWindowSize ::=
        Gauge(0..4294967295)

    ----------------------------------------------------------------------------
    --
    --  SuaAsInstanceOperationalState describes the operational state of an AS
    --  instance within a SUA ASP.
    --
    ----------------------------------------------------------------------------

    SuaAsInstanceOperationalState ::=
        INTEGER {
            adminDisabled(0),
            blocked(1),
            activating(2),
            active(3)
        }

    ----------------------------------------------------------------------------
    --
    --  SuaAsOperationalState describes the operational state of an SUA AS.
    --
    ----------------------------------------------------------------------------

    SuaAsOperationalState ::=
        INTEGER {
            adminDisabled(0),
            blocked(1),
            activating(2),
            active(3)
        }

    ----------------------------------------------------------------------------
    --
    --  SuaAsTableIndex defines the index for the suaAsTable.
    --
    ----------------------------------------------------------------------------

    SuaAsTableIndex ::=
        Gauge(1..128)

    ----------------------------------------------------------------------------
    --
    --  SuaAspOperationalState describes the operational state of an SUA ASP.
    --
    ----------------------------------------------------------------------------

    SuaAspOperationalState ::=
        INTEGER {
            adminDisabled(0),
            blocked(1),
            down(2),
            up(3),
            congested(4)
        }
                
    ----------------------------------------------------------------------------
    --
    --  SuaAspTableIndex defines the index for the suaAspTable.
    --
    ----------------------------------------------------------------------------

    SuaAspTableIndex ::=
        Gauge(1..128)

    ----------------------------------------------------------------------------
    --
    --  SuaLocalAddressTableIndex defines the index for the SuaLocalAddressTable.
    --
    ----------------------------------------------------------------------------

    SuaLocalAddressTableIndex ::=
        Gauge(1..16)

    ----------------------------------------------------------------------------
    --
    --  SuaRemoteAddressTableIndex defines the index for the SuaRemoteAddressTable.
    --
    ----------------------------------------------------------------------------

    SuaRemoteAddressTableIndex ::=
        Gauge(1..16)

    -- the MTP subsystem
 
    mtp OBJECT IDENTIFIER ::= { textpass 11 }

    -- the MTP addresses group

    mtpAddresses OBJECT IDENTIFIER ::= { mtp 1 }
       
    mtpAddrNetworkIndicator OBJECT-TYPE
        SYNTAX  NetworkIndicator
        ACCESS  read-write
        STATUS  mandatory
        DESCRIPTION
            "Indicator specifying the type of SS.7 network
             Values:
             0 - international
             1 - spare (international use only)
             2 - national
             3 - reserved for national use.
             Default value is 2."             
        ::= { mtpAddresses 1 }
        
    mtpAddrActualPointCode OBJECT-TYPE
        SYNTAX  PointCode
        ACCESS  read-write
        STATUS  mandatory
        DESCRIPTION
            "Point code used to address this specific TextPass device and 
             formatted as commonly done in ITU-T.
             Note that this point code can be changed/viewed by this object as 
             well as the mtpAddrActualPointCodeString object."
        ::= { mtpAddresses 2 }

    mtpAddrVirtualPointCode OBJECT-TYPE
        SYNTAX  PointCode
        ACCESS  read-write
        STATUS  mandatory
        DESCRIPTION
            "Point code used to address a platform consisting of a group of 
             TextPass devices and formatted as commonly done in ITU-T.
             Note that this point code can be changed/viewed by this object as 
             well as the mtpAddrVirtualPointCodeString object."
        ::= { mtpAddresses 3 }
        
    mtpAddrActualPointCodeString OBJECT-TYPE
        SYNTAX  PointCodeString
        ACCESS  read-write
        STATUS  mandatory
        DESCRIPTION
            "Point code used to address this specific TextPass device and 
             formatted as commonly done in ANSI.
             Note that this point code can be changed/viewed by this object as 
             well as the mtpAddrActualPointCode object."
        ::= { mtpAddresses 4 }

    mtpAddrVirtualPointCodeString OBJECT-TYPE
        SYNTAX  PointCodeString
        ACCESS  read-write
        STATUS  mandatory
        DESCRIPTION
            "Point code used to address a platform consisting of a group of 
             TextPass devices and formatted as commonly done in ANSI.
             Note that this point code can be changed/viewed by this object as 
             well as the mtpAddrVirtualPointCode object."
        ::= { mtpAddresses 5 }
        
    -- the MTP L2 timers group
    
    mtpL2Timers OBJECT IDENTIFIER ::= { mtp 2 }
    
    mtpL2Timer1 OBJECT-TYPE
        SYNTAX  Gauge(400..500)
        ACCESS  read-write
        STATUS  mandatory
        DESCRIPTION
            "Timer 'alignment ready', expressed in units of 100 ms. Only 
             modify-able after boot and before any link is enabled. Default is
             50 seconds."
        ::= { mtpL2Timers 1 }

    mtpL2Timer2 OBJECT-TYPE
        SYNTAX  Gauge(50..1500)
        ACCESS  read-write
        STATUS  mandatory
        DESCRIPTION
            "Timer 'not aligned', expressed in units of 100 ms. Only
             modify-able after boot and before any link is enabled. Default is
             150 seconds."
        ::= { mtpL2Timers 2 }

    mtpL2Timer3 OBJECT-TYPE
        SYNTAX  Gauge(10..20)
        ACCESS  read-write
        STATUS  mandatory
        DESCRIPTION
            "Timer 'aligned', expressed in units of 100 ms. Only modify-able 
            after boot and before any link is enabled. Default is 1.5 seconds."
        ::= { mtpL2Timers 3 }

    mtpL2Timer4Normal OBJECT-TYPE
        SYNTAX  Gauge(75..95)
        ACCESS  read-write
        STATUS  mandatory
        DESCRIPTION
            "Timer 'normal proving', expressed in units of 100 ms. Only 
             modify-able after boot and before any link is enabled. Default is
             9 seconds."
        ::= { mtpL2Timers 4 }

    mtpL2Timer4Emergency OBJECT-TYPE
        SYNTAX  Gauge(4..6)
        ACCESS  read-write
        STATUS  mandatory
        DESCRIPTION
            "Timer 'emergency proving', expressed in units of 100 ms  Only 
             modify-able after boot and before any link is enabled. Default is
             0.6 seconds."
        ::= { mtpL2Timers 5 }

    mtpL2Timer5 OBJECT-TYPE
        SYNTAX  Gauge(1..1)
        ACCESS  read-write
        STATUS  mandatory
        DESCRIPTION
            "Timer 'sending SIB', expressed in units of 100 ms. Only 
             modify-able after boot and before any link is enabled. Default is
             1 second."
        ::= { mtpL2Timers 6 }

    mtpL2Timer6 OBJECT-TYPE
        SYNTAX  Gauge(30..60)
        ACCESS  read-write
        STATUS  mandatory
        DESCRIPTION
            "Timer 'remote congestion', expressed in units of 100 ms. Only 
             modify-able after boot and before any link is enabled. Default is
             6 seconds."
        ::= { mtpL2Timers 7 }

    mtpL2Timer7 OBJECT-TYPE
        SYNTAX  Gauge(5..20)
        ACCESS  read-write
        STATUS  mandatory
        DESCRIPTION
            "Timer 'excessive delay of acknowledgement', expressed in units of 
            100 ms. Only modify-able after boot and before any link is enabled. 
            Default is 20 seconds."
        ::= { mtpL2Timers 8 }

    -- the MTP test & maintenance timers group

    mtpTestTimers OBJECT IDENTIFIER ::= { mtp 3 }

    mtpTestTimer1 OBJECT-TYPE
        SYNTAX  Gauge(40..120)
        ACCESS  read-write
        STATUS  mandatory
        DESCRIPTION
            "Timer defining maximum time span allowed between test request 
             message (an SLTM) and its response (an SLTA), expressed in units 
             of 100 ms. Default is 8 seconds."
        ::= { mtpTestTimers 1 }

    mtpTestTimer2 OBJECT-TYPE
        SYNTAX  Gauge(300..900)
        ACCESS  read-write
        STATUS  mandatory
        DESCRIPTION
            "Timer defining the duration of the interval at which test request 
             messages are sent, expressed in units of 100 ms. Default is 60 
             seconds."
        ::= { mtpTestTimers 2 }

    -- the MTP management timers group

    mtpManagementTimers OBJECT IDENTIFIER ::= { mtp 4 }

    mtpManagementTimer2 OBJECT-TYPE
        SYNTAX  Gauge(7..20)
        ACCESS  read-write
        STATUS  mandatory
        DESCRIPTION
            "Timer waiting for change-over acknowledgement, expressed in units of 
             100 ms. Default is 1.4 seconds."
        ::= { mtpManagementTimers 1 }
    mtpManagementTimer10 OBJECT-TYPE
        SYNTAX  Gauge(300..600)       
        ACCESS  read-write
        STATUS  mandatory
        DESCRIPTION
            "Timer waiting to repeat signalling route set test messages, 
             expressed in units of 100 ms. Default is 45 seconds."
        ::= { mtpManagementTimers 2 }

    mtpManagementTimer15 OBJECT-TYPE
        SYNTAX  Gauge(20..30)
        ACCESS  read-write
        STATUS  mandatory
        DESCRIPTION
            "Timer waiting to start a signalling route set congestion test, 
             expressed in units of 100 ms. Default value is 3.0 seconds."
        ::= { mtpManagementTimers 3 }

    mtpManagementTimer16 OBJECT-TYPE
        SYNTAX  Gauge(14..20)
        ACCESS  read-write
        STATUS  mandatory
        DESCRIPTION
            "Timer waiting for route set congestion status update, expressed 
             in units of 100 ms. Default value is 2.0 seconds."
        ::= { mtpManagementTimers 4 }

    mtpManagementTimer17 OBJECT-TYPE
        SYNTAX  Gauge(8..15)
        ACCESS  read-write
        STATUS  mandatory
        DESCRIPTION
            "Timer defining delay to avoid oscillation of initial alignment and 
             link restart, expressed in units of 100 ms. Default value is 1.0 
             seconds."
        ::= { mtpManagementTimers 5 }

    mtpManagementTimer19 OBJECT-TYPE
        SYNTAX  Gauge(670..690)
        ACCESS  read-write
        STATUS  mandatory
        DESCRIPTION
            "Supervision timer during MTP restart to avoid pin-pong of TFP, TFR 
             and TRA messages, expressed in units of 100 ms. Default value is 
             67 seconds."
        ::= { mtpManagementTimers 6 }

    mtpManagementTimer20 OBJECT-TYPE
        SYNTAX  Gauge(590..610)
        ACCESS  read-write
        STATUS  mandatory
        DESCRIPTION
            "Overall MTP restart timer at the signalling point whose MTP 
             restarts, expressed in units of 100 ms. Default value is 59
             seconds."
        ::= { mtpManagementTimers 7 }

    mtpManagementTimer21 OBJECT-TYPE
        SYNTAX  Gauge(630..650)
        ACCESS  read-write
        STATUS  mandatory
        DESCRIPTION
            "Overall MTP restart timer at a signalling point adjacent to one
             whose MTP restarts, expressed in units of 100 ms. Default value is 
             63 seconds."
        ::= { mtpManagementTimers 8 }

    mtpManagementTimer8 OBJECT-TYPE
        SYNTAX  Gauge(8..12)
        ACCESS  read-write
        STATUS  mandatory
        DESCRIPTION
            "Transfer prohibited inhibition timer, expressed in units of 100 ms. 
            Default value is 1.2 seconds."
        ::= { mtpManagementTimers 9 }

     -- the MTP SSCOP parameter group (only applicable for HSL)

    mtpSscopParams OBJECT IDENTIFIER ::= { mtp 10 }

    mtpSscopParamMaxCc OBJECT-TYPE
        SYNTAX  Gauge(1..10)
        ACCESS  read-write
        STATUS  mandatory
        DESCRIPTION
            "Maximum value for the state variable VT(CC), corresponding to the 
            maximum number of transmissions of a BGN, END, ER, or RS PDU. 
            Default is 4."
        ::= { mtpSscopParams 1 }

    mtpSscopParamMaxPd OBJECT-TYPE
        SYNTAX  Gauge(5..2120)
        ACCESS  read-write
        STATUS  mandatory
        DESCRIPTION
            "Maximum acceptable value for the state variable VT(PD) before 
            sending a POLL PDU and resetting VT(PD) to zero. This parameter is
            an upper limit for counter VT(PD) that sends a POLL PDU after every
            (MaxPD) SD PDU's. Default is 500."
        ::= { mtpSscopParams 2 }

    mtpSscopParamTimerCc OBJECT-TYPE
        SYNTAX  Gauge(200..2000)
        ACCESS  read-write
        STATUS  mandatory
        DESCRIPTION
            "Timer_CC, expressed in milliseconds. Default is 200 milliseconds."
        ::= { mtpSscopParams 3 }

    mtpSscopParamTimerKeepAlive OBJECT-TYPE
        SYNTAX  Gauge(25..500)
        ACCESS  read-write
        STATUS  mandatory
        DESCRIPTION
            "Timer_KEEP-ALIVE, expressed in milliseconds. Default is 100 ms."
        ::= { mtpSscopParams 4 }

    mtpSscopParamTimerNoResponse OBJECT-TYPE
        SYNTAX  Gauge(200..2000)
        ACCESS  read-write
        STATUS  mandatory
        DESCRIPTION
            "Timer_NO-RESPONSE, expressed in milliseconds. Default is 1500 ms."
        ::= { mtpSscopParams 5 }

    mtpSscopParamTimerPoll OBJECT-TYPE
        SYNTAX  Gauge(25..500)
        ACCESS  read-write
        STATUS  mandatory
        DESCRIPTION
            "Timer_POLL, expressed in milliseconds. Default is 100 ms."
        ::= { mtpSscopParams 6 }

    mtpSscopParamTimerIdle OBJECT-TYPE
        SYNTAX  Gauge(25..1000)
        ACCESS  read-write
        STATUS  mandatory
        DESCRIPTION
            "Timer_IDLE, expressed in milliseconds. Default is 100 ms."
        ::= { mtpSscopParams 7 }

     -- the MTP SSCF characterics group (only applicable for HSL)

    mtpSscfParams OBJECT IDENTIFIER ::= { mtp 11 }

    mtpSscfParamTimer1 OBJECT-TYPE
        SYNTAX  Gauge(1000..15000)
        ACCESS  read-write
        STATUS  mandatory
        DESCRIPTION
            "Time between the link release action an the next link re-establish 
            action during the alignment, expressed in units of milliseconds. 
            Default is 5 seconds."
        ::= { mtpSscfParams 1 }

    mtpSscfParamTimer2 OBJECT-TYPE
        SYNTAX  Gauge(15000..180000)
        ACCESS  read-write
        STATUS  mandatory
        DESCRIPTION
            "Total time SSCF will attempt alignment, expressed in units of 
            milliseconds. Default is 120 seconds."
        ::= { mtpSscfParams 2 }

    mtpSscfParamTimer3 OBJECT-TYPE
        SYNTAX  Gauge(1..25)
        ACCESS  read-write
        STATUS  mandatory
        DESCRIPTION
            "Time between proving PDUs, expressed in units of milliseconds. 
            Default is 10 milliseconds."
        ::= { mtpSscfParams 3 }

    mtpSscfParamN1 OBJECT-TYPE
        SYNTAX  Gauge(500..500000)
        ACCESS  read-write
        STATUS  mandatory
        DESCRIPTION
            "The number of PDUS sent during normal proving. Default is 1000."
        ::= { mtpSscfParams 4 }

     -- the MTP Link utilisation thresholds

    mtpProperties OBJECT IDENTIFIER ::= { mtp 12 }

    mtpLinkUtilisationThreshold1 OBJECT-TYPE
        SYNTAX  Percentage
        ACCESS  read-write
        STATUS  mandatory
        DESCRIPTION
            "A threshold at which a trap will be generated if the link
             utilisation (Rx or Tx) crosses this (growing or shrinking).
             When zero no trap will be generated."
        ::= { mtpProperties 1 }

    mtpLinkUtilisationThreshold2 OBJECT-TYPE
        SYNTAX  Percentage
        ACCESS  read-write
        STATUS  mandatory
        DESCRIPTION
            "A threshold at which a trap will be generated if the link
             utilisation (Rx or Tx) crosses this (growing or shrinking).
             When zero no trap will be generated."
        ::= { mtpProperties 2 }

    mtpLinkUtilisationThreshold3 OBJECT-TYPE
        SYNTAX  Percentage
        ACCESS  read-write
        STATUS  mandatory
        DESCRIPTION
            "A threshold at which a trap will be generated if the link
             utilisation (Rx or Tx) crosses this (growing or shrinking).
             When zero no trap will be generated."
        ::= { mtpProperties 3 }

    mtpLinkUtilisationThreshold4 OBJECT-TYPE
        SYNTAX  Percentage
        ACCESS  read-write
        STATUS  mandatory
        DESCRIPTION
            "A threshold at which a trap will be generated if the link
             utilisation (Rx or Tx) crosses this (growing or shrinking).
             When zero no trap will be generated."
        ::= { mtpProperties 4 }

    mtpLinkUtilisationThreshold5 OBJECT-TYPE
        SYNTAX  Percentage
        ACCESS  read-write
        STATUS  mandatory
        DESCRIPTION
            "A threshold at which a trap will be generated if the link
             utilisation (Rx or Tx) crosses this (growing or shrinking).
             When zero no trap will be generated."
        ::= { mtpProperties 5 }

    -- the MTP counters group

    mtpCounters OBJECT IDENTIFIER ::= { mtp 13 }

    mtpRecvMgmtCounter OBJECT-TYPE
        SYNTAX Counter
        ACCESS read-only
        STATUS mandatory
        DESCRIPTION
            "Counter specifying the number of MTP Management MSU's received."
        ::= { mtpCounters 1 }

    mtpSentMgmtCounter OBJECT-TYPE
        SYNTAX Counter
        ACCESS read-only
        STATUS mandatory
        DESCRIPTION
            "Counter specifying the number of MTP Management MSU's sent."
        ::= { mtpCounters 2 }
      
    mtpRecvTestCounter OBJECT-TYPE
        SYNTAX Counter
        ACCESS read-only
        STATUS mandatory
        DESCRIPTION
            "Counter specifying the number of MTP Testing & Maintenance MSU's 
            received."
        ::= { mtpCounters 3 }
      
    mtpSentTestCounter OBJECT-TYPE
        SYNTAX Counter
        ACCESS read-only
        STATUS mandatory
        DESCRIPTION
            "Counter specifying the number of MTP Testing & Maintenance MSU's 
            sent."
        ::= { mtpCounters 4 }
      
    mtpRecvSccpCounter OBJECT-TYPE
        SYNTAX Counter
        ACCESS read-only
        STATUS mandatory
        DESCRIPTION
            "Counter specifying the number of SCCP MSU's received."
        ::= { mtpCounters 5 }
      
    mtpSentSccpCounter OBJECT-TYPE
        SYNTAX Counter
        ACCESS read-only
        STATUS mandatory
        DESCRIPTION
            "Counter specifying the number of SCCP MSU's sent."
        ::= { mtpCounters 6 }

    -- the MTP trunk group 
    
    mtpTrunkTable OBJECT-TYPE
        SYNTAX  SEQUENCE OF MtpTrunkEntry
        ACCESS  not-accessible
        STATUS  mandatory
        DESCRIPTION
            "Table containing info about E1/T1 trunks."
        ::= { mtp 5 }
 
    mtpTrunkEntry OBJECT-TYPE
        SYNTAX  MtpTrunkEntry
        ACCESS  not-accessible
        STATUS  mandatory
        DESCRIPTION
            "Entry of table containing info about E1/T1 trunks."
        INDEX   { mtpTrunkIndex }
        ::= { mtpTrunkTable 1 }

    MtpTrunkEntry ::=
        SEQUENCE {
            mtpTrunkIndex                         Gauge(1..6),
            mtpTrunkAdminState                    AdminState,
            mtpTrunkOperationalState              TrunkOperationalState,
            mtpTrunkType                          TrunkType,
            mtpTrunkLoopBack                      Boolean,
            mtpTrunkClockGeneration               Boolean,
            mtpTrunkBipolarViolations             Counter,
            mtpTrunkExcessiveZeroes               Counter,
            mtpTrunkFramingErrors                 Counter,           
            mtpTrunkCrc4Errors                    Counter,           
            mtpTrunkControlledSlips               Counter,
            mtpTrunkMultiframeLossOfFrame         Counter,
            mtpTrunkEBitErrors                    Counter,
            mtpTrunkSeverlyErroredFrames          Counter,
            mtpTrunkAtmScramblingEnabled          Boolean
        }

   mtpTrunkIndex OBJECT-TYPE
        SYNTAX  Gauge(1..16)
        ACCESS  not-accessible
        STATUS  mandatory
        DESCRIPTION
            "Index of entry in table containing info about E1/T1 trunks."
        ::= { mtpTrunkEntry 1 }

    mtpTrunkAdminState OBJECT-TYPE
        SYNTAX  AdminState
        ACCESS  read-write
        STATUS  mandatory
        DESCRIPTION
            "Administrative state of entry in table containing info about the 
             E1/T1 trunks. Activating a trunk, deactivating a trunk or 
             removing an entry from table (and implicitly deactivating the 
             associated trunk) is accomplished by writing the administrative
             state."
        ::= { mtpTrunkEntry 2 }

    mtpTrunkOperationalState OBJECT-TYPE
        SYNTAX  TrunkOperationalState
        ACCESS  read-only
        STATUS  mandatory
        DESCRIPTION
            "Operational state of E1/T1 trunk."
        ::= { mtpTrunkEntry 3 }

    mtpTrunkType OBJECT-TYPE
        SYNTAX  TrunkType
        ACCESS  read-write
        STATUS  mandatory
        DESCRIPTION
            "Type of E1/T1 trunk. The default is E1 120 Ohm and CRC. Only
             modify-able if the entry's administrative state is 'inactive'."
        ::= { mtpTrunkEntry 4 }

    mtpTrunkLoopBack OBJECT-TYPE
        SYNTAX  Boolean
        ACCESS  read-write
        STATUS  mandatory
        DESCRIPTION
            "Indicator to enable of disable loopback for E1/T1 trunk. When 
             loopback is enabled, data that the E1/T1 trunk receives from the
             SS7 network is sent back to the SS7 network without passing it to
             to TextPass. By default, loopback is disabled. Only modify-able 
             if the entry's administrative state is 'inactive'."
        ::= { mtpTrunkEntry 5 }

    mtpTrunkClockGeneration OBJECT-TYPE
        SYNTAX  Boolean
        ACCESS  read-write
        STATUS  mandatory
        DESCRIPTION
            "Indicator to enable of disable clock generation of the trunk. When
             clock generation is enabled, TextPass generates a clock on Tx which
             is independent of the clock on Rx clock. When clock generation is
             disabled, TextPass derives the Tx clock from the Rx clock. By 
             default, clock generation is disabled. Only modify-able if the 
             entry's administrative state is 'inactive'."
        ::= { mtpTrunkEntry 6 }
        
    mtpTrunkBipolarViolations OBJECT-TYPE
        SYNTAX  Counter
        ACCESS  read-only
        STATUS  mandatory
        DESCRIPTION
            "The Number of Bipolar Violations  (HDB3 or B8ZS) that occurred on the trunk since activation."          
        ::= { mtpTrunkEntry 7 }

    mtpTrunkExcessiveZeroes OBJECT-TYPE
        SYNTAX  Counter
        ACCESS  read-only
        STATUS  mandatory
        DESCRIPTION
            "The Number of Excessive Zeroes that occurred on the trunk since activation."          
        ::= { mtpTrunkEntry 8 }

    mtpTrunkFramingErrors OBJECT-TYPE
        SYNTAX  Counter
        ACCESS  read-only
        STATUS  mandatory
        DESCRIPTION
            "The Number of Framing Errors (FAS word errors) that occurred on the trunk since activation."          
        ::= { mtpTrunkEntry 9 }
    
    mtpTrunkCrc4Errors OBJECT-TYPE
        SYNTAX  Counter
        ACCESS  read-only
        STATUS  mandatory
        DESCRIPTION
            "The Number of Frames with a wrong CRC4 that occurred on the trunk since boot up."          
        ::= { mtpTrunkEntry 10 }
    
    mtpTrunkControlledSlips OBJECT-TYPE
        SYNTAX  Counter
        ACCESS  read-only
        STATUS  mandatory
        DESCRIPTION
            "The Number of Controlled Slips  (HDB3 or B8ZS) that occurred on the trunk since activation."          
        ::= { mtpTrunkEntry 11 }

    mtpTrunkMultiframeLossOfFrame OBJECT-TYPE
        SYNTAX  Counter
        ACCESS  read-only
        STATUS  mandatory
        DESCRIPTION
            "The Number of multiframe loss-of-frame that occurred on the trunk since boot up."          
        ::= { mtpTrunkEntry 12 }

    mtpTrunkEBitErrors OBJECT-TYPE
        SYNTAX  Counter
        ACCESS  read-only
        STATUS  mandatory
        DESCRIPTION
            "The Number of E1 E-bit errors that occurred on the trunk since activation."          
        ::= { mtpTrunkEntry 13 }

    mtpTrunkSeverlyErroredFrames OBJECT-TYPE
        SYNTAX  Counter
        ACCESS  read-only
        STATUS  mandatory
        DESCRIPTION
            "The Number of Severly Errored Frames that were recevied on the trunk since activation."          
        ::= { mtpTrunkEntry 14 }

    mtpTrunkAtmScramblingEnabled OBJECT-TYPE
        SYNTAX  Boolean
        ACCESS  read-only
        STATUS  mandatory
        DESCRIPTION
            "Indicator specifying whether ATM scrambling should be enabled or not. Only applicable for HSL. 
            By default, ATM scrambling is enabled."          
        ::= { mtpTrunkEntry 31 }


    -- the MTP linkset group
    
    mtpLinkSetTable OBJECT-TYPE
        SYNTAX  SEQUENCE OF MtpLinkSetEntry
        ACCESS  not-accessible
        STATUS  mandatory
        DESCRIPTION
            "Table containing info about MTP linksets."
        ::= { mtp 6 }

    mtpLinkSetEntry OBJECT-TYPE
        SYNTAX  MtpLinkSetEntry
        ACCESS  not-accessible
        STATUS  mandatory
        DESCRIPTION
            "Entry of table containing info about MTP linksets."
        INDEX   { mtpLinkSetIndex }
        ::= { mtpLinkSetTable 1 }

    MtpLinkSetEntry ::=
        SEQUENCE {
            mtpLinkSetIndex                       Gauge(1..16),
            mtpLinkSetAdminState                  AdminState,
            mtpLinkSetOperationalState            LinkSetOperationalState,
            mtpLinkSetName                        NameString,
            mtpLinkSetOwnPointCode                PointCode,
            mtpLinkSetDestination                 NameString,
            mtpLinkSetThroughput                  Throughput,
            mtpLinkSetEmergencyProvingMode        EmergencyProvingMode,
            mtpLinkSetOwnPointCodeString          PointCodeString
        }     

    mtpLinkSetIndex OBJECT-TYPE
        SYNTAX  Gauge(1..16)
        ACCESS  not-accessible
        STATUS  mandatory
        DESCRIPTION
            "Index of entry in table containing info about MTP linksets."
        ::= { mtpLinkSetEntry 1 }

    mtpLinkSetAdminState OBJECT-TYPE
        SYNTAX  AdminState
        ACCESS  read-write
        STATUS  mandatory
        DESCRIPTION
            "Administrative state of entry in table containing info about the 
             MTP linksets. Activating a linkset, deactivating a linkset or 
             removing an entry from the table (and implicitly deactivating the 
             associated linkset) is accomplished by writing the administrative
             state."
        ::= { mtpLinkSetEntry 2 }

    mtpLinkSetOperationalState OBJECT-TYPE
        SYNTAX  LinkSetOperationalState
        ACCESS  read-only
        STATUS  mandatory
        DESCRIPTION
            "Operational state of linkset."
        ::= { mtpLinkSetEntry 3 }

    mtpLinkSetName OBJECT-TYPE
        SYNTAX  NameString
        ACCESS  read-write
        STATUS  mandatory
        DESCRIPTION
            "Name of linkset. Only modify-able if the entry's administrative 
             state is 'inactive'."
        ::= { mtpLinkSetEntry 4 }

    mtpLinkSetOwnPointCode OBJECT-TYPE
        SYNTAX  PointCode
        ACCESS  read-write
        STATUS  mandatory
        DESCRIPTION
            "Point code used as OPC on linkset and formatted as commonly done 
             in ITU-T.
             If not specified, the value of the mtpAddrActualPointCode 
             attribute is used as OPC. Only modify-able if the entry's 
             administrative state is 'inactive'.
             Note that this point code can be changed/viewed by this object as 
             well as the mtpLinkSetOwnPointCodeString object."
        ::= { mtpLinkSetEntry 5 }

    mtpLinkSetDestination OBJECT-TYPE
        SYNTAX  NameString
        ACCESS  read-write
        STATUS  mandatory
        DESCRIPTION
            "Name of entry in MTP destination table that contains properties 
            of adjacent of linkset. Only modify-able if the entry's 
            administrative state is 'inactive'."
        ::= { mtpLinkSetEntry 6 }

    mtpLinkSetThroughput OBJECT-TYPE
        SYNTAX  Throughput
        ACCESS  read-write
        STATUS  mandatory
        DESCRIPTION
            "Maximum throughput per link in terms of MSU's per second 
            (excluding the MSU's for MTP management and MTP testing & 
            maintenance)."
        ::= { mtpLinkSetEntry 7 }

    mtpLinkSetEmergencyProvingMode OBJECT-TYPE
        SYNTAX  EmergencyProvingMode
        ACCESS  read-write
        STATUS  mandatory
        DESCRIPTION
            "Specifies how emergency proving should be applied. Default is
            firstLinkOnly."
        ::= { mtpLinkSetEntry 8 }

    mtpLinkSetOwnPointCodeString OBJECT-TYPE
        SYNTAX  PointCodeString
        ACCESS  read-write
        STATUS  mandatory
        DESCRIPTION
            "Point code used as OPC on linkset and formatted as commonly done 
             in ANSI.
             If not specified, the value of the mtpAddrActualPointCode 
             attribute is used as OPC. Only modify-able if the entry's 
             administrative state is 'inactive'.
             Note that this point code can be changed/viewed by this object as 
             well as the mtpLinkSetOwnPointCode object."
        ::= { mtpLinkSetEntry 9 }


    -- the MTP link group
    
    mtpLinkTable OBJECT-TYPE
        SYNTAX  SEQUENCE OF MtpLinkEntry
        ACCESS  not-accessible
        STATUS  mandatory
        DESCRIPTION
            "Table containing info about MTP links. For each MTP linkset,
             a table of this type should exist."
        ::= { mtp 7 }

    mtpLinkEntry OBJECT-TYPE
        SYNTAX  MtpLinkEntry
        ACCESS  not-accessible
        STATUS  mandatory
        DESCRIPTION
            "Entry of table containing info about MTP links."
        INDEX   { mtpLinkSetIndex, mtpLinkIndex }

        ::= { mtpLinkTable 1 }

    MtpLinkEntry ::=
        SEQUENCE {
            mtpLinkIndex                          Gauge(1..32),
            mtpLinkAdminState                     AdminState,
            mtpLinkOperationalState               LinkOperationalState,
            mtpLinkCode                           SignallingLinkCode,
            mtpLinkTrunk                          Trunk,
            mtpLinkTimeSlot                       TimeSlot,
            mtpLinkTraceEnabled                   Boolean,          
            mtpLinkCodeError                      ErrorString,
            mtpLinkTextPassPcError                ErrorString,
            mtpLinkAdjacentPcError                ErrorString,
            mtpLinkNetworkIndicatorError          ErrorString,
            mtpLinkRxUtilisation                  Percentage,
            mtpLinkTxUtilisation                  Percentage,
            mtpLinkAtmOperationalState            AtmOperationalState,
            mtpLinkAtmLineRecvCellCounter         Counter,
            mtpLinkAtmLineSentCellCounter         Counter,
            mtpLinkAtmDriverRecvCellCounter       Counter,
            mtpLinkAtmDriverSentCellCounter       Counter,
            mtpLinkAtmDriverRecvOamCellCounter    Counter,
            mtpLinkAtmAllocFailureCounter         Counter,
            mtpLinkAtmWrongVcCounter              Counter,
            mtpLinkAtmBadHecCounter               Counter,
            mtpLinkAtmMiscErrorCounter            Counter,
            mtpLinkAtmLossOfCellDelineationCounter Counter,
            mtpLinkAtmHecAnomoliesCounter         Counter,   
            mtpLinkAtmTxFifoFullCounter           Counter,
            mtpLinkAal5RecvPduCounter             Counter,
            mtpLinkAal5SentPduCounter             Counter,
            mtpLinkAal5LengthErrorCounter         Counter,
            mtpLinkAalRxCongestionCounter         Counter,
            mtpLinkAal5CrcErrorCounter            Counter,
            mtpLinkSscopRecvPduCounter            Counter,
            mtpLinkSscopSentPduCounter            Counter,
            mtpLinkSscopRecvPduBytesCounter       Counter,
            mtpLinkSscopSentPduBytesCounter       Counter,
            mtpLinkSscopRecvBgnPduCounter         Counter,
            mtpLinkSscopSentBgnPduCounter         Counter,
            mtpLinkSscopRecvBgakPduCounter        Counter,
            mtpLinkSscopSentBgakPduCounter        Counter,
            mtpLinkSscopRecvBgrejPduCounter       Counter,            
            mtpLinkSscopSentBgrejPduCounter       Counter,
            mtpLinkSscopRecvRsPduCounter          Counter,
            mtpLinkSscopSentRsPduCounter          Counter,
            mtpLinkSscopRecvRsakPduCounter        Counter,
            mtpLinkSscopSentRsakPduCounter        Counter,
            mtpLinkSscopRecvEndPduCounter         Counter,
            mtpLinkSscopSentEndPduCounter         Counter,
            mtpLinkSscopRecvEndakPduCounter       Counter,
            mtpLinkSscopSentEndakPduCounter       Counter,
            mtpLinkSscopRecvErPduCounter          Counter,
            mtpLinkSscopSentErPduCounter          Counter,
            mtpLinkSscopRecvErakPduCounter        Counter,
            mtpLinkSscopSentErakPduCounter        Counter,
            mtpLinkSscopRecvPollPduCounter        Counter,
            mtpLinkSscopSentPollPduCounter        Counter,
            mtpLinkSscopRecvStatPduCounter        Counter,
            mtpLinkSscopSentStatPduCounter        Counter,
            mtpLinkSscopRecvUstatPduCounter       Counter,
            mtpLinkSscopSentUstatPduCounter       Counter,
            mtpLinkSscopRecvUdPduCounter          Counter,
            mtpLinkSscopSentUdPduCounter          Counter,
            mtpLinkSscopRecvMdPduCounter          Counter,
            mtpLinkSscopSentMdPduCounter          Counter,
            mtpLinkSscopRecvSdPduCounter          Counter,
            mtpLinkSscopSentSdPduCounter          Counter,
            mtpLinkSscopLastUpTime                DateTime,
            mtpLinkSscopLastDownTime              DateTime,
            mtpLinkSscopOperationalState          SscopOperationalState,
            mtpLinkSscopErrorATillMCounter        Counter,
            mtpLinkSscopErrorOCounter             Counter,
            mtpLinkSscopErrorPCounter             Counter,
            mtpLinkSscopErrorQCounter             Counter,
            mtpLinkSscopErrorRCounter             Counter,
            mtpLinkSscopErrorSCounter             Counter,
            mtpLinkSscopErrorTCounter             Counter,
            mtpLinkSscopErrorUCounter             Counter,
            mtpLinkSscopErrorVCounter             Counter,
            mtpLinkSscopErrorWCounter             Counter,
            mtpLinkSscopErrorXCounter             Counter,
            mtpLinkSscopToBeSentToPeerCounter     Gauge,
            mtpLinkSscopToBeAckdByPeerCounter     Gauge,
            mtpLinkSscopVtS                       Gauge,
            mtpLinkSscopVtA                       Gauge,
            mtpLinkSscopVtMr                      Gauge,
            mtpLinkSscfRecvPduCounter             Counter,
            mtpLinkSscfSentPduCounter             Counter,
            mtpLinkSscfReSentPduCounter           Counter,
            mtpLinkSscfRecvPduBytesCounter        Counter,
            mtpLinkSscfSentPduBytesCounter        Counter,
            mtpLinkSscfReSentPduBytesCounter      Counter,
            mtpLinkSscfAlignmentFailureCounter    Counter,
            mtpLinkSscfLastInServiceTime          DateTime,
            mtpLinkSscfNoCreditCounter            Counter,
            mtpLinkSscfTotalNoCreditDuration      Counter,
            mtpLinkSscfOperationalState           SscfOperationalState,
            mtpLinkSscfLocalProcOutage            Boolean,
            mtpLinkSscfLastLocalProcOutageTime    DateTime,
            mtpLinkSscfTotalLocalProcOutageDuration Counter,
            mtpLinkSscfRemoteProcOutage           Boolean,
            mtpLinkSscfLastRemoteProcOutageTime   DateTime,
            mtpLinkSscfTotalRemoteProcOutageDuration Counter,
            mtpLinkMtpRecvMgmtCounter             Counter,
            mtpLinkMtpSentMgmtCounter             Counter,
            mtpLinkMtpRecvTestCounter             Counter,
            mtpLinkMtpSentTestCounter             Counter,
            mtpLinkMtpRecvSccpCounter             Counter,
            mtpLinkMtpSentSccpCounter             Counter,
            mtpLinkInServiceStartTime             TimeTicks,
            mtpLinkFailureAllReason               Counter,
            mtpLinkFailureAbnormalFibBsnNum       Counter,
            mtpLinkT7Expiry                       Counter,
            mtpLinkCongTooLong                    Counter,
            mtpLinkFailureSuerm                   Counter,
            mtpLinkFailureT2T3Expiry              Counter,
            mtpLinkProvingAligningFailure         Counter,
            mtpLinkNumSuError                     Counter,
            mtpLinkNumNack                        Counter,
            mtpLinkNumMsuRtx                      Counter,
            mtpLinkNumMsuOctetRtx                 Counter,
            mtpLinkNumMSuOctetTx                  Counter,
            mtpLinkNumMsuOctetRx                  Counter,
            mtpLinkNumMsuTx                       Counter,       
            mtpLinkNumMsuRx                       Counter,
            mtpLinkNumSibTx                       Counter,
            mtpLinkNumSibRx                       Counter
        }     

    mtpLinkIndex OBJECT-TYPE
        SYNTAX  Gauge(1..32)
        ACCESS  not-accessible
        STATUS  mandatory
        DESCRIPTION
            "Index of entry in table containing info about MTP links."
        ::= { mtpLinkEntry 1 }

    mtpLinkAdminState OBJECT-TYPE
        SYNTAX  AdminState
        ACCESS  read-write
        STATUS  mandatory
        DESCRIPTION
            "Administrative state of entry in table containing info about the 
             MTP links. Activating a link, deactivating a link or removing an 
             entry from the table (and implicitly deactivating the associated 
             link) is accomplished by writing the administrative state."
        ::= { mtpLinkEntry 2 }

    mtpLinkOperationalState OBJECT-TYPE
        SYNTAX  LinkOperationalState
        ACCESS  read-only
        STATUS  mandatory
        DESCRIPTION
            "Operational state of link."
        ::= { mtpLinkEntry 3 }

    mtpLinkCode OBJECT-TYPE
        SYNTAX  SignallingLinkCode
        ACCESS  read-write
        STATUS  mandatory
        DESCRIPTION
            "Signalling link code (SLC) of link. Only modify-able if the entry's 
             administrative state is 'inactive'."
        ::= { mtpLinkEntry 4 }

    mtpLinkTrunk OBJECT-TYPE
        SYNTAX  Trunk
        ACCESS  read-write
        STATUS  mandatory
        DESCRIPTION
            "Trunk used for link. Only modify-able if the entry's administrative 
             state is 'inactive'."
        ::= { mtpLinkEntry 5 }

    mtpLinkTimeSlot OBJECT-TYPE
        SYNTAX  TimeSlot
        ACCESS  read-write
        STATUS  mandatory
        DESCRIPTION
            "Timeslot on trunk used for link. Only modify-able if the entry's 
            administrative state is 'inactive'."
        ::= { mtpLinkEntry 6 }

    mtpLinkTraceEnabled OBJECT-TYPE
        SYNTAX  Boolean
        ACCESS  read-write
        STATUS  mandatory
        DESCRIPTION
            "Indicator to enable or disable tracing of link"
        ::= { mtpLinkEntry 7 }

    mtpLinkCodeError OBJECT-TYPE
        SYNTAX  ErrorString
        ACCESS  read-only
        STATUS  mandatory
        DESCRIPTION
            "Error message which is present in case of a mismatch in 
             configuration of link's SLC. The error message shows value for SLC 
             as configured on TextPass device and value for SLC as configured on 
             adjacent."
        ::= { mtpLinkEntry 8 }
        
    mtpLinkTextPassPcError OBJECT-TYPE
        SYNTAX  ErrorString
        ACCESS  read-only
        STATUS  mandatory
        DESCRIPTION
            "Error message which is present in case of a mismatch in 
             configuration of TextPass's point code. The error message shows 
             value for this point code as configured on TextPass device and value 
             for this point code as configured on adjacent."
        ::= { mtpLinkEntry 9 }
        
    mtpLinkAdjacentPcError OBJECT-TYPE
        SYNTAX  ErrorString
        ACCESS  read-only
        STATUS  mandatory
        DESCRIPTION
            "Error message which is present in case of a mismatch in 
             configuration of adjacent's point code. The error message shows 
             value for this point code as configured on TextPass device and value 
             for this point code as configured on adjacent."
        ::= { mtpLinkEntry 10 }                
        
    mtpLinkNetworkIndicatorError OBJECT-TYPE
        SYNTAX  ErrorString
        ACCESS  read-only
        STATUS  mandatory
        DESCRIPTION
            "Error message which is present in case of a mismatch in 
             configuration of the network indicator. The error message shows 
             value for the network indicator as configured on TextPass device 
             and value for the network indicator as configured on adjacent."
        ::= { mtpLinkEntry 11 }
        
    mtpLinkRxUtilisation OBJECT-TYPE
        SYNTAX  Percentage
        ACCESS  read-only
        STATUS  mandatory
        DESCRIPTION
            "Link utilisation on receiving stream during previous second. Link
            utilisation is defined as the rate between the actual load and the
            maximum load possible. Expressed in percents (e.g. 0.4 Erlang 
            results in a utilisation value of 40). Only applicable for NSL and
            HSL."
        ::= { mtpLinkEntry 21 }
        
    mtpLinkTxUtilisation OBJECT-TYPE
        SYNTAX  Percentage
        ACCESS  read-only
        STATUS  mandatory
        DESCRIPTION
            "Link utilisation on transmitting stream during previous second. 
            Link utilisation is defined as the rate between the actual load and
            the maximum load possible. Expressed in percents (e.g. 0.4 Erlang 
            results in a utilisation value of 40). Only applicable for NSL and
            HSL."
        ::= { mtpLinkEntry 22 }
        
     mtpLinkAtmOperationalState OBJECT-TYPE
        SYNTAX AtmOperationalState
        ACCESS read-only
        STATUS mandatory
        DESCRIPTION 
            "Current ATM state. Only applicable for HSL."
        ::= { mtpLinkEntry 31 }

    mtpLinkAtmLineRecvCellCounter OBJECT-TYPE
        SYNTAX Counter
        ACCESS read-only
        STATUS mandatory
        DESCRIPTION
            "Counter specifying the number of ATM cells received on the line. 
            Only applicable for HSL."
        ::= { mtpLinkEntry 41 }    
    
    mtpLinkAtmLineSentCellCounter OBJECT-TYPE
        SYNTAX Counter
        ACCESS read-only
        STATUS mandatory
        DESCRIPTION
            "Counter specifying the number of ATM cells sent on the line. Only 
            applicable for HSL."
        ::= { mtpLinkEntry 42 }    
    
    mtpLinkAtmDriverRecvCellCounter OBJECT-TYPE
        SYNTAX Counter
        ACCESS read-only
        STATUS mandatory
        DESCRIPTION
            "Counter specifying the number of ATM cells received by the device 
            driver. Only applicable for HSL."
        ::= { mtpLinkEntry 43 }    
    
    mtpLinkAtmDriverSentCellCounter OBJECT-TYPE
        SYNTAX Counter
        ACCESS read-only
        STATUS mandatory
        DESCRIPTION
            "Counter specifying the number of ATM cells sent by the device 
            driver. Only applicable for HSL."
        ::= { mtpLinkEntry 44 }    
        
    mtpLinkAtmDriverRecvOamCellCounter OBJECT-TYPE
        SYNTAX Counter
        ACCESS read-only
        STATUS mandatory
        DESCRIPTION
            "Counter specifying the number of OAM ATM Cells received by the 
            device driver. Only applicable for HSL."
            ::= { mtpLinkEntry 45 }    
            
    mtpLinkAtmAllocFailureCounter OBJECT-TYPE
        SYNTAX Counter
        ACCESS read-only
        STATUS mandatory
        DESCRIPTION
            "Counter specifying the number of cells dropped due to buffer 
            allocation failures.  Only applicable for HSL."
            ::= { mtpLinkEntry 51 } 
            
    mtpLinkAtmWrongVcCounter  OBJECT-TYPE          
        SYNTAX Counter
        ACCESS read-only
        STATUS mandatory
        DESCRIPTION
            "Counter specifying the number of cells dropped due to a VC where no 
            application is listening to.  Only applicable for HSL."
            ::= { mtpLinkEntry 52 } 
            
    mtpLinkAtmBadHecCounter OBJECT-TYPE
        SYNTAX Counter
        ACCESS read-only
        STATUS mandatory
        DESCRIPTION
            "Counter specifying the number of cells dropped due to a wrong 
            Header Error Control.  Only applicable for HSL."
            ::= { mtpLinkEntry 53 } 
            
    mtpLinkAtmMiscErrorCounter OBJECT-TYPE
        SYNTAX Counter
        ACCESS read-only
        STATUS mandatory
        DESCRIPTION
            "Counter specifying the number of cells droped due other discard 
            reasons.  Only applicable for HSL."
            ::= { mtpLinkEntry 54 } 
            
    mtpLinkAtmLossOfCellDelineationCounter OBJECT-TYPE
        SYNTAX Counter
        ACCESS read-only
        STATUS mandatory
        DESCRIPTION
            "Counter specifying the number of times Loss of Cell Delineation has
            occurred. Only applicable for HSL."
            ::= { mtpLinkEntry 55 } 
            
    mtpLinkAtmHecAnomoliesCounter OBJECT-TYPE           
        SYNTAX Counter
        ACCESS read-only
        STATUS mandatory
        DESCRIPTION
            "Counter specifying the number times HEC anomalies has occurred. 
            Only applicable for HSL."
            ::= { mtpLinkEntry 56 } 
            
    mtpLinkAtmTxFifoFullCounter OBJECT-TYPE
        SYNTAX Counter
        ACCESS read-only
        STATUS mandatory
        DESCRIPTION
            "Counter specifying the number times the Transmit FIFO full error 
            has occured. Only applicable for HSL."
     ::= { mtpLinkEntry 57 }
     
    mtpLinkAal5RecvPduCounter OBJECT-TYPE
        SYNTAX Counter
        ACCESS read-only
        STATUS mandatory
        DESCRIPTION
            "Counter specifing the number of AAL5 PDU's received. Only 
            applicable for HSL."
     ::= { mtpLinkEntry 71 }
     
     mtpLinkAal5SentPduCounter OBJECT-TYPE      
        SYNTAX Counter
        ACCESS read-only
        STATUS mandatory
        DESCRIPTION
             "Counter specifing the number of AAL5 PDU's sent. Only applicable 
             for HSL."
        ::= { mtpLinkEntry 72 }
             
    mtpLinkAal5LengthErrorCounter OBJECT-TYPE
        SYNTAX Counter
        ACCESS read-only
        STATUS mandatory
        DESCRIPTION
              "Counter specifing the number of AAL5 PDU's dropped due to an 
              invalid length. Only applicable for HSL."
        ::= { mtpLinkEntry 81 }
        
    mtpLinkAalRxCongestionCounter OBJECT-TYPE
        SYNTAX Counter
        ACCESS read-only
        STATUS mandatory
        DESCRIPTION
              "Counter specifing the number of received AAL congestion messages. 
              Only applicable for HSL."
        ::= { mtpLinkEntry 82 }
        
    mtpLinkAal5CrcErrorCounter OBJECT-TYPE
        SYNTAX Counter
        ACCESS read-only
        STATUS mandatory
        DESCRIPTION
              "Counter specifing the number AAL5 PDU's dropped due to invalid 
              CRC. Only applicable for HSL."
        ::= { mtpLinkEntry 83 }
        
    mtpLinkSscopRecvPduCounter OBJECT-TYPE
        SYNTAX  Counter
        ACCESS  read-only
        STATUS  mandatory
        DESCRIPTION
            "Counter specifying the number of SSCOP PDU's received. Only 
            applicable for HSL."
        ::= { mtpLinkEntry 101 }

    mtpLinkSscopSentPduCounter OBJECT-TYPE
        SYNTAX  Counter
        ACCESS  read-only
        STATUS  mandatory
        DESCRIPTION
            "Counter specifying the number of SSCOP PDU's sent. Only applicable 
            for HSL."
        ::= { mtpLinkEntry 102 }

    mtpLinkSscopRecvPduBytesCounter OBJECT-TYPE
        SYNTAX  Counter
        ACCESS  read-only
        STATUS  mandatory
        DESCRIPTION
            "Counter specifying the number of SSCOP PDU bytes received. Only 
            applicable for HSL."
        ::= { mtpLinkEntry 103 }

    mtpLinkSscopSentPduBytesCounter OBJECT-TYPE
        SYNTAX  Counter
        ACCESS  read-only
        STATUS  mandatory
        DESCRIPTION
            "Counter specifying the number of SSCOP PDU bytes sent. Only  
            applicable for HSL."
        ::= { mtpLinkEntry 104 }
        
    mtpLinkSscopRecvBgnPduCounter OBJECT-TYPE
        SYNTAX  Counter
        ACCESS  read-only
        STATUS  mandatory
        DESCRIPTION
            "Counter specifying the number of SSCOP BGN PDU's received. Only 
            applicable for HSL."
        ::= { mtpLinkEntry 111 }

    mtpLinkSscopSentBgnPduCounter OBJECT-TYPE
        SYNTAX  Counter
        ACCESS  read-only
        STATUS  mandatory
        DESCRIPTION
            "Counter specifying the number of SSCOP BGN PDU's sent. Only 
            applicable for HSL."
        ::= { mtpLinkEntry 112 }

    mtpLinkSscopRecvBgakPduCounter OBJECT-TYPE
        SYNTAX  Counter
        ACCESS  read-only
        STATUS  mandatory
        DESCRIPTION
            "Counter specifying the number of SSCOP BGAK PDU's received. Only 
            applicable for HSL."
        ::= { mtpLinkEntry 113 }

    mtpLinkSscopSentBgakPduCounter OBJECT-TYPE
        SYNTAX  Counter
        ACCESS  read-only
        STATUS  mandatory
        DESCRIPTION
            "Counter specifying the number of SSCOP BGAK PDU's sent. Only 
            applicable for HSL."
        ::= { mtpLinkEntry 114 }

    mtpLinkSscopRecvBgrejPduCounter OBJECT-TYPE
        SYNTAX  Counter
        ACCESS  read-only
        STATUS  mandatory
        DESCRIPTION
            "Counter specifying the number of SSCOP BGREJ PDU's received. Only 
            applicable for HSL."
        ::= { mtpLinkEntry 115 }

    mtpLinkSscopSentBgrejPduCounter OBJECT-TYPE
        SYNTAX  Counter
        ACCESS  read-only
        STATUS  mandatory
        DESCRIPTION
            "Counter specifying the number of SSCOP BGREJ PDU's sent. Only 
            applicable for HSL."
        ::= { mtpLinkEntry 116 }

    mtpLinkSscopRecvRsPduCounter OBJECT-TYPE
        SYNTAX  Counter
        ACCESS  read-only
        STATUS  mandatory
        DESCRIPTION
            "Counter specifying the number of SSCOP RS PDU's received. Only 
            applicable for HSL."
        ::= { mtpLinkEntry 117 }

    mtpLinkSscopSentRsPduCounter OBJECT-TYPE
        SYNTAX  Counter
        ACCESS  read-only
        STATUS  mandatory
        DESCRIPTION
            "Counter specifying the number of SSCOP RS PDU's sent. Only 
            applicable for HSL."
        ::= { mtpLinkEntry 118 }

    mtpLinkSscopRecvRsakPduCounter OBJECT-TYPE
        SYNTAX  Counter
        ACCESS  read-only
        STATUS  mandatory
        DESCRIPTION
            "Counter specifying the number of SSCOP RSAK PDU's received. Only 
            applicable for HSL."
        ::= { mtpLinkEntry 119 }

    mtpLinkSscopSentRsakPduCounter OBJECT-TYPE
        SYNTAX  Counter
        ACCESS  read-only
        STATUS  mandatory
        DESCRIPTION
            "Counter specifying the number of SSCOP RSAK PDU's sent. Only 
            applicable for HSL."
        ::= { mtpLinkEntry 120 }

    mtpLinkSscopRecvEndPduCounter OBJECT-TYPE
        SYNTAX  Counter
        ACCESS  read-only
        STATUS  mandatory
        DESCRIPTION
            "Counter specifying the number of SSCOP END PDU's received. Only 
            applicable for HSL."
        ::= { mtpLinkEntry 121 }

    mtpLinkSscopSentEndPduCounter OBJECT-TYPE
        SYNTAX  Counter
        ACCESS  read-only
        STATUS  mandatory
        DESCRIPTION
            "Counter specifying the number of SSCOP END PDU's sent. Only 
            applicable for HSL."
        ::= { mtpLinkEntry 122 }

    mtpLinkSscopRecvEndakPduCounter OBJECT-TYPE
        SYNTAX  Counter
        ACCESS  read-only
        STATUS  mandatory
        DESCRIPTION
            "Counter specifying the number of SSCOP END PDU's received. Only 
            applicable for HSL."
        ::= { mtpLinkEntry 123 }

    mtpLinkSscopSentEndakPduCounter OBJECT-TYPE
        SYNTAX  Counter
        ACCESS  read-only
        STATUS  mandatory
        DESCRIPTION
            "Counter specifying the number of SSCOP END PDU's sent. Only 
            applicable for HSL."
        ::= { mtpLinkEntry 124 }

    mtpLinkSscopRecvErPduCounter OBJECT-TYPE
        SYNTAX  Counter
        ACCESS  read-only
        STATUS  mandatory
        DESCRIPTION
            "Counter specifying the number of SSCOP ER PDU's received. Only 
            applicable for HSL."
        ::= { mtpLinkEntry 125 }

    mtpLinkSscopSentErPduCounter OBJECT-TYPE
        SYNTAX  Counter
        ACCESS  read-only
        STATUS  mandatory
        DESCRIPTION
            "Counter specifying the number of SSCOP ER PDU's sent. Only 
            applicable for HSL."
        ::= { mtpLinkEntry 126 }

    mtpLinkSscopRecvErakPduCounter OBJECT-TYPE
        SYNTAX  Counter
        ACCESS  read-only
        STATUS  mandatory
        DESCRIPTION
            "Counter specifying the number of SSCOP ERAK PDU's received. Only 
            applicable for HSL."
        ::= { mtpLinkEntry 127 }

    mtpLinkSscopSentErakPduCounter OBJECT-TYPE
        SYNTAX  Counter
        ACCESS  read-only
        STATUS  mandatory
        DESCRIPTION
            "Counter specifying the number of SSCOP ERAK PDU's sent. Only 
            applicable for HSL."
        ::= { mtpLinkEntry 128 }

    mtpLinkSscopRecvPollPduCounter OBJECT-TYPE
        SYNTAX  Counter
        ACCESS  read-only
        STATUS  mandatory
        DESCRIPTION
            "Counter specifying the number of SSCOP POLL PDU's received. Only 
            applicable for HSL."
        ::= { mtpLinkEntry 129 }

    mtpLinkSscopSentPollPduCounter OBJECT-TYPE
        SYNTAX  Counter
        ACCESS  read-only
        STATUS  mandatory
        DESCRIPTION
            "Counter specifying the number of SSCOP POLL PDU's sent. Only 
            applicable for HSL."
        ::= { mtpLinkEntry 130 }

    mtpLinkSscopRecvStatPduCounter OBJECT-TYPE
        SYNTAX  Counter
        ACCESS  read-only
        STATUS  mandatory
        DESCRIPTION
            "Counter specifying the number of SSCOP STAT PDU's received. Only 
            applicable for HSL."
        ::= { mtpLinkEntry 131 }

    mtpLinkSscopSentStatPduCounter OBJECT-TYPE
        SYNTAX  Counter
        ACCESS  read-only
        STATUS  mandatory
        DESCRIPTION
            "Counter specifying the number of SSCOP STAT PDU's sent. Only 
            applicable for HSL."
        ::= { mtpLinkEntry 132 }

    mtpLinkSscopRecvUstatPduCounter OBJECT-TYPE
        SYNTAX  Counter
        ACCESS  read-only
        STATUS  mandatory
        DESCRIPTION
            "Counter specifying the number of SSCOP USTAT PDU's received. Only 
            applicable for HSL."
        ::= { mtpLinkEntry 133 }

    mtpLinkSscopSentUstatPduCounter OBJECT-TYPE
        SYNTAX  Counter
        ACCESS  read-only
        STATUS  mandatory
        DESCRIPTION
            "Counter specifying the number of SSCOP USTAT PDU's sent. Only 
            applicable for HSL."
        ::= { mtpLinkEntry 134 }

    mtpLinkSscopRecvUdPduCounter OBJECT-TYPE
        SYNTAX  Counter
        ACCESS  read-only
        STATUS  mandatory
        DESCRIPTION
            "Counter specifying the number of SSCOP UD PDU's received. Only 
            applicable for HSL."
        ::= { mtpLinkEntry 135 }

    mtpLinkSscopSentUdPduCounter OBJECT-TYPE
        SYNTAX  Counter
        ACCESS  read-only
        STATUS  mandatory
        DESCRIPTION
            "Counter specifying the number of SSCOP UD PDU's sent. Only 
            applicable for HSL."
        ::= { mtpLinkEntry 136 }

    mtpLinkSscopRecvMdPduCounter OBJECT-TYPE
        SYNTAX  Counter
        ACCESS  read-only
        STATUS  mandatory
        DESCRIPTION
            "Counter specifying the number of SSCOP MD PDU's received. Only 
            applicable for HSL."
        ::= { mtpLinkEntry 137 }

    mtpLinkSscopSentMdPduCounter OBJECT-TYPE
        SYNTAX  Counter
        ACCESS  read-only
        STATUS  mandatory
        DESCRIPTION
            "Counter specifying the number of SSCOP MD PDU's sent. Only 
            applicable for HSL."
        ::= { mtpLinkEntry 138 }

    mtpLinkSscopRecvSdPduCounter OBJECT-TYPE
        SYNTAX  Counter
        ACCESS  read-only
        STATUS  mandatory
        DESCRIPTION
            "Counter specifying the number of SSCOP SD PDU's received. Only 
            applicable for HSL."
        ::= { mtpLinkEntry 139 }

    mtpLinkSscopSentSdPduCounter OBJECT-TYPE
        SYNTAX  Counter
        ACCESS  read-only
        STATUS  mandatory
        DESCRIPTION
            "Counter specifying the number of SSCOP SD PDU's sent. Only 
            applicable for HSL."
        ::= { mtpLinkEntry 140 }

    mtpLinkSscopLastUpTime OBJECT-TYPE
        SYNTAX  DateTime
        ACCESS  read-only
        STATUS  mandatory
        DESCRIPTION
            "Time of last down-to-up transition, expressed in seconds since 1 
            Jan 1970. Only applicable for HSL."
        ::= { mtpLinkEntry 141 }

    mtpLinkSscopLastDownTime OBJECT-TYPE
        SYNTAX  DateTime
        ACCESS  read-only
        STATUS  mandatory
        DESCRIPTION
            "Time of last up-to-down transition, expressed in seconds since 1 
            Jan 1970. Only applicable for HSL."
        ::= { mtpLinkEntry 142 }

    mtpLinkSscopOperationalState OBJECT-TYPE
        SYNTAX  SscopOperationalState
        ACCESS  read-only
        STATUS  mandatory
        DESCRIPTION
            "Current SSCOP state. Only applicable for HSL."
        ::= { mtpLinkEntry 143 }

    mtpLinkSscopErrorATillMCounter OBJECT-TYPE
        SYNTAX  Counter
        ACCESS  read-only
        STATUS  mandatory
        DESCRIPTION
            "Cumulative counter specifying the number of times that error 'A' 
            till error 'M (i.e. unexpected PDU received) at SSCOP layer. Only 
            applicable for HSL."
        ::= { mtpLinkEntry 151 }

    mtpLinkSscopErrorOCounter OBJECT-TYPE
        SYNTAX  Counter
        ACCESS  read-only
        STATUS  mandatory
        DESCRIPTION
            "Counter specifying the number of times that error 'O' (i.e. 
            unsuccessful retransmission due to VT(CC) >= MaxCC) occurred at 
            SSCOP layer. Only applicable for HSL."
        ::= { mtpLinkEntry 152 }

    mtpLinkSscopErrorPCounter OBJECT-TYPE
        SYNTAX  Counter
        ACCESS  read-only
        STATUS  mandatory
        DESCRIPTION
            "Counter specifying the number of times that error 'P' (i.e. 
            unsuccessful retransmission due to Timer_NO_RESPONSE expiry) 
            occurred at SSCOP layer. Only applicable for HSL."
        ::= { mtpLinkEntry 153 }

    mtpLinkSscopErrorQCounter OBJECT-TYPE
        SYNTAX  Counter
        ACCESS  read-only
        STATUS  mandatory
        DESCRIPTION
            "Counter specifying the number of times that error 'Q' (i.e. 
            other list elements error type due to SD or POLL, N(S) error) 
            occurred at SSCOP layer. Only applicable for HSL."
        ::= { mtpLinkEntry 154 }

    mtpLinkSscopErrorRCounter OBJECT-TYPE
        SYNTAX  Counter
        ACCESS  read-only
        STATUS  mandatory
        DESCRIPTION
            "Counter specifying the number of times that error 'R' (i.e. 
            other list elements error type due to STAT N(PS) error) occurred 
            at SSCOP layer. Only applicable for HSL."
        ::= { mtpLinkEntry 155 }

    mtpLinkSscopErrorSCounter OBJECT-TYPE
        SYNTAX  Counter
        ACCESS  read-only
        STATUS  mandatory
        DESCRIPTION
            "Counter specifying the number of times that error 'S' (i.e. 
            other list elements error type due to STAT N(R) error or list 
            elements error) occurred at SSCOP layer. 
            Only applicable for HSL."
        ::= { mtpLinkEntry 156 }

    mtpLinkSscopErrorTCounter OBJECT-TYPE
        SYNTAX  Counter
        ACCESS  read-only
        STATUS  mandatory
        DESCRIPTION
            "Counter specifying the number of times that error 'T' (i.e. 
            other list elements error type due to USTAT N(R) or list elements 
            error) occurred at SSCOP layer. Only applicable for HSL."
        ::= { mtpLinkEntry 157 }

    mtpLinkSscopErrorUCounter OBJECT-TYPE
        SYNTAX  Counter
        ACCESS  read-only
        STATUS  mandatory
        DESCRIPTION
            "Counter specifying the number of times that error 'U' (i.e. 
            other list elements error type due to PDU length violation) occurred 
            at SSCOP layer. Only applicable for HSL."
        ::= { mtpLinkEntry 158 }

    mtpLinkSscopErrorVCounter OBJECT-TYPE
        SYNTAX  Counter
        ACCESS  read-only
        STATUS  mandatory
        DESCRIPTION
            "Counter specifying the number of times that error 'V' (i.e. 
            SD loss) occurred at SSCOP layer. Only applicable for HSL."
        ::= { mtpLinkEntry 159 }

    mtpLinkSscopErrorWCounter OBJECT-TYPE
        SYNTAX  Counter
        ACCESS  read-only
        STATUS  mandatory
        DESCRIPTION
            "Counter specifying the number of times that error 'W' (i.e. 
            credit condition due to lack of credit) occurred at SSCOP layer. 
            Only applicable for HSL."
        ::= { mtpLinkEntry 160 }

    mtpLinkSscopErrorXCounter OBJECT-TYPE
        SYNTAX  Counter
        ACCESS  read-only
        STATUS  mandatory
        DESCRIPTION
            "Counter specifying the number of times that error 'X' (i.e. 
            credit condition due to credit obtained) occurred at SSCOP layer. 
            Only applicable for HSL."
        ::= { mtpLinkEntry 161 }
        
    mtpLinkSscopToBeSentToPeerCounter OBJECT-TYPE
        SYNTAX  Gauge
        ACCESS  read-only
        STATUS  mandatory
        DESCRIPTION
            "Counter specifying the number of messages in the transmit queue 
            of the SSCOP layer that have not yet been sent to the peer. Only 
            applicable for HSL."
        ::= { mtpLinkEntry 171 }
        
    mtpLinkSscopToBeAckdByPeerCounter OBJECT-TYPE
        SYNTAX  Gauge
        ACCESS  read-only
        STATUS  mandatory
        DESCRIPTION
            "Counter specifying the number of messages in the transmit queue 
            of the SSCOP layer that have been sent to the peer, but have not yet
            been acknowledged by peer. Only applicable for HSL."
        ::= { mtpLinkEntry 172 }

    mtpLinkSscopVtS OBJECT-TYPE
        SYNTAX  Gauge
        ACCESS  read-only
        STATUS  mandatory
        DESCRIPTION
            "Value of the 'send state' variable, VT(S), of the SCCOP layer. This 
            variable contains the sequence number of the next SD PDU to be 
            transmitted for the first time (i.e. excluding retransmissions). 
            Only applicable for HSL."
        ::= { mtpLinkEntry 173 }

    mtpLinkSscopVtA OBJECT-TYPE
        SYNTAX  Gauge
        ACCESS  read-only
        STATUS  mandatory
        DESCRIPTION
            "Value of the 'acknowledge state' variable, VT(A), of the SCCOP 
            layer. This variable contains the sequence number of the next 
            in-sequence SD PDU expected to be acknowledged, which forms the
            lower edge of the window of acceptable acknowledgements. Only 
            applicable for HSL."
        ::= { mtpLinkEntry 174 }

    mtpLinkSscopVtMr OBJECT-TYPE
        SYNTAX  Gauge
        ACCESS  read-only
        STATUS  mandatory
        DESCRIPTION
            "Value of the 'maximum acceptable receive state' variable, VT(MR), 
            of the SCCOP layer. This variable contains the sequence number of 
            the first SD PDU not allowed by the receiver. Only applicable for 
            HSL."
        ::= { mtpLinkEntry 175 }

    mtpLinkSscfRecvPduCounter OBJECT-TYPE
        SYNTAX  Counter
        ACCESS  read-only
        STATUS  mandatory
        DESCRIPTION
            "Counter specifying the number of SSCF PDU's received. Only 
            applicable for HSL."
        ::= { mtpLinkEntry 201 }

    mtpLinkSscfSentPduCounter OBJECT-TYPE
        SYNTAX  Counter
        ACCESS  read-only
        STATUS  mandatory
        DESCRIPTION
            "Counter specifying the number of SSCF PDU's sent. Only applicable 
            for HSL."
        ::= { mtpLinkEntry 202 }

    mtpLinkSscfReSentPduCounter OBJECT-TYPE
        SYNTAX  Counter
        ACCESS  read-only
        STATUS  mandatory
        DESCRIPTION
            "Counter specifying the number of SSCF PDU's resent. Only 
            applicable for HSL."
        ::= { mtpLinkEntry 203 }

    mtpLinkSscfRecvPduBytesCounter OBJECT-TYPE
        SYNTAX  Counter
        ACCESS  read-only
        STATUS  mandatory
        DESCRIPTION
            "Counter specifying the number of SSCF PDU bytes received. Only 
            applicable for HSL."
        ::= { mtpLinkEntry 204 }

    mtpLinkSscfSentPduBytesCounter OBJECT-TYPE
        SYNTAX  Counter
        ACCESS  read-only
        STATUS  mandatory
        DESCRIPTION
            "Counter specifying the number of SSCF PDU bytes sent. Only  
            applicable for HSL."
        ::= { mtpLinkEntry 205 }

    mtpLinkSscfReSentPduBytesCounter OBJECT-TYPE
        SYNTAX  Counter
        ACCESS  read-only
        STATUS  mandatory
        DESCRIPTION
            "Counter specifying the number of SSCF PDU bytes resent. Only 
            applicable for HSL."
        ::= { mtpLinkEntry 206 }

    mtpLinkSscfAlignmentFailureCounter OBJECT-TYPE
        SYNTAX  Counter
        ACCESS  read-only
        STATUS  mandatory
        DESCRIPTION
            "Counter specifying the number of failures to align a link. 
            Only applicable for HSL."
        ::= { mtpLinkEntry 211 }

    mtpLinkSscfLastInServiceTime OBJECT-TYPE
        SYNTAX  DateTime
        ACCESS  read-only
        STATUS  mandatory
        DESCRIPTION
            "Time of last transition to 'in service', expressed in seconds since
            1 Jan 1970. Only applicable for HSL."
        ::= { mtpLinkEntry 212 }

    mtpLinkSscfNoCreditCounter OBJECT-TYPE
        SYNTAX  Counter
        ACCESS  read-only
        STATUS  mandatory
        DESCRIPTION
            "Counter specifying the number of times that no credit was available. 
            Only applicable for HSL."
        ::= { mtpLinkEntry 213 }

    mtpLinkSscfTotalNoCreditDuration OBJECT-TYPE
        SYNTAX  Counter
        ACCESS  read-only
        STATUS  mandatory
        DESCRIPTION
            "Cumulative time expressed in seconds that no credit was available. 
            Only applicable for HSL."
        ::= { mtpLinkEntry 214 }
        
    mtpLinkSscfOperationalState OBJECT-TYPE
        SYNTAX  SscfOperationalState 
        ACCESS  read-only
        STATUS  mandatory
        DESCRIPTION
            "Current SSCF state. Only applicable for HSL."
        ::= { mtpLinkEntry 215 }

    mtpLinkSscfLocalProcOutage OBJECT-TYPE
        SYNTAX  Boolean
        ACCESS  read-only
        STATUS  mandatory
        DESCRIPTION
            "Indicates whether local processor has an outage. Only applicable 
            for HSL."
        ::= { mtpLinkEntry 221 }

    mtpLinkSscfLastLocalProcOutageTime OBJECT-TYPE
        SYNTAX  DateTime
        ACCESS  read-only
        STATUS  mandatory
        DESCRIPTION
            "Indicates start time of local processor outage. Only applicable for 
            HSL."
        ::= { mtpLinkEntry 222 }

    mtpLinkSscfTotalLocalProcOutageDuration OBJECT-TYPE
        SYNTAX  Counter 
        ACCESS  read-only
        STATUS  mandatory
        DESCRIPTION
            "Cumulative time that local processor experienced an outage. Only 
            applicable for HSL."
        ::= { mtpLinkEntry 223 }

    mtpLinkSscfRemoteProcOutage OBJECT-TYPE
        SYNTAX  Boolean
        ACCESS  read-only
        STATUS  mandatory
        DESCRIPTION
            "Indicates whether remote processor has an outage. Only applicable 
            for HSL."
        ::= { mtpLinkEntry 226 }

    mtpLinkSscfLastRemoteProcOutageTime OBJECT-TYPE
        SYNTAX  DateTime
        ACCESS  read-only
        STATUS  mandatory
        DESCRIPTION
            "Indicates start time of remote processor outage. Only applicable for 
            HSL."
        ::= { mtpLinkEntry 227 }

    mtpLinkSscfTotalRemoteProcOutageDuration OBJECT-TYPE
        SYNTAX  Counter 
        ACCESS  read-only
        STATUS  mandatory
        DESCRIPTION
            "Cumulative time that remote processor experienced an outage. Only 
            applicable for HSL."
        ::= { mtpLinkEntry 228 }

    mtpLinkMtpRecvMgmtCounter OBJECT-TYPE
        SYNTAX Counter
        ACCESS read-only
        STATUS mandatory
        DESCRIPTION
            "Counter specifying the number of MTP Management MSU's received."
        ::= { mtpLinkEntry 401 }
      
    mtpLinkMtpSentMgmtCounter OBJECT-TYPE
        SYNTAX Counter
        ACCESS read-only
        STATUS mandatory
        DESCRIPTION
            "Counter specifying the number of MTP Management MSU's sent."
        ::= { mtpLinkEntry 402 }
      
    mtpLinkMtpRecvTestCounter OBJECT-TYPE
        SYNTAX Counter
        ACCESS read-only
        STATUS mandatory
        DESCRIPTION
            "Counter specifying the number of MTP Testing & Maintenance MSU's 
            received."
        ::= { mtpLinkEntry 403 }
      
    mtpLinkMtpSentTestCounter OBJECT-TYPE
        SYNTAX Counter
        ACCESS read-only
        STATUS mandatory
        DESCRIPTION
            "Counter specifying the number of MTP Testing & Maintenance MSU's 
            sent."
        ::= { mtpLinkEntry 404 }
      
    mtpLinkMtpRecvSccpCounter OBJECT-TYPE
        SYNTAX Counter
        ACCESS read-only
        STATUS mandatory
        DESCRIPTION
            "Counter specifying the number of MTP SCCP MSU's received."
        ::= { mtpLinkEntry 405 }
      
    mtpLinkMtpSentSccpCounter OBJECT-TYPE
        SYNTAX Counter
        ACCESS read-only
        STATUS mandatory
        DESCRIPTION
            "Counter specifying the number of MTP SCCP MSU's sent."
        ::= { mtpLinkEntry 406 }

    mtpLinkInServiceStartTime OBJECT-TYPE 
        SYNTAX TimeTicks
        ACCESS read-only
        STATUS mandatory
        DESCRIPTION
            "Counter specifying the number of 10ms ticks since the board level 
            code was started when the MTP2 link came into the InService State."
        ::= { mtpLinkEntry 421 }
            
    mtpLinkFailureAllReason OBJECT-TYPE
        SYNTAX Counter
        ACCESS read-only
        STATUS mandatory
        DESCRIPTION
            "Counter specifying the number of times the MTP2 link entered the 
            Out of Service state for all reasons."
        ::= { mtpLinkEntry 422 }
            
    mtpLinkFailureAbnormalFibBsnNum OBJECT-TYPE
        SYNTAX Counter
        ACCESS read-only
        STATUS mandatory
        DESCRIPTION
            "Counter specifying the number of times the MTP2 link entered the 
            Out of Service state due to receiving 2 out of 3 frames with an 
            erroneous FIB or BSNR."
        ::= { mtpLinkEntry 423 }
            
    mtpLinkT7Expiry OBJECT-TYPE
        SYNTAX Counter
        ACCESS read-only
        STATUS mandatory
        DESCRIPTION
            "Counter specifying the number of times the MTP2 link entered the 
            Out of Service state due to expiry of the T7 (excessive delay of 
            acknowledgement) timer"
        ::= { mtpLinkEntry 424 }
            
    mtpLinkCongTooLong OBJECT-TYPE
        SYNTAX Counter
        ACCESS read-only
        STATUS mandatory
        DESCRIPTION
            "Counter specifying the number of times the MTP2 link entered the 
            Out of Service state due to expiry of the T6 timer."
        ::= { mtpLinkEntry 425 }
            
    mtpLinkFailureSuerm OBJECT-TYPE
        SYNTAX Counter
        ACCESS read-only
        STATUS mandatory
        DESCRIPTION
            "Counter specifying the number of times the MTP2 link entered the 
            Out of Service state due to SUERM detecting an high error rate."
        ::= { mtpLinkEntry 426 }
            
    mtpLinkFailureT2T3Expiry OBJECT-TYPE
        SYNTAX Counter
        ACCESS read-only
        STATUS mandatory
        DESCRIPTION
            "Counter specifying the number of times the MTP2 link entered the 
            Out of Service state due to timer T2 (Timer 'Not Aligned') or T3
            (Timer 'Aligned') expiring."
        ::= { mtpLinkEntry 427 }
            
    mtpLinkProvingAligningFailure OBJECT-TYPE
        SYNTAX Counter
        ACCESS read-only
        STATUS mandatory
        DESCRIPTION
            "Counter specifying the number of times the MTP2 link entered the 
            Out of Service state due to AERM detecting a high error rate."
        ::= { mtpLinkEntry 428 }
            
    mtpLinkNumSuError OBJECT-TYPE
        SYNTAX Counter
        ACCESS read-only
        STATUS mandatory
        DESCRIPTION
            "Counter specifying the number of MSU frames received in error."
        ::= { mtpLinkEntry 429 }
            
    mtpLinkNumNack OBJECT-TYPE
        SYNTAX Counter
        ACCESS read-only
        STATUS mandatory
        DESCRIPTION
            "Counter specifying the number of negative acknowledgements 
            received."
        ::= { mtpLinkEntry 430 }
            
    mtpLinkNumMsuRtx OBJECT-TYPE
        SYNTAX Counter
        ACCESS read-only
        STATUS mandatory
        DESCRIPTION
            "Counter specifying the number of MSU frames retransmitted."
        ::= { mtpLinkEntry 431 }
            
    mtpLinkNumMsuOctetRtx OBJECT-TYPE
        SYNTAX Counter
        ACCESS read-only
        STATUS mandatory
        DESCRIPTION
            "Counter specifying the number of MSU octets retransmitted. The
            count does not include the MTP2 header, flags or CRC bytes."
        ::= { mtpLinkEntry 432 }

    mtpLinkNumMSuOctetTx OBJECT-TYPE
        SYNTAX Counter
        ACCESS read-only
        STATUS mandatory
        DESCRIPTION
            "Counter specifying the number of MSU octets transmitted. The
            count does not include the MTP2 header, flags or CRC bytes."
        ::= { mtpLinkEntry 433 }

    mtpLinkNumMsuOctetRx OBJECT-TYPE
        SYNTAX Counter
        ACCESS read-only
        STATUS mandatory
        DESCRIPTION
            "Counter specifying the number of MSU octets received. The
            count does not include the MTP2 header, flags or CRC bytes."
        ::= { mtpLinkEntry 434 }

    mtpLinkNumMsuTx  OBJECT-TYPE 
        SYNTAX Counter
        ACCESS read-only
        STATUS mandatory
        DESCRIPTION
            "Counter specifying the number of MSUs transmitted."
        ::= { mtpLinkEntry 435 }

    mtpLinkNumMsuRx OBJECT-TYPE
        SYNTAX Counter
        ACCESS read-only
        STATUS mandatory
        DESCRIPTION
            "Counter specifying the number of MSUs received."
        ::= { mtpLinkEntry 436 }

    mtpLinkNumSibTx OBJECT-TYPE
        SYNTAX Counter
        ACCESS read-only
        STATUS mandatory
        DESCRIPTION
            "Counter specifying the number of SIB (Local Processor Busy) frames
            transmitted."
        ::= { mtpLinkEntry 437 }

    mtpLinkNumSibRx OBJECT-TYPE
        SYNTAX Counter
        ACCESS read-only
        STATUS mandatory
        DESCRIPTION
            "Counter specifying the number of SIB (Local Processor Busy) frames
            received."
        ::= { mtpLinkEntry 438 }

    -- the MTP destination group

    mtpDestinationTable OBJECT-TYPE
        SYNTAX  SEQUENCE OF MtpDestinationEntry
        ACCESS  not-accessible
        STATUS  mandatory
        DESCRIPTION
            "Table containing info about MTP destinations."
        ::= { mtp 8 }

    mtpDestinationEntry OBJECT-TYPE
        SYNTAX  MtpDestinationEntry
        ACCESS  not-accessible
        STATUS  mandatory
        DESCRIPTION
            "Entry of table containing info about MTP destinations."
        INDEX   { mtpDestinationIndex }
        ::= { mtpDestinationTable 1 }

    MtpDestinationEntry ::=
        SEQUENCE {
            mtpDestinationIndex                   Gauge(1..500),
            mtpDestinationAdminState              AdminState,            
            mtpDestinationOperationalState        DestinationOperationalState,
            mtpDestinationName                    NameString,
            mtpDestinationPointCode               PointCode,
            mtpDestinationThroughput              Throughput,
            mtpDestinationMonitor                 Boolean,
            mtpDestinationPointCodeString         PointCodeString,
            mtpDestinationMtpRecvMgmtCounter      Counter,
            mtpDestinationMtpSentMgmtCounter      Counter,
            mtpDestinationMtpRecvTestCounter      Counter,
            mtpDestinationMtpSentTestCounter      Counter,
            mtpDestinationMtpRecvSccpCounter      Counter,
            mtpDestinationMtpSentSccpCounter      Counter
        }     

    mtpDestinationIndex OBJECT-TYPE
        SYNTAX  Gauge(1..100)
        ACCESS  not-accessible
        STATUS  mandatory
        DESCRIPTION
            "Index of entry in table containing info about MTP destinations."
        ::= { mtpDestinationEntry 1 }

    mtpDestinationAdminState OBJECT-TYPE
        SYNTAX  AdminState
        ACCESS  read-write
        STATUS  mandatory
        DESCRIPTION
            "Administrative state of entry in table containing info about the 
             MTP destinations. Activating a destination, deactivating a 
             destination or removing an entry from the table (and implicitly 
             deactivating the associated destination) is accomplished by 
             writing the administrative state."
        ::= { mtpDestinationEntry 2 }

    mtpDestinationOperationalState OBJECT-TYPE
        SYNTAX  DestinationOperationalState
        ACCESS  read-only
        STATUS  mandatory
        DESCRIPTION
            "Operational state of destination."
        ::= { mtpDestinationEntry 3 }

    mtpDestinationName OBJECT-TYPE
        SYNTAX  NameString
        ACCESS  read-write
        STATUS  mandatory
        DESCRIPTION
            "Name of destination. Only modify-able if the entry's administrative 
             state is 'inactive'."
        ::= { mtpDestinationEntry 4 }

    mtpDestinationPointCode OBJECT-TYPE
        SYNTAX  PointCode
        ACCESS  read-write
        STATUS  mandatory
        DESCRIPTION
            "Point code of destination and formatted as commonly done 
             in ITU-T.
             Only modify-able if the entry's administrative state is 
             'inactive'.
             Note that this point code can be changed/viewed by this object as 
             well as the mtpDestinationPointCodeString object."
        ::= { mtpDestinationEntry 5 }

    mtpDestinationThroughput OBJECT-TYPE
        SYNTAX  Throughput
        ACCESS  read-write
        STATUS  mandatory
        DESCRIPTION
            "Maximum throughput in terms of MSU's per second for the
             destination (excluding the MSU's for MTP management and 
             MTP testing & maintenance)."
        ::= { mtpDestinationEntry 6 }

    mtpDestinationMonitor OBJECT-TYPE
        SYNTAX  Boolean
        ACCESS  read-write
        STATUS  mandatory
        DESCRIPTION
            "Indicator that determines whether the destination is being 
            monitored. In case a destination is being monitored, the following
            applies:
            (1) Only applicable for adjacents;
            (2) TextPass processes each MSU originated from the destination, 
                regardless whether the MSU is destined for TextPass or not;
            (3) From the perspective of the destination, TextPass acts as an 
                STP (at MTP3 level, not on SCCP level).
            By default, monitoring is disabled."
        ::= { mtpDestinationEntry 7 }
        
    mtpDestinationPointCodeString OBJECT-TYPE
        SYNTAX  PointCodeString
        ACCESS  read-write
        STATUS  mandatory
        DESCRIPTION
            "Point code of destination and formatted as commonly done 
             in ANSI.
             Only modify-able if the entry's administrative state is 
             'inactive'.
             Note that this point code can be changed/viewed by this object as 
             well as the mtpDestinationPointCode object."
        ::= { mtpDestinationEntry 8 }

    mtpDestinationMtpRecvMgmtCounter OBJECT-TYPE
        SYNTAX Counter
        ACCESS read-only
        STATUS mandatory
        DESCRIPTION
            "Counter specifying the number of MTP Management MSU's received."
        ::= { mtpDestinationEntry 11 }
      
    mtpDestinationMtpSentMgmtCounter OBJECT-TYPE
        SYNTAX Counter
        ACCESS read-only
        STATUS mandatory
        DESCRIPTION
            "Counter specifying the number of MTP Management MSU's sent."
        ::= { mtpDestinationEntry 12 }
      
    mtpDestinationMtpRecvTestCounter OBJECT-TYPE
        SYNTAX Counter
        ACCESS read-only
        STATUS mandatory
        DESCRIPTION
            "Counter specifying the number of MTP Testing & Maintenance MSU's sent."
        ::= { mtpDestinationEntry 13 }
      
    mtpDestinationMtpSentTestCounter OBJECT-TYPE
        SYNTAX Counter
        ACCESS read-only
        STATUS mandatory
        DESCRIPTION
            "Counter specifying the number of MTP Testing & Maintenance MSU's sent."
        ::= { mtpDestinationEntry 14 }
      
    mtpDestinationMtpRecvSccpCounter OBJECT-TYPE
        SYNTAX Counter
        ACCESS read-only
        STATUS mandatory
        DESCRIPTION
            "Counter specifying the number of SCCP MSU's sent."
        ::= { mtpDestinationEntry 15 }
      
    mtpDestinationMtpSentSccpCounter OBJECT-TYPE
        SYNTAX Counter
        ACCESS read-only
        STATUS mandatory
        DESCRIPTION
            "Counter specifying the number of SCCP MSU's sent."
        ::= { mtpDestinationEntry 16 }
      
    -- the MTP route group

    mtpRouteTable OBJECT-TYPE
        SYNTAX  SEQUENCE OF MtpRouteEntry
        ACCESS  not-accessible
        STATUS  mandatory
        DESCRIPTION
            "Table containing info about MTP routes. For each MTP destination, 
            a table of this type should exist."
        ::= { mtp 9 }

    mtpRouteEntry OBJECT-TYPE
        SYNTAX  MtpRouteEntry
        ACCESS  not-accessible
        STATUS  mandatory
        DESCRIPTION
            "Entry of table containing info about MTP routes."
        INDEX   { mtpDestinationIndex, mtpRouteIndex }
        ::= { mtpRouteTable 1 }

    MtpRouteEntry ::=
        SEQUENCE {
            mtpRouteIndex                         Gauge(1..32),
            mtpRouteAdminState                    AdminState,
            mtpRouteOperationalState              RouteOperationalState,
            mtpRouteLinkSet                       NameString,
            mtpRoutePriority                      Priority,
            mtpRouteWeight                        Weight,
            mtpRouteThroughput                    Throughput,
            mtpRouteM3uaSgp                       NameString,
            mtpRouteM3uaAs                        NameString
        }     

    mtpRouteIndex OBJECT-TYPE
        SYNTAX  Gauge(1..32)
        ACCESS  not-accessible
        STATUS  mandatory
        DESCRIPTION
            "Index of entry in table containing info about MTP routes."
        ::= { mtpRouteEntry 1 }

    mtpRouteAdminState OBJECT-TYPE
        SYNTAX  AdminState
        ACCESS  read-write
        STATUS  mandatory
        DESCRIPTION
            "Administrative state of entry in table containing info about the 
             MTP route. Activating a route, deactivating a route or 
             removing an entry from the table (and implicitly deactivating the 
             associated route) is accomplished by writing the administrative
             state."
        ::= { mtpRouteEntry 2 }

    mtpRouteOperationalState OBJECT-TYPE
        SYNTAX  RouteOperationalState
        ACCESS  read-only
        STATUS  mandatory
        DESCRIPTION
            "Operational state of route."
        ::= { mtpRouteEntry 3 }

    mtpRouteLinkSet OBJECT-TYPE
        SYNTAX  NameString
        ACCESS  read-write
        STATUS  mandatory
        DESCRIPTION
            "Name of M3UA SGP entry that the route uses. Only modify-able if 
             the entry's administrative state is 'inactive'. Note that presence
             of this attribute is mutually exclusive with mtpRouteM3uaSgp and
             mtpRouteM3uaAs."
        ::= { mtpRouteEntry 4 }

    mtpRoutePriority OBJECT-TYPE
        SYNTAX  Priority
        ACCESS  read-write
        STATUS  mandatory
        DESCRIPTION
            "Priority of route. TextPass device will always select route with 
             highest priority. Only modify-able if the entry's administrative 
             state is 'inactive'."
        ::= { mtpRouteEntry 5 }

    mtpRouteWeight OBJECT-TYPE
        SYNTAX  Weight
        ACCESS  read-write
        STATUS  mandatory
        DESCRIPTION
            "Weight of route. When more than one route of highest priority are
             available, the TextPass device will perform loadsharing based on
             the route's weight. The higher the weight, the higher the load.
             Only modify-able if the entry's administrative state is 
             'inactive'."
        ::= { mtpRouteEntry 6 }

    mtpRouteThroughput OBJECT-TYPE
        SYNTAX  Throughput
        ACCESS  read-write
        STATUS  mandatory
        DESCRIPTION
            "Maximum throughput in terms of MSU's per second for the route
            (excluding the MSU's for MTP management and MTP testing & 
            maintenance)."
        ::= { mtpRouteEntry 7 }

    mtpRouteM3uaSgp OBJECT-TYPE
        SYNTAX  NameString
        ACCESS  read-write
        STATUS  mandatory
        DESCRIPTION
            "Name of M3UA SGP entry that the route uses. Only modify-able if 
             the entry's administrative state is 'inactive'. Note that presence
             of this attribute is mutually exclusive with mtpRouteLinkSet and 
             mtpRouteM3uaAs."
        ::= { mtpRouteEntry 8 }

    mtpRouteM3uaAs OBJECT-TYPE
        SYNTAX  NameString
        ACCESS  read-write
        STATUS  mandatory
        DESCRIPTION
            "Name of M3UA AS entry that the route uses. Only modify-able if 
             the entry's administrative state is 'inactive'. Note that presence
             of this attribute is mutually exclusive with mtpRouteLinkSet and 
             mtpRouteM3uaSgp."
        ::= { mtpRouteEntry 9 }

    -- the SCCP subsystem

    sccp   OBJECT IDENTIFIER ::= { textpass 12 }

    -- the SCCP addresses group
    
    sccpAddresses OBJECT IDENTIFIER ::= { sccp 1 }

    sccpActualAddrNationalUseBit OBJECT-TYPE
        SYNTAX  Boolean
        ACCESS  read-write
        STATUS  mandatory
        DESCRIPTION
            "National use bit used in global title to address this specific 
             TextPass device. Defaults to false for ITU-T and to true for ANSI."
        ::= { sccpAddresses 1 }

    sccpActualAddrGtAddressInfo OBJECT-TYPE
        SYNTAX  E164AddressString
        ACCESS  read-write
        STATUS  mandatory
        DESCRIPTION
            "Address digit string used in global title to address this specific 
             TextPass device."
        ::= { sccpAddresses 2 }

    sccpActualAddrGtIndicator OBJECT-TYPE
        SYNTAX  GlobalTitleIndicator
        ACCESS  read-write
        STATUS  mandatory
        DESCRIPTION
            "Global title indicator used in global title to address this 
             specific TextPass device."
        ::= { sccpAddresses 3 }

    sccpActualAddrGtTranslationType OBJECT-TYPE
        SYNTAX  TranslationType
        ACCESS  read-write
        STATUS  mandatory
        DESCRIPTION
            "Translation type used in global title to address this specific 
             TextPass device."
        ::= { sccpAddresses 4 }

    sccpActualAddrGtNumberingPlan OBJECT-TYPE
        SYNTAX  NumberingPlan
        ACCESS  read-write
        STATUS  mandatory
        DESCRIPTION
            "Numbering plan used in global title to address this specific 
             TextPass device."
        ::= { sccpAddresses 5 }

    sccpActualAddrGtNatureOfAddressInd OBJECT-TYPE
        SYNTAX  NatureOfAddressIndication
        ACCESS  read-write
        STATUS  mandatory
        DESCRIPTION
            "Nature of address indicator used in global title to address this 
             specific TextPass device."
        ::= { sccpAddresses 6 }

    sccpActualAddrPcInCaPaIncluded OBJECT-TYPE
        SYNTAX  Boolean
        ACCESS  read-write
        STATUS  mandatory
        DESCRIPTION
            "Indicator determining whether the point code should be included in 
             the calling party address of MSU's that this specific TextPass 
             device sends."
        ::= { sccpAddresses 7 }

    sccpOptimisedAddressing OBJECT-TYPE
        SYNTAX  Boolean
        ACCESS  read-write
        STATUS  mandatory
        DESCRIPTION
            "When the sccpAlwaysUsePcSsnAddressing object is set to 'true', 
            this object has no effect. This object is only applicable when 
            the sccpAlwaysUsePcSsnAddressing object is set to 'false'.             
            The behaviour resulting from  this object is then as following:
            When set to 'true', which is the default, the SCCP calling party 
            address in the UDT's output by TextPass depends on the
            routing indicator of the SCCP called party address. If this
            indicator is set to PC/SSN, TextPass will specify a routing
            indicator of PC/SSN for the SCCP calling party address of the
            SCCP calling party address. Futhermore, it will not include
            a GT address in the SCCP calling party address. When the 
            indicator is GT or when optimised addresing is disabled, 
            TextPass will use an SCCP calling party address as specified
            by the objects that make up the SCCP address of TextPass."
        ::= { sccpAddresses 14 }

    sccpAlwaysUsePcSsnAddressing OBJECT-TYPE
        SYNTAX  Boolean
        ACCESS  read-write
        STATUS  mandatory
        DESCRIPTION
            "When set to 'true', the SCCP calling party address in the 
            UDT's output by TextPass will always have as SCCP called party 
            address with the routing indicator set to PC/SSN. Futhermore, 
            it will not include a GT address in the SCCP calling party 
            address. When set to 'false', the format of the SCCP called 
            party address is determined by sccpOptimisedAddressing. 
            Default value of this object is 'false'."
        ::= { sccpAddresses 15 }

    sccpAliasForHlrSsn OBJECT-TYPE
        SYNTAX  SubSystemNumber
        ACCESS  read-write
        STATUS  mandatory
        DESCRIPTION
            "Alias for HLR SSN. The HLR subsystem within TextPass can be 
            addressed through SSN 6 and through this alias. Default for 
            this alias is 221."
        ::= { sccpAddresses 21 }

    sccpAliasForMscSsn OBJECT-TYPE
        SYNTAX  SubSystemNumber
        ACCESS  read-write
        STATUS  mandatory
        DESCRIPTION
            "Alias for MSC SSN. The MSC subsystem within TextPass can be 
            addressed through SSN 8 and through this alias. Default for 
            this alias is 221."
        ::= { sccpAddresses 22 }

    sccpAliasForSgsnSsn OBJECT-TYPE
        SYNTAX  SubSystemNumber
        ACCESS  read-write
        STATUS  mandatory
        DESCRIPTION
            "Alias for SGSN SSN. The SGSN subsystem within TextPass can be 
            addressed through SSN 149 and through this alias. Default for 
            this alias is 222."
        ::= { sccpAddresses 23 }

    sccpAliasForTt OBJECT-TYPE
        SYNTAX  TranslationType
        ACCESS  read-write
        STATUS  mandatory
        DESCRIPTION
            "Alias for translation type used in global title to address this 
             specific TextPass device."
        ::= { sccpAddresses 31 }

    -- the SCCP timers group
    
    sccpTimers OBJECT IDENTIFIER ::= { sccp 2 }

    sccpTimerStatInfo OBJECT-TYPE
        SYNTAX  Gauge(50..100)
        ACCESS  read-write
        STATUS  mandatory
        DESCRIPTION
            "Delay between requests for tracking subsystem information. 
             Expressed in units of 100 ms. Default 10 seconds."
        ::= { sccpTimers 1 }
        
    sccpTimerReassembly OBJECT-TYPE
        SYNTAX  Gauge(10..300)
        ACCESS  read-write
        STATUS  mandatory
        DESCRIPTION
            "Maximum timespan in which a segmented message, conveyed with 
             multiple XUDTs, is to be received. Expressed in units of 100 ms. 
             Default is 5 seconds."
        ::= { sccpTimers 2 }
        
    -- the SCCP STP table
    
    sccpStpTable OBJECT-TYPE
        SYNTAX  SEQUENCE OF SccpStpEntry
        ACCESS  not-accessible
        STATUS  mandatory
        DESCRIPTION
            "Table containing info about SCCP STP's."
        ::= { sccp 3 }

    sccpStpEntry OBJECT-TYPE
        SYNTAX  SccpStpEntry
        ACCESS  not-accessible
        STATUS  mandatory
        DESCRIPTION
            "Entry of table containing info about STP STP's."
        INDEX   { sccpStpIndex }
        ::= { sccpStpTable 1 }

    SccpStpEntry ::=
        SEQUENCE {
            sccpStpIndex                          Gauge(1..100),
            sccpStpAdminState                     AdminState,
            sccpStpOperationalState               StpOperationalState,
            sccpStpName                           NameString,
            sccpStpMtpDestination                 NameString,
            sccpStpPriority                       Priority,
            sccpStpWeight                         Weight,
            sccpStpThroughput                     Throughput
        }     

    sccpStpIndex OBJECT-TYPE
        SYNTAX  Gauge(1..100)
        ACCESS  not-accessible
        STATUS  mandatory
        DESCRIPTION
            "Index of entry in table containing info about SCCP STP's."
        ::= { sccpStpEntry 1 }

    sccpStpAdminState OBJECT-TYPE
        SYNTAX  AdminState
        ACCESS  read-write
        STATUS  mandatory
        DESCRIPTION
            "Administrative state of entry in table containing info about the 
             SCCP STP's. Activating an STP, deactivating an STP or 
             removing an entry from the table (and implicitly deactivating the 
             associated STP) is accomplished by writing the administrative
             state."
        ::= { sccpStpEntry 2 }

    sccpStpOperationalState OBJECT-TYPE
        SYNTAX  StpOperationalState
        ACCESS  read-only
        STATUS  mandatory
        DESCRIPTION
            "Operational state of STP."
        ::= { sccpStpEntry 3 }
        
    sccpStpName OBJECT-TYPE
        SYNTAX  NameString
        ACCESS  read-write
        STATUS  mandatory
        DESCRIPTION
            "Operational state of STP. Only modify-able if the entry's 
             administrative state is 'inactive'."
        ::= { sccpStpEntry 4 }

    sccpStpMtpDestination OBJECT-TYPE
        SYNTAX  NameString
        ACCESS  read-write
        STATUS  mandatory
        DESCRIPTION
            "Name of entry in MTP destination table. Refers to the MTP 
             destination that runs the STP."
        ::= { sccpStpEntry 5 }

    sccpStpPriority OBJECT-TYPE
        SYNTAX  Priority
        ACCESS  read-write
        STATUS  mandatory
        DESCRIPTION
            "Priority of STP. TextPass device will always select STP with 
             highest priority. Only modify-able if the entry's administrative 
             state is 'inactive'."
        ::= { sccpStpEntry 6 }

    sccpStpWeight OBJECT-TYPE
        SYNTAX  Weight
        ACCESS  read-write
        STATUS  mandatory
        DESCRIPTION
            "Weight of STP. When more than one STP of highest priority are
             available, the TextPass device will perform loadsharing based on
             the STP's weight. The higher the weight, the higher the load.
             Only modify-able if the entry's administrative state is 'inactive'."
        ::= { sccpStpEntry 7 }

    sccpStpThroughput OBJECT-TYPE
        SYNTAX  Throughput
        ACCESS  read-write
        STATUS  mandatory
        DESCRIPTION
            "Maximum throughput in terms of UDT's and UDTS's per second for the
             STP (excluding the UDT's for SCCP management)."
        ::= { sccpStpEntry 8 }

    -- the SCCP global title translation table
    
    sccpGttTable OBJECT-TYPE
        SYNTAX  SEQUENCE OF SccpGttEntry
        ACCESS  not-accessible
        STATUS  mandatory
        DESCRIPTION
            "Table containing SCCP global title translation rules. TextPass 
             uses those rules when it needs to compose an SCCP called party 
             address for an outgoing UDT message. Whenever TextPass needs to 
             send a UDT, it has an internationally encoded E164 address that 
             identifies the destination. Based on this E164 address, TextPass 
             will select one of the translation rules. The translation rule contains 
             information that is needed to compose the SCCP called party 
             address. 
             
             Two types of translation rules exist. Rules that exactly match and 
             wildcard rules. To match an exact rule, the E164 address that
             identifies the destination should be equal to the address of the 
             translation rule. Using a wildcard rule, one can match a range of 
             addresses. The address of a wildcard rule is specified as a number
             of digits followed by an asterix ('*'). A wildcard rule matches 
             when the E164 address that identifies the destination starts with 
             the address digits of the wildcard rule.
             
             In case multiple rules apply, the following applies:
             - Exactly matching rules have precedence over wildcard rules.
             - Between wildcard rules, the rule containing the most digits
               always wins."
        ::= { sccp 4 }

    sccpGttEntry OBJECT-TYPE
        SYNTAX  SccpGttEntry
        ACCESS  not-accessible
        STATUS  mandatory
        DESCRIPTION
            "Entry of table containing SCCP translation rules."
        INDEX   { sccpGttIndex }
        ::= { sccpGttTable 1 }

    SccpGttEntry ::=
        SEQUENCE {
            sccpGttIndex                          Gauge(1..10000),
            sccpGttAdminState                     AdminState,
            sccpGttAppliedCounter                 Counter,
            sccpGttInputSubSystemNumber           SubSystemNumber,
            sccpGttInputGtTranslationType         TranslationType,
            sccpGttInputGtNatureOfAddressInd      NatureOfAddressIndication,
            sccpGttInputGtAddressInfo             E164AddressString,
            sccpGttInputGtNumberingPlan           NumberingPlan,
            sccpGttOutputNationalUseBit           Boolean,
            sccpGttOutputRoutingIndicator         RoutingIndicator,
            sccpGttOutputGtIndicator              GlobalTitleIndicator,
            sccpGttOutputPointCode                PointCode,
            sccpGttOutputSubSystemNumber          SubSystemNumber,
            sccpGttOutputGtTranslationType        TranslationType,
            sccpGttOutputGtNatureOfAddressInd     NatureOfAddressIndication,
            sccpGttOutputGtAddressInfo            E164AddressString,
            sccpGttOutputMtpDestination           NameString,
            sccpGttOutputSuaAs                    NameString,
            sccpGttOutputGtNumberingPlan          NumberingPlan,
            sccpGttOutputPointCodeString          PointCodeString
        }               

    sccpGttIndex OBJECT-TYPE
        SYNTAX  Gauge(1..10000)
        ACCESS  not-accessible
        STATUS  mandatory
        DESCRIPTION
            "Index of entry in table containing info about SCCP translation rules."
        ::= { sccpGttEntry 1 }

    sccpGttAdminState OBJECT-TYPE
        SYNTAX  AdminState
        ACCESS  read-write
        STATUS  mandatory
        DESCRIPTION
            "Administrative state of entry in table containing translation rules. 
             Activating a translation rule, deactivating a translation rule or 
             removing an entry from the table (and implicitly deactivating the 
             associated translation rule) is accomplished by writing the 
             administrative state."
        ::= { sccpGttEntry 2 }

    sccpGttAppliedCounter OBJECT-TYPE
        SYNTAX Counter
        ACCESS read-only
        STATUS mandatory
        DESCRIPTION
            "Counter specifying the number of times that the SCCP GTT rule has 
            been applied."
        ::= { sccpGttEntry 3 }
      
    sccpGttInputSubSystemNumber OBJECT-TYPE
        SYNTAX  SubSystemNumber
        ACCESS  read-write
        STATUS  mandatory
        DESCRIPTION
            "Value that should match the Subsystem Number in the input. If not 
            specified, any Subsystem Number value satisfies."
        ::= { sccpGttEntry 11 }

    sccpGttInputGtTranslationType OBJECT-TYPE
        SYNTAX  TranslationType
        ACCESS  read-write
        STATUS  mandatory
        DESCRIPTION
            "Value that should match the Translation Type in the input. If not 
            specified, any Translation Type value satisfies."
        ::= { sccpGttEntry 12 }

    sccpGttInputGtNatureOfAddressInd OBJECT-TYPE
        SYNTAX  NatureOfAddressIndication
        ACCESS  read-write
        STATUS  mandatory
        DESCRIPTION
            "Value that should match the Nature of Address Indicator in the 
            input. If not specified, defaults to 'internationalNumber'."
        ::= { sccpGttEntry 13 }

    sccpGttInputGtAddressInfo OBJECT-TYPE
        SYNTAX  E164AddressString
        ACCESS  read-write
        STATUS  mandatory
        DESCRIPTION
            "Value that should match the Global Title Address Information in 
            the input. Consisting of one or more digits in case of an exactly 
            matching rule. For wildcard rules, consisting of zero or more digits 
            followed by an asterix."
        ::= { sccpGttEntry 14 }

    sccpGttInputGtNumberingPlan OBJECT-TYPE
        SYNTAX  NumberingPlan
        ACCESS  read-write
        STATUS  mandatory
        DESCRIPTION
            "Value that should match the Numbering Plan in the input. If not 
            specified, any Numbering Plan value satisfies."
        ::= { sccpGttEntry 15 }

    sccpGttOutputNationalUseBit OBJECT-TYPE
        SYNTAX  Boolean
        ACCESS  read-write
        STATUS  mandatory
        DESCRIPTION
            "Value for National Use Bit that is specified in output when rule 
            matches. If not specified, defaults to 'false' for ITU-T and to 
            'false' for ANSI."
        ::= { sccpGttEntry 21 }

    sccpGttOutputRoutingIndicator OBJECT-TYPE
        SYNTAX  RoutingIndicator 
        ACCESS  read-write
        STATUS  mandatory
        DESCRIPTION
            "Value for Routing Indicator that is specified in output when rule 
            matches. If not specified, defaults to 'routeOnGlobalTitle'."
        ::= { sccpGttEntry 22 }

    sccpGttOutputGtIndicator OBJECT-TYPE
        SYNTAX  GlobalTitleIndicator
        ACCESS  read-write
        STATUS  mandatory
        DESCRIPTION
            "Value for Global Title Indicator that is specified in output when 
            rule matches. If not specified, defaults to 4. 
            
            NOTE: In case the value for sccpGttOutputRoutingIndicator is 
            'routeOnGlobalTitle', the only valid value is 4. Otherwise, when the 
            for sccpGttOutputRoutingIndicator is 'routeOnSubSystemNumber', 0 and 
            4 are valid values."
        ::= { sccpGttEntry 23 }

    sccpGttOutputPointCode OBJECT-TYPE
        SYNTAX  PointCode
        ACCESS  read-write
        STATUS  mandatory
        DESCRIPTION
            "Value for Point Code that is specified in output when rule
            matches and formatted as commonly done in ITU-T.
            If not specified, point code is not included in output.
            Note that this point code can be changed/viewed by this object as 
            well as the sccpGttOutputPointCodeString object."
        ::= { sccpGttEntry 24 }

    sccpGttOutputSubSystemNumber OBJECT-TYPE
        SYNTAX  SubSystemNumber 
        ACCESS  read-write
        STATUS  mandatory
        DESCRIPTION
            "Value for Subsystem Number that is specified in output when rule
            matches. If not specified, defaults to value as set in input." 
        ::= { sccpGttEntry 25 }

    sccpGttOutputGtTranslationType OBJECT-TYPE
        SYNTAX  TranslationType
        ACCESS  read-write
        STATUS  mandatory
        DESCRIPTION
            "Value for Translation Type that is specified in output when rule
            matches. If not specified, defaults to value as set in input. 
            
            NOTE: Only applicable when sccpGttOutputGtIndicator is 4."
        ::= { sccpGttEntry 26 }

    sccpGttOutputGtNatureOfAddressInd OBJECT-TYPE
        SYNTAX  NatureOfAddressIndication
        ACCESS  read-write
        STATUS  mandatory
        DESCRIPTION
            "Value for Nature of Address Indicator that is specified in output 
            when rule matches. If not specified, defaults to value as set in 
            input. 

            NOTE: Only applicable when sccpGttOutputGtIndicator is 4."
        ::= { sccpGttEntry 27 }

    sccpGttOutputGtAddressInfo OBJECT-TYPE
        SYNTAX  E164AddressString
        ACCESS  read-write
        STATUS  mandatory
        DESCRIPTION
            "Value for Global Title Address Information that is specified in
            output when rule matches. If not specified, defaults to the value
            as set in input. 
            
            For wilcard rules, the value for sccpGttOutputGtAddressInfo might
            consist of zero or more digits followed by an asterix. The value for
            Global Title Address Information in the output will then specify
            the digits within the value for sccpGttOutputGtAddressInfo followed
            by the digits in the input that are caught by the asterix in the
            value for sccpGttInputGtAddressInfo. (e.g. suppose 
            sccpGttInputGtAddressInfo is equal to 31653*, 
            sccpGttOutputGtAddressInfo is equal to 0653*, and the Global Title
            Address Info in the input is 31653131313; the Global Title Address 
            Info in the output will then become 0653131313)

            NOTE: Only applicable when sccpGttOutputGtIndicator is 4."
        ::= { sccpGttEntry 28 }

    sccpGttOutputMtpDestination OBJECT-TYPE
        SYNTAX  NameString
        ACCESS  read-write
        STATUS  mandatory
        DESCRIPTION
            "Name of MTP destination to which UDT is sent. If not specified, the
            UDT is sent to a SUA application server or to the STP."
        ::= { sccpGttEntry 29 }

    sccpGttOutputSuaAs OBJECT-TYPE
        SYNTAX  NameString
        ACCESS  read-write
        STATUS  mandatory
        DESCRIPTION
            "Name of SUA AS to which UDT is sent. If not specified, the UDT is 
            sent to an MTP destination or to the STP."
        ::= { sccpGttEntry 30 }

    sccpGttOutputGtNumberingPlan OBJECT-TYPE
        SYNTAX  NumberingPlan
        ACCESS  read-write
        STATUS  mandatory
        DESCRIPTION
            "Value for Numbering Plan that is specified in output when rule
            matches. If not specified, defaults to value as set in input." 
        ::= { sccpGttEntry 31 }

    sccpGttOutputPointCodeString OBJECT-TYPE
        SYNTAX  PointCodeString
        ACCESS  read-write
        STATUS  mandatory
        DESCRIPTION
            "Value for Point Code that is specified in output when rule
            matches and formatted as commonly done in ANSI.
            If not specified, point code is not included in output.
            Note that this point code can be changed/viewed by this object as 
            well as the sccpGttOutputPointCodeString object."
        ::= { sccpGttEntry 32 }

    -- the SCCP counters group
    
    sccpCounters OBJECT IDENTIFIER ::= { sccp 5 }

    sccpRecvUdtCounter OBJECT-TYPE
        SYNTAX Counter
        ACCESS read-only
        STATUS mandatory
        DESCRIPTION
            "Counter specifying the number of SCCP Unit Data messages received."
        ::= { sccpCounters 1 }
      
    sccpSentUdtCounter OBJECT-TYPE
        SYNTAX Counter
        ACCESS read-only
        STATUS mandatory
        DESCRIPTION
            "Counter specifying the number of SCCP Unit Data messages sent."
        ::= { sccpCounters 2 }
      
    sccpRecvUdtsCounter OBJECT-TYPE
        SYNTAX Counter
        ACCESS read-only
        STATUS mandatory
        DESCRIPTION
            "Counter specifying the number of SCCP Unit Data Service messages 
            received."
        ::= { sccpCounters 3 }
      
    sccpSentUdtsCounter OBJECT-TYPE
        SYNTAX Counter
        ACCESS read-only
        STATUS mandatory
        DESCRIPTION
            "Counter specifying the number of SCCP Unit Data Service 
            messages sent."
        ::= { sccpCounters 4 }
          
    sccpRecvXudtCounter OBJECT-TYPE
        SYNTAX Counter
        ACCESS read-only
        STATUS mandatory
        DESCRIPTION
            "Counter specifying the number of SCCP Extended Unit Data messages received."
        ::= { sccpCounters 5 }
      
    sccpSentXudtsCounter OBJECT-TYPE
        SYNTAX Counter
        ACCESS read-only
        STATUS mandatory
        DESCRIPTION
            "Counter specifying the number of SCCP Extended Unit Data Service 
            messages sent."
        ::= { sccpCounters 8 }
          
    sccpProperties OBJECT IDENTIFIER ::= { sccp 6 }

    sccpDiscardUdtWithOwnAddressInCgPa OBJECT-TYPE
        SYNTAX Boolean
        ACCESS read-only
        STATUS mandatory
        DESCRIPTION
            "Boolean specifying whether UDT-s with own address in SCCP CGPA 
             will be discarded. Defautl is 'true'."
        ::= { sccpProperties 1 }
        
    sccpHopCounter OBJECT-TYPE 
        SYNTAX Gauge(1..255)
        ACCESS read-only
        STATUS mandatory
        DESCRIPTION
            "Value to be used for Hop Counter parameter in XUDTS. Default is 10."
        ::= { sccpProperties 2 }
        
          
    -- the TCAP subsystem
    
    tcap   OBJECT IDENTIFIER ::= { textpass 13 }

    -- the TCAP timers group
    
    tcapTimers OBJECT IDENTIFIER ::= { tcap 1 }

    tcapTmrMaxResponseTime OBJECT-TYPE
        SYNTAX  Gauge(1..100)
        ACCESS  read-write
        STATUS  mandatory
        DESCRIPTION
            "Timer for regular MAP operations defining maximum time span allowed 
             between a TCAP request message (i.e. TC-BEGIN, TC-CONTINUE) and a 
             TCAP response (i.e. TC-END, TC-CONTINUE), expressed in units of 
             seconds. Default is 5 seconds. This timer is applicable for any
             MAP operation apart from the MAP 'mtForwardSm' operation (which
             is used for SMS delivery)."
        ::= { tcapTimers 1 }

    tcapTmrMaxLongResponseTime OBJECT-TYPE
        SYNTAX  Gauge(1..100)
        ACCESS  read-write
        STATUS  mandatory
        DESCRIPTION
            "Timer for long MAP operations defining maximum time span allowed 
             between a TCAP request message (i.e. TC-BEGIN, TC-CONTINUE) and a 
             TCAP response (i.e. TC-END, TC-CONTINUE), expressed in units of 
             seconds. Default is 30 seconds. This timer is applicable for the 
             MAP 'mtForwardSm' operation (which is used for SMS delivery)."
        ::= { tcapTimers 2 }

    tcapTmrAnsiMaxResponseTime OBJECT-TYPE
        SYNTAX  Gauge(1..100)
        ACCESS  read-write
        STATUS  mandatory
        DESCRIPTION
            "Timer for regular ANSI-MAP operations defining maximum time span
            allowed between a TCAP Query-With-Permission message and a TCAP
            Response, expressed in units of seconds. Default is 5 seconds.
            This timer is applicable for any MAP operation apart from the
            SMDPP-MT operation, which is used for SMS delivery."
        ::= { tcapTimers 3 }

    tcapTmrAnsiMaxDeliveryTime OBJECT-TYPE
        SYNTAX  Gauge(1..100)
        ACCESS  read-write
        STATUS  mandatory
        DESCRIPTION
            "Timer for ANSI-41 SMDPP-MT message delivery operations, defining
            the maximum time span allowed between a TCAP Query-With-Permission
            message and a TCAP Response, expressed in units of seconds. 
            Default is 30 seconds."
        ::= { tcapTimers 4 }

    tcapCapTmrMaxResponseTime OBJECT-TYPE
        SYNTAX  Gauge(1..100)
        ACCESS  read-write
        STATUS  mandatory
        DESCRIPTION
            "Value for CAP timer tssf. This timer specifies the maximum 
             inactivity time of a CAP-relating dialogue. Default is 10 seconds."
        ::= { tcapTimers 11 }

    -- the TCAP counters group
    
    tcapCounters OBJECT IDENTIFIER ::= { tcap 2 }

    tcapRecvBeginCounter OBJECT-TYPE
        SYNTAX Counter
        ACCESS read-only
        STATUS mandatory
        DESCRIPTION
            "Counter specifying the number of TCAP BEGIN messages received."
        ::= { tcapCounters 1 }
      
    tcapSentBeginCounter OBJECT-TYPE
        SYNTAX Counter
        ACCESS read-only
        STATUS mandatory
        DESCRIPTION
            "Counter specifying the number of TCAP BEGIN messages sent."
        ::= { tcapCounters 2 }
      
    tcapRecvContinueCounter OBJECT-TYPE
        SYNTAX Counter
        ACCESS read-only
        STATUS mandatory
        DESCRIPTION
            "Counter specifying the number of TCAP CONTINUE messages received."
        ::= { tcapCounters 3 }
      
    tcapSentContinueCounter OBJECT-TYPE
        SYNTAX Counter
        ACCESS read-only
        STATUS mandatory
        DESCRIPTION
            "Counter specifying the number of TCAP CONTINUE messages sent."
        ::= { tcapCounters 4 }
      
    tcapRecvEndCounter OBJECT-TYPE
        SYNTAX Counter
        ACCESS read-only
        STATUS mandatory
        DESCRIPTION
            "Counter specifying the number of TCAP END messages received."
        ::= { tcapCounters 5 }
      
    tcapSentEndCounter OBJECT-TYPE
        SYNTAX Counter
        ACCESS read-only
        STATUS mandatory
        DESCRIPTION
            "Counter specifying the number of TCAP END MSU's sent."
        ::= { tcapCounters 6 }
      
    tcapRecvAbortCounter OBJECT-TYPE
        SYNTAX Counter
        ACCESS read-only
        STATUS mandatory
        DESCRIPTION
            "Counter specifying the number of TCAP ABORT messages received."
        ::= { tcapCounters 7 }
      
    tcapSentAbortCounter OBJECT-TYPE
        SYNTAX Counter
        ACCESS read-only
        STATUS mandatory
        DESCRIPTION
            "Counter specifying the number of TCAP ABORT messages sent."
        ::= { tcapCounters 8 }
    
    -- the TCAP properties group
    
    tcapProperties OBJECT IDENTIFIER ::= { tcap 3 }

    tcapPropRelayTcContinueOnVpc OBJECT-TYPE
        SYNTAX Boolean
        ACCESS read-only
        STATUS mandatory
        DESCRIPTION
            "Indicator specifying how TextPass should handle a TC-CONTINUE 
            that has been received on the virtual point code. When the 
            indicator is 'false', TextPass passes the TC-CONTINUE up to the 
            MAP layer for further processing. When the indicator is 'true', 
            TextPass derives the destination for the TC-CONTINUE. The 
            destination is either the TextPass itself or another TextPass.
            If the destination is the TextPass itself, the TC-CONTINUE is
            treated as if it has been received on the specific point code.
            Otherwise, when the destination is another TextPass, the 
            TC-CONTINUE is relayed to the other TextPass (provided that
            an MTP destination exists for this other TextPass).
            Default is 'false'.
            Currently, this parameter is only supported for an ITU-T SS.7
            stack."            
        ::= { tcapProperties 1 }
        
    -- the MAP subsystem

    map    OBJECT IDENTIFIER ::= { textpass 14 }
       
    -- the M3UA subsystem

    m3ua   OBJECT IDENTIFIER ::= { textpass 19 }

    -- the M3UA properties
    
    m3uaProperties OBJECT IDENTIFIER ::= { m3ua 1 }
    
    m3uaPropAspIdentifier OBJECT-TYPE
        SYNTAX  AspIdentifier
        ACCESS  read-write
        STATUS  mandatory
        DESCRIPTION
            "Value of ASP identifier to be used in ASP-UP message towards remote 
            M3UA SGPs.  Default is 0."
        ::= { m3uaProperties 1 }

    m3uaPropRoutingContextForActualSpc OBJECT-TYPE
        SYNTAX  RoutingContext
        ACCESS  read-write
        STATUS  mandatory
        DESCRIPTION
            "Value of routing context for actual SPC. Default is 0."
        ::= { m3uaProperties 2 }

    m3uaPropRoutingContextForVirtualSpc OBJECT-TYPE
        SYNTAX  RoutingContext
        ACCESS  read-write
        STATUS  mandatory
        DESCRIPTION
            "Value of routing context for virtual SPC. Default is 1."
        ::= { m3uaProperties 3 }
 
    m3uaPropNetworkAppearance OBJECT-TYPE
        SYNTAX  NetworkAppearance
        ACCESS  read-write
        STATUS  mandatory
        DESCRIPTION
            "Value of network appearance to be used in messages towards remote 
            M3UA SGPs.  Default is 0."
        ::= { m3uaProperties 4 }

    -- the M3UA local IP address table

    m3uaLocalAddressTable OBJECT-TYPE
        SYNTAX  SEQUENCE OF M3uaLocalAddressEntry
        ACCESS  not-accessible
        STATUS  mandatory
        DESCRIPTION
            "Table containing info about local IP addresses that TextPass 
            uses for M3UA."
        ::= { m3ua 2 }

    m3uaLocalAddressEntry OBJECT-TYPE
        SYNTAX  M3uaLocalAddressEntry
        ACCESS  not-accessible
        STATUS  mandatory
        DESCRIPTION
            "Entry of table containing info about local IP addresses that  
            TextPass uses for M3UA."
        INDEX   { m3uaLocalAddressIndex }
        ::= { m3uaLocalAddressTable 1 }

    M3uaLocalAddressEntry ::=
        SEQUENCE {
            m3uaLocalAddressIndex                   M3uaLocalAddressTableIndex,
            m3uaLocalAddressAdminState              AdminState,
            m3uaLocalAddressSpec                    IpAddressSpec
        }
        
    m3uaLocalAddressIndex OBJECT-TYPE
        SYNTAX  M3uaLocalAddressTableIndex
        ACCESS  read-write
        STATUS  mandatory
        DESCRIPTION
            "Index of entry in table with local IP addresses for M3UA."
        ::= { m3uaLocalAddressEntry 1 }

    m3uaLocalAddressAdminState OBJECT-TYPE
        SYNTAX  AdminState
        ACCESS  read-write
        STATUS  mandatory
        DESCRIPTION
            "Administrative state of the local IP address for M3UA."
        ::= { m3uaLocalAddressEntry 2 }

    m3uaLocalAddressSpec OBJECT-TYPE
        SYNTAX  IpAddressSpec
        ACCESS  read-write
        STATUS  mandatory
        DESCRIPTION
            "IPv4 or IPv6 specification for local IP address for M3UA."
        ::= { m3uaLocalAddressEntry 11 }

        
    -- the M3UA SGP table
    
    m3uaSgpTable OBJECT-TYPE
        SYNTAX  SEQUENCE OF M3uaSgpEntry
        ACCESS  not-accessible
        STATUS  mandatory
        DESCRIPTION
            "Table containing info about remote M3UA Signalling Gateway 
            Processes (SGP)."
        ::= { m3ua 11 }

    m3uaSgpEntry OBJECT-TYPE
        SYNTAX  M3uaSgpEntry
        ACCESS  not-accessible
        STATUS  mandatory
        DESCRIPTION
            "Entry of table containing info about remote M3UA Signalling Gateway 
            Processes (SGP)."
        INDEX   { m3uaSgpIndex }
        ::= { m3uaSgpTable 1 }

    M3uaSgpEntry ::=
        SEQUENCE {
            m3uaSgpIndex                            M3uaSgpTableIndex,
            m3uaSgpAdminState                       AdminState,
            m3uaSgpOperationalState                 M3uaSgpOperationalState,
            m3uaSgpActualSpcOperationalState        M3uaSgpSpcOperationalState,
            m3uaSgpVirtualSpcOperationalState       M3uaSgpSpcOperationalState,
            m3uaSgpName                             NameString,
            m3uaSgpUseForActualSpc                  Boolean,
            m3uaSgpUseForVirtualSpc                 Boolean,
            m3uaSgpFillInAspIdentifierField         Boolean,
            m3uaSgpFillInRoutingContextField        Boolean,
            m3uaSgpFillInNetworkAppearanceField     Boolean, 
            m3uaSgpTrafficModeField                 M3uaSgpTrafficMode,
            m3uaSgpSctpLocalPort                    SctpPort,
            m3uaSgpSctpRemotePort                   SctpPort,
            m3uaSgpSctpMaxOutboundPduSize           SctpMaxPduSize,
            m3uaSgpSctpMaxInboundPduSize            SctpMaxPduSize,
            m3uaSgpSctpTimerT1Init                  SctpTimerT1Init,
            m3uaSgpSctpTimerT3Rtx                   SctpTimerT3Rtx,
            m3uaSgpSctpTimerHeartbeat               SctpTimerHeartbeat,
            m3uaSgpSctpTimerT1Cookie                SctpTimerT1Cookie,
            m3uaSgpSctpMaxRetransmitTimeout         SctpRetransmitTimeout,
            m3uaSgpSctpMaxPathRetransmits           SctpRetransmits,
            m3uaSgpSctpMaxAssociationRetransmits    SctpRetransmits,
            m3uaSgpSctpMaxConnectAttempts           SctpMaxConnectAttempts,
            m3uaSgpSctpMaxAllowedInboundStreams     SctpStreams,
            m3uaSgpSctpPreferredOutboundStreams     SctpStreams,
            m3uaSgpSctpInitiatingStartupEnabled     Boolean,
            m3uaSgpSctpLocalSendPort                SctpPort,
            m3uaSgpSctpRemoteSendPort               SctpPort,
            m3uaSgpSctpSackDelay                    SctpSackDelay,
            m3uaSgpSctpOperationalState             SctpOperationalState,
            m3uaSgpSctpNegotiatedInboundStreams     SctpStreams,
            m3uaSgpSctpNegotiatedOutboundStreams    SctpStreams,
            m3uaSgpSctpUpTime                       Gauge,
            m3uaSgpSctpDownTime                     Gauge,
            m3uaSgpSctpInboundTsn                   SctpTsn,
            m3uaSgpSctpOutboudTsn                   SctpTsn,
            m3uaSgpSctpTsnCumulativeAck             SctpTsn,
            m3uaSgpSctpLocalReceiveWindow           SctpWindowSize,
            m3uaSgpSctpRemoteReceiveWindow          SctpWindowSize,
            m3uaSgpSctpCongestionWindow             SctpWindowSize,
            m3uaSgpSctpRoundTripTime                SctpRoundTripTime,
            m3uaSgpSctpRetransmissionTimeout        SctpRetransmitTimeout,
            m3uaSgpSctpSmoothedLinkQuality          SctpSmoothedLinkQuality,
            m3uaSgpSctpT3RtxBasedRetransmitCounter  Counter,
            m3uaSgpSctpSackBasedRetransmitCounter   Counter,
            m3uaSgpSctpDataChunkRetransmitCounter   Counter,
            m3uaSgpSctpPrimaryChangeOverCounter     Counter,
            m3uaSgpSctpSentDataByteCounter          Counter,
            m3uaSgpSctpRecvDataByteCounter          Counter,
            m3uaSgpSctpSentSackWithGapCounter       Counter,
            m3uaSgpSctpRecvSackWithGapCounter       Counter,
            m3uaSgpSctpRecvDataChunkDiscardedCounter Counter,
            m3uaSgpSctpSentDataChunkDroppedCounter  Counter,
            m3uaSgpSctpSentDataChunkCounter         Counter,
            m3uaSgpSctpRecvDataChunkCounter         Counter,
            m3uaSgpSctpSentInitChunkCounter         Counter,
            m3uaSgpSctpRecvInitChunkCounter         Counter,
            m3uaSgpSctpSentInitAckChunkCounter      Counter,
            m3uaSgpSctpRecvInitAckChunkCounter      Counter,
            m3uaSgpSctpSentSackChunkCounter         Counter,
            m3uaSgpSctpRecvSackChunkCounter         Counter,
            m3uaSgpSctpSentHeartbeatCounter         Counter,
            m3uaSgpSctpRecvHeartbeatCounter         Counter,
            m3uaSgpSctpSentHeartbeatAckCounter      Counter,
            m3uaSgpSctpRecvHeartbeatAckCounter      Counter,
            m3uaSgpSctpSentAbortChunkCounter        Counter,
            m3uaSgpSctpRecvAbortChunkCounter        Counter,
            m3uaSgpSctpSentShutdownChunkCounter     Counter,
            m3uaSgpSctpRecvShutdownChunkCounter     Counter,
            m3uaSgpSctpSentShutdownAckChunkCounter  Counter,
            m3uaSgpSctpRecvShutdownAckChunkCounter  Counter,
            m3uaSgpSctpSentErrorChunkCounter        Counter,
            m3uaSgpSctpRecvErrorChunkCounter        Counter,
            m3uaSgpSctpSentCookieEchoChunkCounter   Counter,
            m3uaSgpSctpRecvCookieEchoChunkCounter   Counter,
            m3uaSgpSctpSentCookieAckChunkCounter    Counter,
            m3uaSgpSctpRecvCookieAckChunkCounter    Counter,
            m3uaSgpSctpSentShutdownCompleteChunkCounter Counter,
            m3uaSgpSctpRecvShutdownCompleteChunkCounter Counter,
            m3uaSgpSctpInvalidStreamIdErrorCounter  Counter,
            m3uaSgpSctpMissingMandatoryParameterErrorCounter Counter,
            m3uaSgpSctpStaleCookieErrorCounter      Counter,
            m3uaSgpSctpOutOfResourceErrorCounter    Counter,
            m3uaSgpSctpUnresolvableAddressErrorCounter Counter,
            m3uaSgpSctpUnrecognisedChunkTypeErrorCounter Counter,
            m3uaSgpSctpInvalidMandatoryParameterErrorCounter Counter,
            m3uaSgpSctpUnrecognisedParamtersErrorCounter Counter,
            m3uaSgpSctpNoUserDataErrorCounter       Counter,
            m3uaSgpSctpCookieRecvWhileShuttingDownErrorCounter Counter,
            m3uaSgpSctpSendBuffer                   BufferSize,
            m3uaSgpSctpSendBufferActual             BufferSize,
            m3uaSgpSctpSendLoWat                    BufferSize,
            m3uaSgpSctpSendLoWatActual              BufferSize,
            m3uaSgpSctpRecvBuffer                   BufferSize,
            m3uaSgpSctpRecvBufferActual             BufferSize,
            m3uaSgpSctpRecvLoWat                    BufferSize,
            m3uaSgpSctpRecvLoWatActual              BufferSize,
            m3uaSgpSctpNoDelay                      Boolean,
            m3uaSgpSctpNoDelayActual                Boolean
        }
        
    m3uaSgpIndex OBJECT-TYPE
        SYNTAX  M3uaSgpTableIndex
        ACCESS  read-write
        STATUS  mandatory
        DESCRIPTION
            "Index of entry in M3UA SGP table."
        ::= { m3uaSgpEntry 1 }

    m3uaSgpAdminState OBJECT-TYPE
        SYNTAX  AdminState
        ACCESS  read-write
        STATUS  mandatory
        DESCRIPTION
            "Administrative state of the M3UA SGP."
        ::= { m3uaSgpEntry 2 }

    m3uaSgpOperationalState OBJECT-TYPE
        SYNTAX  M3uaSgpOperationalState
        ACCESS  read-write
        STATUS  mandatory
        DESCRIPTION
            "Operational state of the M3UA SGP."
        ::= { m3uaSgpEntry 3 }

    m3uaSgpActualSpcOperationalState OBJECT-TYPE
        SYNTAX  M3uaSgpSpcOperationalState
        ACCESS  read-write
        STATUS  mandatory
        DESCRIPTION
            "Operational state of the M3UA SGP for the actual SPC of TextPass."
        ::= { m3uaSgpEntry 4 }

    m3uaSgpVirtualSpcOperationalState OBJECT-TYPE
        SYNTAX  M3uaSgpSpcOperationalState
        ACCESS  read-write
        STATUS  mandatory
        DESCRIPTION
            "Operational state of the M3UA SGP for the virtual SPC of TextPass."
        ::= { m3uaSgpEntry 5 }

    m3uaSgpName OBJECT-TYPE
        SYNTAX  NameString
        ACCESS  read-write
        STATUS  mandatory
        DESCRIPTION
            "Name of M3UA SGP."
        ::= { m3uaSgpEntry 6 }

    m3uaSgpUseForActualSpc OBJECT-TYPE
        SYNTAX  Boolean
        ACCESS  read-write
        STATUS  mandatory
        DESCRIPTION
            "Identifier specifying whether this association is used for the 
            actual SPC. Default is 'true'."
        ::= { m3uaSgpEntry 11 }

    m3uaSgpUseForVirtualSpc OBJECT-TYPE
        SYNTAX  Boolean
        ACCESS  read-write
        STATUS  mandatory
        DESCRIPTION
            "Identifier specifying whether this association is used for the 
            virtual SPC. Default is 'true'."
        ::= { m3uaSgpEntry 12 }

    m3uaSgpFillInAspIdentifierField OBJECT-TYPE
        SYNTAX  Boolean
        ACCESS  read-write
        STATUS  mandatory
        DESCRIPTION
            "Identifier specifying whether TextPass includes ASP Identifier in 
            ASP UP message towards M3UA SGP. When set to 'true', the field is 
            always specified. When set to to 'false', the field in never 
            specified. Default is 'true'."
        ::= { m3uaSgpEntry 13 }

    m3uaSgpFillInRoutingContextField OBJECT-TYPE
        SYNTAX  Boolean
        ACCESS  read-write
        STATUS  mandatory
        DESCRIPTION
            "Identifier specifying whether TextPass includes Routing Context in 
            messages towards M3UA SGP. When set to 'true', the field is always 
            specified. When set to to 'false', the field in never specified. 
            Default is 'true'. This setting only has effect when only one SPC 
            is enabled for the SGP. If both, the actual SPC and virtual SPC, 
            are enabled, the Routing Context is always included."
        ::= { m3uaSgpEntry 14 }

    m3uaSgpFillInNetworkAppearanceField OBJECT-TYPE
        SYNTAX  Boolean
        ACCESS  read-write
        STATUS  mandatory
        DESCRIPTION
            "Identifier specifying whether TextPass includes Network Appearance
            in messages towards M3UA SGP. When set to 'true', the field is always 
            specified. When set to to 'false', the field in never specified. 
            Default is 'false'."
        ::= { m3uaSgpEntry 15 }

    m3uaSgpTrafficModeField OBJECT-TYPE
        SYNTAX  M3uaSgpTrafficMode
        ACCESS  read-write
        STATUS  mandatory
        DESCRIPTION
            "Determines the traffic mode to advertise in the ASP_AC
            message. A value of 0 (unconfigured) means not to advertise
            a traffic mode. The textpass system will always employ
            loadshare mode, independent of this setting."
        ::= { m3uaSgpEntry 16 }

    m3uaSgpSctpLocalPort OBJECT-TYPE
        SYNTAX  SctpPort
        ACCESS  read-write
        STATUS  mandatory
        DESCRIPTION
            "Local SCTP port for the SCTP association that TextPass maintains 
            with the remote M3UA SGP. Default is 2905."
        ::= { m3uaSgpEntry 21 }

    m3uaSgpSctpRemotePort OBJECT-TYPE
        SYNTAX  SctpPort
        ACCESS  read-write
        STATUS  mandatory
        DESCRIPTION
            "Remote SCTP port for the SCTP association that TextPass maintains 
            with the remote M3UA SGP. Default is 2905."
        ::= { m3uaSgpEntry 22 }

    m3uaSgpSctpMaxOutboundPduSize OBJECT-TYPE
        SYNTAX  SctpMaxPduSize
        ACCESS  read-write
        STATUS  mandatory
        DESCRIPTION
            "Maximum outbound PDU size for the SCTP association that TextPass 
            maintains with the remote M3UA SGP. Default is 1500."
        ::= { m3uaSgpEntry 23 }

    m3uaSgpSctpMaxInboundPduSize OBJECT-TYPE
        SYNTAX  SctpMaxPduSize
        ACCESS  read-write
        STATUS  mandatory
        DESCRIPTION
            "Maximum inbound PDU size for the SCTP association that TextPass 
            maintains with the remote M3UA SGP. Default is 1500."
        ::= { m3uaSgpEntry 24 }

    m3uaSgpSctpTimerT1Init OBJECT-TYPE
        SYNTAX  SctpTimerT1Init
        ACCESS  read-write
        STATUS  mandatory
        DESCRIPTION
            "Value for T1-init timer for the SCTP association that TextPass 
            maintains with the remote M3UA SGP, expressed in units of 
            milliseconds. Default is 3000."
        ::= { m3uaSgpEntry 25 }

    m3uaSgpSctpTimerT3Rtx OBJECT-TYPE
        SYNTAX  SctpTimerT3Rtx
        ACCESS  read-write
        STATUS  mandatory
        DESCRIPTION
            "Value for T3-rtx timer for the SCTP association that TextPass 
            maintains with the remote M3UA SGP, expressed in units of 
            milliseconds. Default is 2000."
        ::= { m3uaSgpEntry 26 }

    m3uaSgpSctpTimerHeartbeat OBJECT-TYPE
        SYNTAX  SctpTimerHeartbeat
        ACCESS  read-write
        STATUS  mandatory
        DESCRIPTION
            "SCTP heartbeat interval for the SCTP association that TextPass 
            maintains with the remote M3UA SGP, expressed in units of 
            milliseconds. Default is 1000."
        ::= { m3uaSgpEntry 27 }

    m3uaSgpSctpTimerT1Cookie OBJECT-TYPE
        SYNTAX  SctpTimerT1Cookie
        ACCESS  read-write
        STATUS  mandatory
        DESCRIPTION
            "Value for T1-cookie timer for the SCTP association that TextPass 
            maintains with the remote M3UA SGP, expressed in units of 
            milliseconds. Default is 3000."
        ::= { m3uaSgpEntry 28 }

    m3uaSgpSctpMaxRetransmitTimeout OBJECT-TYPE
        SYNTAX  SctpRetransmitTimeout
        ACCESS  read-write
        STATUS  mandatory
        DESCRIPTION
            "Maximum value of the dynamic retransmit timer (RTO.max) for the 
            SCTP association that TextPass maintains with the remote M3UA SGP, 
            expressed in units of milliseconds. Default is 2000." 

        ::= { m3uaSgpEntry 29 }

    m3uaSgpSctpMaxPathRetransmits OBJECT-TYPE
        SYNTAX  SctpRetransmits
        ACCESS  read-write
        STATUS  mandatory
        DESCRIPTION
            "Maximum number of path retries (Path.Max.Retrans) for the SCTP
            association that TextPass maintains with the remote M3UA SGP.
            Default is 15." 
        ::= { m3uaSgpEntry 30 }

    m3uaSgpSctpMaxAssociationRetransmits OBJECT-TYPE
        SYNTAX  SctpRetransmits
        ACCESS  read-write
        STATUS  mandatory
        DESCRIPTION
            "Maximum number of association retries (Association.Max.Retrans) for 
            the SCTP association that TextPass maintains with the remote M3UA 
            SGP. Default is 20." 
        ::= { m3uaSgpEntry 31 }

    m3uaSgpSctpMaxConnectAttempts OBJECT-TYPE
        SYNTAX  SctpMaxConnectAttempts
        ACCESS  read-write
        STATUS  mandatory
        DESCRIPTION
            "Maximum number of connect attempts (Max.Init.Retransmits) for 
            the SCTP association that TextPass maintains with the remote M3UA 
            SGP. Default is 8."         
        ::= { m3uaSgpEntry 32 }

    m3uaSgpSctpMaxAllowedInboundStreams OBJECT-TYPE
        SYNTAX  SctpStreams
        ACCESS  read-write
        STATUS  mandatory
        DESCRIPTION
            "Maximum number of inbound streams that TextPass allows for the SCTP
            SCTP association that TextPass maintains with the remote M3UA SGP. 
            Default is 255."         
        ::= { m3uaSgpEntry 33 }

    m3uaSgpSctpPreferredOutboundStreams OBJECT-TYPE
        SYNTAX  SctpStreams
        ACCESS  read-write
        STATUS  mandatory
        DESCRIPTION
            "Number of outbound streams that TextPass prefers for the SCTP
            SCTP association that TextPass maintains with the remote M3UA SGP. 
            Default is 2."         
        ::= { m3uaSgpEntry 34 }

    m3uaSgpSctpInitiatingStartupEnabled OBJECT-TYPE
        SYNTAX  Boolean
        ACCESS  read-write
        STATUS  mandatory
        DESCRIPTION
            "Identifier specifying whether TextPass should initiate 
            establishment of SCTP association. When set to 'true', TextPass
            actively tries to establish the association by sending out INIT
            chunks and responding with INIT ACK chunks when receiving INIT
            chunks. When set to 'false', TextPass has a passive role, meaning
            that it will only respond to inbound INIT chunks. Default is 
            'true'."
        ::= { m3uaSgpEntry 35 }

    m3uaSgpSctpLocalSendPort OBJECT-TYPE
        SYNTAX  SctpPort
        ACCESS  read-write
        STATUS  mandatory
        DESCRIPTION
            "Local SCTP port for the outgoing SCTP association that TextPass maintains 
            with the remote M3UA SGP. Default is 0, which means chosen by the system."
        ::= { m3uaSgpEntry 36 }

    m3uaSgpSctpRemoteSendPort OBJECT-TYPE
        SYNTAX  SctpPort
        ACCESS  read-write
        STATUS  mandatory
        DESCRIPTION
            "Remote SCTP port for the incoming SCTP association that TextPass maintains 
            with the remote M3UA SGP. Default is 0, which means it is not checked."
        ::= { m3uaSgpEntry 37 }

    m3uaSgpSctpSackDelay OBJECT-TYPE
        SYNTAX  SctpSackDelay
        ACCESS  read-write
        STATUS  mandatory
        DESCRIPTION
            "Time (in ms) to wait before acknowledging SCTP DATA chunks. A
            value of 0 (default) means use the system default, which tends
            to be 200ms. This setting only has an effect for newly created
            SCTP associations, and only when running on Linux/TPD. On
            Solaris, this setting is ignored."
        ::= { m3uaSgpEntry 38 }

    m3uaSgpSctpOperationalState OBJECT-TYPE
        SYNTAX  SctpOperationalState
        ACCESS  read-write
        STATUS  mandatory
        DESCRIPTION
            "Operation state of the SCTP association that TextPass maintains
            with the remote M3UA SGP."
        ::= { m3uaSgpEntry 41 }

    m3uaSgpSctpNegotiatedInboundStreams OBJECT-TYPE
        SYNTAX  SctpStreams
        ACCESS  read-write
        STATUS  mandatory
        DESCRIPTION
            "Number of inbound streams for the SCTP association that TextPass 
            maintains with the remote M3UA SGP. This number results from the 
            negotiation between TextPass and the remote M3UA SGP."
        ::= { m3uaSgpEntry 42 }

    m3uaSgpSctpNegotiatedOutboundStreams OBJECT-TYPE
        SYNTAX  SctpStreams
        ACCESS  read-write
        STATUS  mandatory
        DESCRIPTION
            "Number of outbound streams for the SCTP association that TextPass 
            maintains with the remote M3UA SGP. This number results from the 
            negotiation between TextPass and the remote M3UA SGP."
        ::= { m3uaSgpEntry 43 }

    m3uaSgpSctpUpTime OBJECT-TYPE
        SYNTAX  Gauge
        ACCESS  read-only
        STATUS  mandatory
        DESCRIPTION
            "Up time, expressed in number of seconds, for the SCTP association 
            that TextPass maintains with the remote M3UA SGP."
        ::= { m3uaSgpEntry 44 }

    m3uaSgpSctpDownTime OBJECT-TYPE
        SYNTAX  Gauge
        ACCESS  read-only
        STATUS  mandatory
        DESCRIPTION
            "Down time, expressed in number of seconds, for the SCTP association 
            that TextPass maintains with the remote M3UA SGP."
        ::= { m3uaSgpEntry 45 }

    m3uaSgpSctpInboundTsn OBJECT-TYPE
        SYNTAX  SctpTsn
        ACCESS  read-write
        STATUS  mandatory
        DESCRIPTION
            "Current value of the Transmission Sequence Number (TSN) for the 
            inbound direction of the association that TextPass maintains with
            the remote M3UA SGP."
        ::= { m3uaSgpEntry 46 }

    m3uaSgpSctpOutboudTsn OBJECT-TYPE
        SYNTAX  SctpTsn
        ACCESS  read-write
        STATUS  mandatory
        DESCRIPTION
            "Current value of the Transmission Sequence Number (TSN) for the 
            outbound direction of the association that TextPass maintains with
            the remote M3UA SGP."
        ::= { m3uaSgpEntry 47 }

    m3uaSgpSctpTsnCumulativeAck OBJECT-TYPE
        SYNTAX  SctpTsn
        ACCESS  read-write
        STATUS  mandatory
        DESCRIPTION
            "The Transmission Sequence Number (TSN) of the last DATA chunk that 
            the M3UA SGP acknowledged via the Cumulative TSN Ack field of a SACK."
        ::= { m3uaSgpEntry 48 }

    m3uaSgpSctpLocalReceiveWindow OBJECT-TYPE
        SYNTAX  SctpWindowSize
        ACCESS  read-write
        STATUS  mandatory
        DESCRIPTION
            "Current value of the receiver window (rwnd) on TextPass for the 
            association that TextPass maintains with the remote M3UA SGP."
        ::= { m3uaSgpEntry 49 }

    m3uaSgpSctpRemoteReceiveWindow OBJECT-TYPE
        SYNTAX  SctpWindowSize
        ACCESS  read-write
        STATUS  mandatory
        DESCRIPTION
            "Current value of the receiver window (rwnd) on remote M3UA SGP for 
            the association that TextPass maintains with the remote M3UA SGP."
        ::= { m3uaSgpEntry 50 }

    m3uaSgpSctpCongestionWindow OBJECT-TYPE
        SYNTAX  SctpWindowSize
        ACCESS  read-write
        STATUS  mandatory
        DESCRIPTION
            "Current value of the congestion window (cwnd) for the association 
            that TextPass maintains with the remote M3UA SGP."
        ::= { m3uaSgpEntry 51 }

    m3uaSgpSctpRoundTripTime OBJECT-TYPE
        SYNTAX  SctpRoundTripTime
        ACCESS  read-write
        STATUS  mandatory
        DESCRIPTION
            "Current value of the round trip time (RTT) for primary address of 
            the SCTP association that TextPass maintains with the remote M3UA 
            SGP."
        ::= { m3uaSgpEntry 52 }

    m3uaSgpSctpRetransmissionTimeout OBJECT-TYPE
        SYNTAX  SctpRetransmitTimeout
        ACCESS  read-write
        STATUS  mandatory
        DESCRIPTION
            "Current value of the retransmission timeout (RTO) for the primary 
            destination of the SCTP association that TextPass maintains with the 
            remote M3UA SGP."
        ::= { m3uaSgpEntry 53 }

    m3uaSgpSctpSmoothedLinkQuality OBJECT-TYPE
        SYNTAX  SctpSmoothedLinkQuality
        ACCESS  read-write
        STATUS  mandatory
        DESCRIPTION
            "Current value of the smoothed link quality indicator for the 
            primary destination of the SCTP association that TextPass maintains 
            with the remote M3UA SGP. Smoothed link quality is a proprietary 
            measurement that indicates the quality of a path."
        ::= { m3uaSgpEntry 54 }

    m3uaSgpSctpT3RtxBasedRetransmitCounter OBJECT-TYPE
        SYNTAX  Counter
        ACCESS  read-write
        STATUS  mandatory
        DESCRIPTION
            "Counter specifying the number of retransmits resulting from an 
            expiration of T3-rtx timer on the SCTP association that TextPass 
            maintains with the remote M3UA SGP." 
        ::= { m3uaSgpEntry 55 }

    m3uaSgpSctpSackBasedRetransmitCounter OBJECT-TYPE
        SYNTAX  Counter
        ACCESS  read-write
        STATUS  mandatory
        DESCRIPTION
            "Counter specifying the number of retransmits resulting from errors 
            reported by a SACK chunk on the SCTP association that TextPass 
            maintains with the remote M3UA SGP." 
        ::= { m3uaSgpEntry 56 }

    m3uaSgpSctpDataChunkRetransmitCounter OBJECT-TYPE
        SYNTAX  Counter
        ACCESS  read-write
        STATUS  mandatory
        DESCRIPTION
            "Counter specifying the number of DATA chunks retransmits on the 
            SCTP association that TextPass maintains with the remote M3UA SGP."
        ::= { m3uaSgpEntry 57 }

    m3uaSgpSctpPrimaryChangeOverCounter OBJECT-TYPE
        SYNTAX  Counter
        ACCESS  read-write
        STATUS  mandatory
        DESCRIPTION
            "Counter specifying the number of primary path changeovers on the 
            SCTP association that TextPass maintains with the remote M3UA SGP."
        ::= { m3uaSgpEntry 58 }

    m3uaSgpSctpSentDataByteCounter OBJECT-TYPE
        SYNTAX  Counter
        ACCESS  read-write
        STATUS  mandatory
        DESCRIPTION
            "Counter specifying the number of data bytes sent on the SCTP 
            association that TextPass maintains with the remote M3UA SGP."
        ::= { m3uaSgpEntry 71 }

    m3uaSgpSctpRecvDataByteCounter OBJECT-TYPE
        SYNTAX  Counter
        ACCESS  read-write
        STATUS  mandatory
        DESCRIPTION
            "Counter specifying the number of data bytes received on the SCTP 
            association that TextPass maintains with the remote M3UA SGP."
        ::= { m3uaSgpEntry 72 }

    m3uaSgpSctpSentSackWithGapCounter OBJECT-TYPE
        SYNTAX  Counter
        ACCESS  read-write
        STATUS  mandatory
        DESCRIPTION
            "Counter specifying the number of SACK chunks sent with a gap on the 
            SCTP association that TextPass maintains with the remote M3UA SGP."
        ::= { m3uaSgpEntry 73 }

    m3uaSgpSctpRecvSackWithGapCounter OBJECT-TYPE
        SYNTAX  Counter
        ACCESS  read-write
        STATUS  mandatory
        DESCRIPTION
            "Counter specifying the number of SACK chunks received with a gap on  
            the SCTP association that TextPass maintains with the remote M3UA 
            SGP."
        ::= { m3uaSgpEntry 74 }

    m3uaSgpSctpRecvDataChunkDiscardedCounter OBJECT-TYPE
        SYNTAX  Counter
        ACCESS  read-write
        STATUS  mandatory
        DESCRIPTION
            "Counter specifying the number of received DATA chunks that have 
            been discarded for the SCTP association that TextPass maintains with 
            the remote M3UA SGP."
        ::= { m3uaSgpEntry 75 }

    m3uaSgpSctpSentDataChunkDroppedCounter OBJECT-TYPE
        SYNTAX  Counter
        ACCESS  read-write
        STATUS  mandatory
        DESCRIPTION
            "Counter specifying the number of sent DATA chunks that have been 
            dropped for the SCTP association that TextPass maintains with the 
            remote M3UA SGP."
        ::= { m3uaSgpEntry 76 }

    m3uaSgpSctpSentDataChunkCounter OBJECT-TYPE
        SYNTAX  Counter
        ACCESS  read-write
        STATUS  mandatory
        DESCRIPTION
            "Counter specifying the number of DATA chunks sent on the SCTP 
            association that TextPass maintains with the remote M3UA SGP."
        ::= { m3uaSgpEntry 81 }

    m3uaSgpSctpRecvDataChunkCounter OBJECT-TYPE
        SYNTAX  Counter
        ACCESS  read-write
        STATUS  mandatory
        DESCRIPTION
            "Counter specifying the number of DATA chunks received on the SCTP 
            association that TextPass maintains with the remote M3UA SGP."
        ::= { m3uaSgpEntry 82 }

    m3uaSgpSctpSentInitChunkCounter OBJECT-TYPE
        SYNTAX  Counter
        ACCESS  read-write
        STATUS  mandatory
        DESCRIPTION
            "Counter specifying the number of INIT chunks sent on the SCTP 
            association that TextPass maintains with the remote M3UA SGP."
        ::= { m3uaSgpEntry 83 }

    m3uaSgpSctpRecvInitChunkCounter OBJECT-TYPE
        SYNTAX  Counter
        ACCESS  read-write
        STATUS  mandatory
        DESCRIPTION
            "Counter specifying the number of INIT chunks received on the SCTP 
            association that TextPass maintains with the remote M3UA SGP."
        ::= { m3uaSgpEntry 84 }

    m3uaSgpSctpSentInitAckChunkCounter OBJECT-TYPE
        SYNTAX  Counter
        ACCESS  read-write
        STATUS  mandatory
        DESCRIPTION
            "Counter specifying the number of INIT ACK chunks sent on the SCTP 
            association that TextPass maintains with the remote M3UA SGP."
        ::= { m3uaSgpEntry 85 }

    m3uaSgpSctpRecvInitAckChunkCounter OBJECT-TYPE
        SYNTAX  Counter
        ACCESS  read-write
        STATUS  mandatory
        DESCRIPTION
            "Counter specifying the number of INIT ACK chunks received on the  
            SCTP association that TextPass maintains with the remote M3UA SGP."
        ::= { m3uaSgpEntry 86 }

    m3uaSgpSctpSentSackChunkCounter OBJECT-TYPE
        SYNTAX  Counter
        ACCESS  read-write
        STATUS  mandatory
        DESCRIPTION
            "Counter specifying the number of SACK chunks sent on the SCTP 
            association that TextPass maintains with the remote M3UA SGP."
        ::= { m3uaSgpEntry 87 }

    m3uaSgpSctpRecvSackChunkCounter OBJECT-TYPE
        SYNTAX  Counter
        ACCESS  read-write
        STATUS  mandatory
        DESCRIPTION
            "Counter specifying the number of SACK chunks received on the SCTP 
            association that TextPass maintains with the remote M3UA SGP."
        ::= { m3uaSgpEntry 88 }

    m3uaSgpSctpSentHeartbeatCounter OBJECT-TYPE
        SYNTAX  Counter
        ACCESS  read-write
        STATUS  mandatory
        DESCRIPTION
            "Counter specifying the number of HEARTBEAT chunks sent on the SCTP 
            association that TextPass maintains with the remote M3UA SGP."
        ::= { m3uaSgpEntry 89 }

    m3uaSgpSctpRecvHeartbeatCounter OBJECT-TYPE
        SYNTAX  Counter
        ACCESS  read-write
        STATUS  mandatory
        DESCRIPTION
            "Counter specifying the number of HEARTBEAT chunks received on the  
            SCTP association that TextPass maintains with the remote M3UA SGP."
        ::= { m3uaSgpEntry 90 }

    m3uaSgpSctpSentHeartbeatAckCounter OBJECT-TYPE
        SYNTAX  Counter
        ACCESS  read-write
        STATUS  mandatory
        DESCRIPTION
            "Counter specifying the number of HEARTBEAT ACK chunks sent on the 
            SCTP association that TextPass maintains with the remote M3UA SGP."
        ::= { m3uaSgpEntry 91 }

    m3uaSgpSctpRecvHeartbeatAckCounter OBJECT-TYPE
        SYNTAX  Counter
        ACCESS  read-write
        STATUS  mandatory
        DESCRIPTION
            "Counter specifying the number of HEARTBEAT ACK chunks received on 
            the SCTP association that TextPass maintains with the remote M3UA 
            SGP."
        ::= { m3uaSgpEntry 92 }

    m3uaSgpSctpSentAbortChunkCounter OBJECT-TYPE
        SYNTAX  Counter
        ACCESS  read-write
        STATUS  mandatory
        DESCRIPTION
            "Counter specifying the number of ABORT chunks sent on the SCTP 
            association that TextPass maintains with the remote M3UA SGP."
        ::= { m3uaSgpEntry 93 }

    m3uaSgpSctpRecvAbortChunkCounter OBJECT-TYPE
        SYNTAX  Counter
        ACCESS  read-write
        STATUS  mandatory
        DESCRIPTION
            "Counter specifying the number of ABORT chunks received on the  
            SCTP association that TextPass maintains with the remote M3UA SGP."
        ::= { m3uaSgpEntry 94 }

    m3uaSgpSctpSentShutdownChunkCounter OBJECT-TYPE
        SYNTAX  Counter
        ACCESS  read-write
        STATUS  mandatory
        DESCRIPTION
            "Counter specifying the number of SHUTDOWN chunks sent on the SCTP 
            association that TextPass maintains with the remote M3UA SGP."
        ::= { m3uaSgpEntry 95 }

    m3uaSgpSctpRecvShutdownChunkCounter OBJECT-TYPE
        SYNTAX  Counter
        ACCESS  read-write
        STATUS  mandatory
        DESCRIPTION
            "Counter specifying the number of SHUTDOWN chunks received on the  
            SCTP association that TextPass maintains with the remote M3UA SGP."
        ::= { m3uaSgpEntry 96 }

    m3uaSgpSctpSentShutdownAckChunkCounter OBJECT-TYPE
        SYNTAX  Counter
        ACCESS  read-write
        STATUS  mandatory
        DESCRIPTION
            "Counter specifying the number of SHUTDOWN ACK chunks sent on the  
            SCTP association that TextPass maintains with the remote M3UA SGP."
        ::= { m3uaSgpEntry 97 }

    m3uaSgpSctpRecvShutdownAckChunkCounter OBJECT-TYPE
        SYNTAX  Counter
        ACCESS  read-write
        STATUS  mandatory
        DESCRIPTION
            "Counter specifying the number of SHUTDOWN ACK chunks received on   
            the SCTP association that TextPass maintains with the remote M3UA 
            SGP."
        ::= { m3uaSgpEntry 98 }

    m3uaSgpSctpSentErrorChunkCounter OBJECT-TYPE
        SYNTAX  Counter
        ACCESS  read-write
        STATUS  mandatory
        DESCRIPTION
            "Counter specifying the number of ERROR chunks sent on the SCTP 
            association that TextPass maintains with the remote M3UA SGP."
        ::= { m3uaSgpEntry 99 }

    m3uaSgpSctpRecvErrorChunkCounter OBJECT-TYPE
        SYNTAX  Counter
        ACCESS  read-write
        STATUS  mandatory
        DESCRIPTION
            "Counter specifying the number of ERROR chunks received on the SCTP 
            association that TextPass maintains with the remote M3UA SGP."
        ::= { m3uaSgpEntry 100 }

    m3uaSgpSctpSentCookieEchoChunkCounter OBJECT-TYPE
        SYNTAX  Counter
        ACCESS  read-write
        STATUS  mandatory
        DESCRIPTION
            "Counter specifying the number of COOKIE ECHO chunks sent on the  
            SCTP association that TextPass maintains with the remote M3UA SGP."
        ::= { m3uaSgpEntry 101 }

    m3uaSgpSctpRecvCookieEchoChunkCounter OBJECT-TYPE
        SYNTAX  Counter
        ACCESS  read-write
        STATUS  mandatory
        DESCRIPTION
            "Counter specifying the number of COOKIE ECHO chunks received on the  
            SCTP association that TextPass maintains with the remote M3UA SGP."
        ::= { m3uaSgpEntry 102 }

    m3uaSgpSctpSentCookieAckChunkCounter OBJECT-TYPE
        SYNTAX  Counter
        ACCESS  read-write
        STATUS  mandatory
        DESCRIPTION
            "Counter specifying the number of COOKIE ACK chunks sent on the SCTP 
            association that TextPass maintains with the remote M3UA SGP."
        ::= { m3uaSgpEntry 103 }

    m3uaSgpSctpRecvCookieAckChunkCounter OBJECT-TYPE
        SYNTAX  Counter
        ACCESS  read-write
        STATUS  mandatory
        DESCRIPTION
            "Counter specifying the number of COOKIE ACK chunks received on the  
            SCTP association that TextPass maintains with the remote M3UA SGP."
        ::= { m3uaSgpEntry 104 }

    m3uaSgpSctpSentShutdownCompleteChunkCounter OBJECT-TYPE
        SYNTAX  Counter
        ACCESS  read-write
        STATUS  mandatory
        DESCRIPTION
            "Counter specifying the number of SHUTDOWN COMPLETE chunks sent on 
            the SCTP association that TextPass maintains with the remote M3UA SGP."
        ::= { m3uaSgpEntry 105 }

    m3uaSgpSctpRecvShutdownCompleteChunkCounter OBJECT-TYPE
        SYNTAX  Counter
        ACCESS  read-write
        STATUS  mandatory
        DESCRIPTION
            "Counter specifying the number of SHUTDOWN COMPLETE chunks received 
            on the SCTP association that TextPass maintains with the remote M3UA 
            SGP."
        ::= { m3uaSgpEntry 106 }

    m3uaSgpSctpInvalidStreamIdErrorCounter OBJECT-TYPE
        SYNTAX  Counter
        ACCESS  read-write
        STATUS  mandatory
        DESCRIPTION
            "Counter specifying the number of 'Invalid Stream Id' ERROR chunks 
            received on the SCTP association that TextPass maintains with the 
            remote M3UA SGP."
        ::= { m3uaSgpEntry 121 }

    m3uaSgpSctpMissingMandatoryParameterErrorCounter OBJECT-TYPE
        SYNTAX  Counter
        ACCESS  read-write
        STATUS  mandatory
        DESCRIPTION
            "Counter specifying the number of 'Missing Mandatory Parameter' 
            ERROR chunks received on the SCTP association that TextPass 
            maintains with the remote M3UA SGP."
        ::= { m3uaSgpEntry 122 }

    m3uaSgpSctpStaleCookieErrorCounter OBJECT-TYPE
        SYNTAX  Counter
        ACCESS  read-write
        STATUS  mandatory
        DESCRIPTION
            "Counter specifying the number of 'Stale Cookie' ERROR chunks 
            received on the SCTP association that TextPass maintains with the 
            remote M3UA SGP."
        ::= { m3uaSgpEntry 123 }

    m3uaSgpSctpOutOfResourceErrorCounter OBJECT-TYPE
        SYNTAX  Counter
        ACCESS  read-write
        STATUS  mandatory
        DESCRIPTION
            "Counter specifying the number of 'Out Of Resource' ERROR chunks 
            received on the SCTP association that TextPass maintains with the 
            remote M3UA SGP."
        ::= { m3uaSgpEntry 124 }

    m3uaSgpSctpUnresolvableAddressErrorCounter OBJECT-TYPE
        SYNTAX  Counter
        ACCESS  read-write
        STATUS  mandatory
        DESCRIPTION
            "Counter specifying the number of 'Unresolvable Address' ERROR 
            chunks received on the SCTP association that TextPass maintains with 
            the remote M3UA SGP."
        ::= { m3uaSgpEntry 125 }

    m3uaSgpSctpUnrecognisedChunkTypeErrorCounter OBJECT-TYPE
        SYNTAX  Counter
        ACCESS  read-write
        STATUS  mandatory
        DESCRIPTION
            "Counter specifying the number of 'Unrecognised Chunk Type' ERROR 
            chunks received on the SCTP association that TextPass maintains with 
            the remote M3UA SGP."
        ::= { m3uaSgpEntry 126 }

    m3uaSgpSctpInvalidMandatoryParameterErrorCounter OBJECT-TYPE
        SYNTAX  Counter
        ACCESS  read-write
        STATUS  mandatory
        DESCRIPTION
            "Counter specifying the number of 'Invalid Mandatory Parameter' 
            ERROR chunks received on the SCTP association that TextPass 
            maintains with the remote M3UA SGP."
        ::= { m3uaSgpEntry 127 }

    m3uaSgpSctpUnrecognisedParamtersErrorCounter OBJECT-TYPE
        SYNTAX  Counter
        ACCESS  read-write
        STATUS  mandatory
        DESCRIPTION
            "Counter specifying the number of 'Unrecognised Parameters' ERROR
            chunks received on the SCTP association that TextPass maintains with 
            the remote M3UA SGP."
        ::= { m3uaSgpEntry 128 }

    m3uaSgpSctpNoUserDataErrorCounter OBJECT-TYPE
        SYNTAX  Counter
        ACCESS  read-write
        STATUS  mandatory
        DESCRIPTION
            "Counter specifying the number of 'No User Data' ERROR chunks 
            received on the SCTP association that TextPass maintains with 
            the remote M3UA SGP."
        ::= { m3uaSgpEntry 129 }

    m3uaSgpSctpCookieRecvWhileShuttingDownErrorCounter OBJECT-TYPE
        SYNTAX  Counter
        ACCESS  read-write
        STATUS  mandatory
        DESCRIPTION
            "Counter specifying the number of 'Cookie Received While Shutting 
            Down' ERROR chunks received on the SCTP association that TextPass 
            maintains with the remote M3UA SGP."
        ::= { m3uaSgpEntry 130 }

    m3uaSgpSctpSendBuffer OBJECT-TYPE
        SYNTAX  BufferSize
        ACCESS  read-write
        STATUS  mandatory
        DESCRIPTION
            "Requested size of the local send buffer in bytes. 
            The default value is 0, which means to use the OS default. 
            Note that the OS may have a maximum size, 
            which can not be exceeded without changing system wide settings.
            This option has no effect on Solaris 8."
        ::= { m3uaSgpEntry 141 }

    m3uaSgpSctpSendBufferActual OBJECT-TYPE
        SYNTAX  BufferSize
        ACCESS  read-only
        STATUS  mandatory
        DESCRIPTION
            "Actual size of the local send buffer in bytes. 
            Some rounding may be applied compared to the requested setting,
            and a ceiling may be enforced by the OS.
            This option has no effect on Solaris 8."
        ::= { m3uaSgpEntry 142 }

    m3uaSgpSctpSendLoWat OBJECT-TYPE
        SYNTAX  BufferSize
        ACCESS  read-write
        STATUS  mandatory
        DESCRIPTION
            "Requested low water mark of the local send buffer in bytes. 
            The default value is 0, which means to use the OS default. 
            This value has to be lower than the send buffer size. 
            Usually a value between 10% and 25% is recommended.
            This option has no effect on Solaris 8."
        ::= { m3uaSgpEntry 143 }

    m3uaSgpSctpSendLoWatActual OBJECT-TYPE
        SYNTAX  BufferSize
        ACCESS  read-only
        STATUS  mandatory
        DESCRIPTION
            "Actual low water mark of the local send buffer in bytes. 
            This option has no effect on Solaris 8."
        ::= { m3uaSgpEntry 144 }

    m3uaSgpSctpRecvBuffer OBJECT-TYPE
        SYNTAX  BufferSize
        ACCESS  read-write
        STATUS  mandatory
        DESCRIPTION
            "Requested size of the local recv buffer in bytes. 
            The default value is 0, which means to use the OS default. 
            Note that the OS may have a maximum size, 
            which can not be exceeded without changing system wide settings.
            This option has no effect on Solaris 8."
        ::= { m3uaSgpEntry 145 }

    m3uaSgpSctpRecvBufferActual OBJECT-TYPE
        SYNTAX  BufferSize
        ACCESS  read-only
        STATUS  mandatory
        DESCRIPTION
            "Actual size of the local recv buffer in bytes. 
            Some rounding may be applied compared to the requested setting,
            and a ceiling may be enforced by the OS.
            This option has no effect on Solaris 8."
        ::= { m3uaSgpEntry 146 }

    m3uaSgpSctpRecvLoWat OBJECT-TYPE
        SYNTAX  BufferSize
        ACCESS  read-write
        STATUS  mandatory
        DESCRIPTION
            "Requested low water mark of the local receive buffer in bytes. 
            The default value is 0, which means to use the OS default. 
            This value has to be lower than the receive buffer size. 
            Usually a value between 10% and 25% is recommended.
            This option has no effect on Solaris 8."
        ::= { m3uaSgpEntry 147 }

    m3uaSgpSctpRecvLoWatActual OBJECT-TYPE
        SYNTAX  BufferSize
        ACCESS  read-only
        STATUS  mandatory
        DESCRIPTION
            "Actual low water mark of the local receive buffer in bytes. 
            This option has no effect on Solaris 8."
        ::= { m3uaSgpEntry 148 }

    m3uaSgpSctpNoDelay OBJECT-TYPE
        SYNTAX  Boolean
        ACCESS  read-write
        STATUS  mandatory
        DESCRIPTION
            "Requested setting of the NO DELAY flag. 
            Setting this flags disables the Nagle algorithm.
            The Nagle algorithm may reduce the network load on 
            high latency low throughput connections by delaying and
            bundling small messages into one network packet.
            The messages are only delayed until the aknowledgement
            of the previous packet is received 
            (or until a full packet can be send).
            Disabling the Nagle algorithm may reduce latency slightly on
            high latency low throughput connections, at the expense
            of an increased network load. 
            However, disabling the Nagle algorithm is no guarantee that
            no bundling is performed.
            The default is false, which means to use the Nagle algorithm.
            This option has no effect on Solaris 8,
            because Solaris 8 does not support bundling of SCTP messages."
        ::= { m3uaSgpEntry 149 }

    m3uaSgpSctpNoDelayActual OBJECT-TYPE
        SYNTAX  Boolean
        ACCESS  read-only
        STATUS  mandatory
        DESCRIPTION
            "Actual setting of the NO DELAY flag.
            This option has no effect on Solaris 8,
            because Solaris 8 does not support bundling of SCTP messages."
        ::= { m3uaSgpEntry 150 }

    -- the M3UA SGP remote IP address table

    m3uaSgpRemoteAddressTable OBJECT-TYPE
        SYNTAX  SEQUENCE OF M3uaSgpRemoteAddressEntry
        ACCESS  not-accessible
        STATUS  mandatory
        DESCRIPTION
            "Table containing info about IP addresses of remote M3UA Application 
            Servers Processes (ASP's)."
        ::= { m3ua 12 }

    m3uaSgpRemoteAddressEntry OBJECT-TYPE
        SYNTAX  M3uaSgpRemoteAddressEntry
        ACCESS  not-accessible
        STATUS  mandatory
        DESCRIPTION
            "Entry of table containing info about IP addresses of remote M3UA 
            Signalling Gateways Processes (ASP's)."
        INDEX   { m3uaSgpIndex, m3uaSgpRemoteAddressIndex }
        ::= { m3uaSgpRemoteAddressTable 1 }

    M3uaSgpRemoteAddressEntry ::=
        SEQUENCE {
            m3uaSgpRemoteAddressIndex               M3uaRemoteAddressTableIndex,
            m3uaSgpRemoteAddressAdminState          AdminState,
            m3uaSgpRemoteAddressOperationalState    RemoteAddressOperationalState,
            m3uaSgpRemoteAddressSpec                IpAddressSpec,
            m3uaSgpRemoteAddressSctpErrorCounter    Counter,
            m3uaSgpRemoteAddressSctpSentHeartbeatCounter Counter,
            m3uaSgpRemoteAddressSctpRecvHeartbeatCounter Counter,
            m3uaSgpRemoteAddressSctpSentHeartbeatAckCounter Counter,
            m3uaSgpRemoteAddressSctpRecvHeartbeatAckCounter Counter,
            m3uaSgpRemoteAddressSctpRoundTripTime   SctpRoundTripTime,
            m3uaSgpRemoteAddressSctpRetransmissionTimeout SctpRetransmitTimeout,
            m3uaSgpRemoteAddressSctpSmoothedLinkQuality SctpSmoothedLinkQuality
        }    

    m3uaSgpRemoteAddressIndex OBJECT-TYPE
        SYNTAX  M3uaRemoteAddressTableIndex
        ACCESS  read-write
        STATUS  mandatory
        DESCRIPTION
            "Index of entry in table with IP addresses for remote M3UA SGP."
        ::= { m3uaSgpRemoteAddressEntry 1 }

    m3uaSgpRemoteAddressAdminState OBJECT-TYPE
        SYNTAX  AdminState
        ACCESS  read-write
        STATUS  mandatory
        DESCRIPTION
            "Administrative state of IP address of remote M3UA SGP."
        ::= { m3uaSgpRemoteAddressEntry 2 }

    m3uaSgpRemoteAddressOperationalState OBJECT-TYPE
        SYNTAX  RemoteAddressOperationalState
        ACCESS  read-write
        STATUS  mandatory
        DESCRIPTION
            "Operational state of IP address of remote M3UA SGP."
        ::= { m3uaSgpRemoteAddressEntry 3 }

    m3uaSgpRemoteAddressSpec OBJECT-TYPE
        SYNTAX  IpAddressSpec
        ACCESS  read-write
        STATUS  mandatory
        DESCRIPTION
            "IPv4 or IPv6 specification for IP address of remote M3UA SGP."
        ::= { m3uaSgpRemoteAddressEntry 11 }

    m3uaSgpRemoteAddressSctpErrorCounter OBJECT-TYPE
        SYNTAX  Counter
        ACCESS  read-write
        STATUS  mandatory
        DESCRIPTION
            "Counter specifying number of SCTP errors for IP address of
            remote M3UA SGP."
        ::= { m3uaSgpRemoteAddressEntry 21 }

    m3uaSgpRemoteAddressSctpSentHeartbeatCounter OBJECT-TYPE
        SYNTAX  Counter
        ACCESS  read-write
        STATUS  mandatory
        DESCRIPTION
            "Counter specifying the number of HEARTBEAT chunks sent to IP 
            address of remote M3UA SGP."
        ::= { m3uaSgpRemoteAddressEntry 31 }

    m3uaSgpRemoteAddressSctpRecvHeartbeatCounter OBJECT-TYPE
        SYNTAX  Counter
        ACCESS  read-write
        STATUS  mandatory
        DESCRIPTION
            "Counter specifying the number of HEARTBEAT chunks received from IP 
            address of remote M3UA SGP."
        ::= { m3uaSgpRemoteAddressEntry 32 }

    m3uaSgpRemoteAddressSctpSentHeartbeatAckCounter OBJECT-TYPE
        SYNTAX  Counter
        ACCESS  read-write
        STATUS  mandatory
        DESCRIPTION
            "Counter specifying the number of HEARTBEAT ACK chunks sent to IP
            address of remote M3UA SGP."
        ::= { m3uaSgpRemoteAddressEntry 33 }

    m3uaSgpRemoteAddressSctpRecvHeartbeatAckCounter OBJECT-TYPE
        SYNTAX  Counter
        ACCESS  read-write
        STATUS  mandatory
        DESCRIPTION
            "Counter specifying the number of HEARTBEAT ACK chunks received from
            IP address of remote M3UA SGP."
        ::= { m3uaSgpRemoteAddressEntry 34 }

    m3uaSgpRemoteAddressSctpRoundTripTime OBJECT-TYPE
        SYNTAX  SctpRoundTripTime
        ACCESS  read-write
        STATUS  mandatory
        DESCRIPTION
            "Current value of the round trip time (RTT) for IP address of remote 
            M3UA SGP."
        ::= { m3uaSgpRemoteAddressEntry 41 }

    m3uaSgpRemoteAddressSctpRetransmissionTimeout OBJECT-TYPE
        SYNTAX  SctpRetransmitTimeout
        ACCESS  read-write
        STATUS  mandatory
        DESCRIPTION
            "Current value of the retransmission timeout (RTO) for the IP  
            address of remote M3UA SGP."
        ::= { m3uaSgpRemoteAddressEntry 42 }

    m3uaSgpRemoteAddressSctpSmoothedLinkQuality OBJECT-TYPE
        SYNTAX  SctpSmoothedLinkQuality
        ACCESS  read-write
        STATUS  mandatory
        DESCRIPTION
            ""
        ::= { m3uaSgpRemoteAddressEntry 43 }

    -- the M3UA ASP table
    
    m3uaAspTable OBJECT-TYPE
        SYNTAX  SEQUENCE OF M3uaAspEntry
        ACCESS  not-accessible
        STATUS  mandatory
        DESCRIPTION
            "Table containing info about remote M3UA Application Server 
            Processes (ASP)."
        ::= { m3ua 21 }

    m3uaAspEntry OBJECT-TYPE
        SYNTAX  M3uaAspEntry
        ACCESS  not-accessible
        STATUS  mandatory
        DESCRIPTION
            "Entry of table containing info about remote M3UA Application Server 
            Processes (ASP)."
        INDEX   { m3uaAspIndex }
        ::= { m3uaAspTable 1 }

    M3uaAspEntry ::=
        SEQUENCE {
            m3uaAspIndex                            M3uaAspTableIndex,
            m3uaAspAdminState                       AdminState,
            m3uaAspOperationalState                 M3uaAspOperationalState,
            m3uaAspName                             NameString,
            m3uaAspAspIdentifier                    AspIdentifier,
            m3uaAspFillInRoutingContextField        Boolean,
            m3uaAspFillInNetworkAppearanceField     Boolean, 
            m3uaAspSctpLocalPort                    SctpPort,
            m3uaAspSctpRemotePort                   SctpPort,
            m3uaAspSctpMaxOutboundPduSize           SctpMaxPduSize,
            m3uaAspSctpMaxInboundPduSize            SctpMaxPduSize,
            m3uaAspSctpTimerT1Init                  SctpTimerT1Init,
            m3uaAspSctpTimerT3Rtx                   SctpTimerT3Rtx,
            m3uaAspSctpTimerHeartbeat               SctpTimerHeartbeat,
            m3uaAspSctpTimerT1Cookie                SctpTimerT1Cookie,
            m3uaAspSctpMaxRetransmitTimeout         SctpRetransmitTimeout,
            m3uaAspSctpMaxPathRetransmits           SctpRetransmits,
            m3uaAspSctpMaxAssociationRetransmits    SctpRetransmits,
            m3uaAspSctpMaxConnectAttempts           SctpMaxConnectAttempts,
            m3uaAspSctpMaxAllowedInboundStreams     SctpStreams,
            m3uaAspSctpPreferredOutboundStreams     SctpStreams,
            m3uaAspSctpInitiatingStartupEnabled     Boolean,
            m3uaAspSctpSackDelay                    SctpSackDelay,
            m3uaAspSctpOperationalState             SctpOperationalState,
            m3uaAspSctpNegotiatedInboundStreams     SctpStreams,
            m3uaAspSctpNegotiatedOutboundStreams    SctpStreams,
            m3uaAspSctpUpTime                       Gauge,
            m3uaAspSctpDownTime                     Gauge,
            m3uaAspSctpInboundTsn                   SctpTsn,
            m3uaAspSctpOutboudTsn                   SctpTsn,
            m3uaAspSctpTsnCumulativeAck             SctpTsn,
            m3uaAspSctpLocalReceiveWindow           SctpWindowSize,
            m3uaAspSctpRemoteReceiveWindow          SctpWindowSize,
            m3uaAspSctpCongestionWindow             SctpWindowSize,
            m3uaAspSctpRoundTripTime                SctpRoundTripTime,
            m3uaAspSctpRetransmissionTimeout        SctpRetransmitTimeout,
            m3uaAspSctpSmoothedLinkQuality          SctpSmoothedLinkQuality,
            m3uaAspSctpT3RtxBasedRetransmitCounter  Counter,
            m3uaAspSctpSackBasedRetransmitCounter   Counter,
            m3uaAspSctpDataChunkRetransmitCounter   Counter,
            m3uaAspSctpPrimaryChangeOverCounter     Counter,
            m3uaAspSctpSentDataByteCounter          Counter,
            m3uaAspSctpRecvDataByteCounter          Counter,
            m3uaAspSctpSentSackWithGapCounter       Counter,
            m3uaAspSctpRecvSackWithGapCounter       Counter,
            m3uaAspSctpRecvDataChunkDiscardedCounter Counter,
            m3uaAspSctpSentDataChunkDroppedCounter  Counter,
            m3uaAspSctpSentDataChunkCounter         Counter,
            m3uaAspSctpRecvDataChunkCounter         Counter,
            m3uaAspSctpSentInitChunkCounter         Counter,
            m3uaAspSctpRecvInitChunkCounter         Counter,
            m3uaAspSctpSentInitAckChunkCounter      Counter,
            m3uaAspSctpRecvInitAckChunkCounter      Counter,
            m3uaAspSctpSentSackChunkCounter         Counter,
            m3uaAspSctpRecvSackChunkCounter         Counter,
            m3uaAspSctpSentHeartbeatCounter         Counter,
            m3uaAspSctpRecvHeartbeatCounter         Counter,
            m3uaAspSctpSentHeartbeatAckCounter      Counter,
            m3uaAspSctpRecvHeartbeatAckCounter      Counter,
            m3uaAspSctpSentAbortChunkCounter        Counter,
            m3uaAspSctpRecvAbortChunkCounter        Counter,
            m3uaAspSctpSentShutdownChunkCounter     Counter,
            m3uaAspSctpRecvShutdownChunkCounter     Counter,
            m3uaAspSctpSentShutdownAckChunkCounter  Counter,
            m3uaAspSctpRecvShutdownAckChunkCounter  Counter,
            m3uaAspSctpSentErrorChunkCounter        Counter,
            m3uaAspSctpRecvErrorChunkCounter        Counter,
            m3uaAspSctpSentCookieEchoChunkCounter   Counter,
            m3uaAspSctpRecvCookieEchoChunkCounter   Counter,
            m3uaAspSctpSentCookieAckChunkCounter    Counter,
            m3uaAspSctpRecvCookieAckChunkCounter    Counter,
            m3uaAspSctpSentShutdownCompleteChunkCounter Counter,
            m3uaAspSctpRecvShutdownCompleteChunkCounter Counter,
            m3uaAspSctpInvalidStreamIdErrorCounter  Counter,
            m3uaAspSctpMissingMandatoryParameterErrorCounter Counter,
            m3uaAspSctpStaleCookieErrorCounter      Counter,
            m3uaAspSctpOutOfResourceErrorCounter    Counter,
            m3uaAspSctpUnresolvableAddressErrorCounter Counter,
            m3uaAspSctpUnrecognisedChunkTypeErrorCounter Counter,
            m3uaAspSctpInvalidMandatoryParameterErrorCounter Counter,
            m3uaAspSctpUnrecognisedParamtersErrorCounter Counter,
            m3uaAspSctpNoUserDataErrorCounter       Counter,
            m3uaAspSctpCookieRecvWhileShuttingDownErrorCounter Counter
        }
        
    m3uaAspIndex OBJECT-TYPE
        SYNTAX  M3uaAspTableIndex
        ACCESS  read-write
        STATUS  mandatory
        DESCRIPTION
            "Index of entry in M3UA ASP table."
        ::= { m3uaAspEntry 1 }

    m3uaAspAdminState OBJECT-TYPE
        SYNTAX  AdminState
        ACCESS  read-write
        STATUS  mandatory
        DESCRIPTION
            "Administrative state of the M3UA ASP."
        ::= { m3uaAspEntry 2 }

    m3uaAspOperationalState OBJECT-TYPE
        SYNTAX  M3uaAspOperationalState
        ACCESS  read-write
        STATUS  mandatory
        DESCRIPTION
            "Operational state of the M3UA ASP."
        ::= { m3uaAspEntry 3 }

    m3uaAspName OBJECT-TYPE
        SYNTAX  NameString
        ACCESS  read-write
        STATUS  mandatory
        DESCRIPTION
            "Name of M3UA ASP."
        ::= { m3uaAspEntry 4 }

    m3uaAspAspIdentifier OBJECT-TYPE
        SYNTAX  AspIdentifier
        ACCESS  read-write
        STATUS  mandatory
        DESCRIPTION
            "Value of ASP identifier that remote M3UA ASP has sent in its last
            ASP-UP message."
        ::= { m3uaAspEntry 11 }

    m3uaAspFillInRoutingContextField OBJECT-TYPE
        SYNTAX  Boolean
        ACCESS  read-write
        STATUS  mandatory
        DESCRIPTION
            "Identifier specifying whether TextPass includes Routing Context in 
            messages towards M3UA ASP. When set to 'true', the field is always 
            specified. When set to to 'false', the field in never specified. 
            Default is 'true'."
        ::= { m3uaAspEntry 14 }

    m3uaAspFillInNetworkAppearanceField OBJECT-TYPE
        SYNTAX  Boolean
        ACCESS  read-write
        STATUS  mandatory
        DESCRIPTION
            "Identifier specifying whether TextPass includes Network Appearance
            in messages towards M3UA ASP. When set to 'true', the field is always 
            specified. When set to to 'false', the field in never specified. 
            Default is 'false'."
        ::= { m3uaAspEntry 15 }

    m3uaAspSctpLocalPort OBJECT-TYPE
        SYNTAX  SctpPort
        ACCESS  read-write
        STATUS  mandatory
        DESCRIPTION
            "Local SCTP port for the SCTP association that TextPass maintains 
            with the remote M3UA ASP. Default is 14001."
        ::= { m3uaAspEntry 21 }

    m3uaAspSctpRemotePort OBJECT-TYPE
        SYNTAX  SctpPort
        ACCESS  read-write
        STATUS  mandatory
        DESCRIPTION
            "Remote SCTP port for the SCTP association that TextPass maintains 
            with the remote M3UA ASP. Default is 14001."
        ::= { m3uaAspEntry 22 }

    m3uaAspSctpMaxOutboundPduSize OBJECT-TYPE
        SYNTAX  SctpMaxPduSize
        ACCESS  read-write
        STATUS  mandatory
        DESCRIPTION
            "Maximum outbound PDU size for the SCTP association that TextPass 
            maintains with the remote M3UA ASP. Default is 1500."
        ::= { m3uaAspEntry 23 }

    m3uaAspSctpMaxInboundPduSize OBJECT-TYPE
        SYNTAX  SctpMaxPduSize
        ACCESS  read-write
        STATUS  mandatory
        DESCRIPTION
            "Maximum inbound PDU size for the SCTP association that TextPass 
            maintains with the remote M3UA ASP. Default is 1500."
        ::= { m3uaAspEntry 24 }

    m3uaAspSctpTimerT1Init OBJECT-TYPE
        SYNTAX  SctpTimerT1Init
        ACCESS  read-write
        STATUS  mandatory
        DESCRIPTION
            "Value for T1-init timer for the SCTP association that TextPass 
            maintains with the remote M3UA ASP, expressed in units of 
            milliseconds. Default is 3000."
        ::= { m3uaAspEntry 25 }

    m3uaAspSctpTimerT3Rtx OBJECT-TYPE
        SYNTAX  SctpTimerT3Rtx
        ACCESS  read-write
        STATUS  mandatory
        DESCRIPTION
            "Value for T3-rtx timer for the SCTP association that TextPass 
            maintains with the remote M3UA ASP, expressed in units of 
            milliseconds. Default is 2000."
        ::= { m3uaAspEntry 26 }

    m3uaAspSctpTimerHeartbeat OBJECT-TYPE
        SYNTAX  SctpTimerHeartbeat
        ACCESS  read-write
        STATUS  mandatory
        DESCRIPTION
            "SCTP heartbeat interval for the SCTP association that TextPass 
            maintains with the remote M3UA ASP, expressed in units of 
            milliseconds. Default is 1000."
        ::= { m3uaAspEntry 27 }

    m3uaAspSctpTimerT1Cookie OBJECT-TYPE
        SYNTAX  SctpTimerT1Cookie
        ACCESS  read-write
        STATUS  mandatory
        DESCRIPTION
            "Value for T1-cookie timer for the SCTP association that TextPass 
            maintains with the remote M3UA ASP, expressed in units of 
            milliseconds. Default is 3000."
        ::= { m3uaAspEntry 28 }

    m3uaAspSctpMaxRetransmitTimeout OBJECT-TYPE
        SYNTAX  SctpRetransmitTimeout
        ACCESS  read-write
        STATUS  mandatory
        DESCRIPTION
            "Maximum value of the dynamic retransmit timer (RTO.max) for the 
            SCTP association that TextPass maintains with the remote M3UA ASP, 
            expressed in units of milliseconds. Default is 2000." 

        ::= { m3uaAspEntry 29 }

    m3uaAspSctpMaxPathRetransmits OBJECT-TYPE
        SYNTAX  SctpRetransmits
        ACCESS  read-write
        STATUS  mandatory
        DESCRIPTION
            "Maximum number of path retries (Path.Max.Retrans) for the SCTP
            association that TextPass maintains with the remote M3UA ASP.
            Default is 15." 
        ::= { m3uaAspEntry 30 }

    m3uaAspSctpMaxAssociationRetransmits OBJECT-TYPE
        SYNTAX  SctpRetransmits
        ACCESS  read-write
        STATUS  mandatory
        DESCRIPTION
            "Maximum number of association retries (Association.Max.Retrans) for 
            the SCTP association that TextPass maintains with the remote M3UA 
            ASP. Default is 20." 
        ::= { m3uaAspEntry 31 }

    m3uaAspSctpMaxConnectAttempts OBJECT-TYPE
        SYNTAX  SctpMaxConnectAttempts
        ACCESS  read-write
        STATUS  mandatory
        DESCRIPTION
            "Maximum number of connect attempts (Max.Init.Retransmits) for 
            the SCTP association that TextPass maintains with the remote M3UA 
            ASP. Default is 8."         
        ::= { m3uaAspEntry 32 }

    m3uaAspSctpMaxAllowedInboundStreams OBJECT-TYPE
        SYNTAX  SctpStreams
        ACCESS  read-write
        STATUS  mandatory
        DESCRIPTION
            "Maximum number of inbound streams that TextPass allows for the SCTP
            SCTP association that TextPass maintains with the remote M3UA ASP. 
            Default is 255."         
        ::= { m3uaAspEntry 33 }

    m3uaAspSctpPreferredOutboundStreams OBJECT-TYPE
        SYNTAX  SctpStreams
        ACCESS  read-write
        STATUS  mandatory
        DESCRIPTION
            "Number of outbound streams that TextPass prefers for the SCTP
            SCTP association that TextPass maintains with the remote M3UA ASP. 
            Default is 2."         
        ::= { m3uaAspEntry 34 }

    m3uaAspSctpInitiatingStartupEnabled OBJECT-TYPE
        SYNTAX  Boolean
        ACCESS  read-write
        STATUS  mandatory
        DESCRIPTION
            "Identifier specifying whether TextPass should initiate 
            establishment of SCTP association. When set to 'true', TextPass
            actively tries to establish the association by sending out INIT
            chunks and responding with INIT ACK chunks when receiving INIT
            chunks. When set to 'false', TextPass has a passive role, meaning
            that it will only respond to inbound INIT chunks. Default is 
            'true'."
        ::= { m3uaAspEntry 35 }

    m3uaAspSctpSackDelay OBJECT-TYPE
        SYNTAX  SctpSackDelay
        ACCESS  read-write
        STATUS  mandatory
        DESCRIPTION
            "Time (in ms) to wait before acknowledging SCTP DATA chunks. A
            value of 0 (default) means use the system default, which tends
            to be 200ms. This setting only has an effect for newly created
            SCTP associations, and only when running on Linux/TPD. On
            Solaris, this setting is ignored."
        ::= { m3uaAspEntry 38 }

    m3uaAspSctpOperationalState OBJECT-TYPE
        SYNTAX  SctpOperationalState
        ACCESS  read-write
        STATUS  mandatory
        DESCRIPTION
            "Operation state of the SCTP association that TextPass maintains
            with the remote M3UA ASP."
        ::= { m3uaAspEntry 41 }

    m3uaAspSctpNegotiatedInboundStreams OBJECT-TYPE
        SYNTAX  SctpStreams
        ACCESS  read-write
        STATUS  mandatory
        DESCRIPTION
            "Number of inbound streams for the SCTP association that TextPass 
            maintains with the remote M3UA ASP. This number results from the 
            negotiation between TextPass and the remote M3UA ASP."
        ::= { m3uaAspEntry 42 }

    m3uaAspSctpNegotiatedOutboundStreams OBJECT-TYPE
        SYNTAX  SctpStreams
        ACCESS  read-write
        STATUS  mandatory
        DESCRIPTION
            "Number of outbound streams for the SCTP association that TextPass 
            maintains with the remote M3UA ASP. This number results from the 
            negotiation between TextPass and the remote M3UA ASP."
        ::= { m3uaAspEntry 43 }

    m3uaAspSctpUpTime OBJECT-TYPE
        SYNTAX  Gauge
        ACCESS  read-only
        STATUS  mandatory
        DESCRIPTION
            "Up time, expressed in number of seconds, for the SCTP association 
            that TextPass maintains with the remote M3UA ASP."
        ::= { m3uaAspEntry 44 }

    m3uaAspSctpDownTime OBJECT-TYPE
        SYNTAX  Gauge
        ACCESS  read-only
        STATUS  mandatory
        DESCRIPTION
            "Down time, expressed in number of seconds, for the SCTP association 
            that TextPass maintains with the remote M3UA ASP."
        ::= { m3uaAspEntry 45 }

    m3uaAspSctpInboundTsn OBJECT-TYPE
        SYNTAX  SctpTsn
        ACCESS  read-write
        STATUS  mandatory
        DESCRIPTION
            "Current value of the Transmission Sequence Number (TSN) for the 
            inbound direction of the association that TextPass maintains with
            the remote M3UA ASP."
        ::= { m3uaAspEntry 46 }

    m3uaAspSctpOutboudTsn OBJECT-TYPE
        SYNTAX  SctpTsn
        ACCESS  read-write
        STATUS  mandatory
        DESCRIPTION
            "Current value of the Transmission Sequence Number (TSN) for the 
            outbound direction of the association that TextPass maintains with
            the remote M3UA ASP."
        ::= { m3uaAspEntry 47 }

    m3uaAspSctpTsnCumulativeAck OBJECT-TYPE
        SYNTAX  SctpTsn
        ACCESS  read-write
        STATUS  mandatory
        DESCRIPTION
            "The Transmission Sequence Number (TSN) of the last DATA chunk that 
            the M3UA ASP acknowledged via the Cumulative TSN Ack field of a SACK."
        ::= { m3uaAspEntry 48 }

    m3uaAspSctpLocalReceiveWindow OBJECT-TYPE
        SYNTAX  SctpWindowSize
        ACCESS  read-write
        STATUS  mandatory
        DESCRIPTION
            "Current value of the receiver window (rwnd) on TextPass for the 
            association that TextPass maintains with the remote M3UA ASP."
        ::= { m3uaAspEntry 49 }

    m3uaAspSctpRemoteReceiveWindow OBJECT-TYPE
        SYNTAX  SctpWindowSize
        ACCESS  read-write
        STATUS  mandatory
        DESCRIPTION
            "Current value of the receiver window (rwnd) on remote M3UA ASP for 
            the association that TextPass maintains with the remote M3UA ASP."
        ::= { m3uaAspEntry 50 }

    m3uaAspSctpCongestionWindow OBJECT-TYPE
        SYNTAX  SctpWindowSize
        ACCESS  read-write
        STATUS  mandatory
        DESCRIPTION
            "Current value of the congestion window (cwnd) for the association 
            that TextPass maintains with the remote M3UA ASP."
        ::= { m3uaAspEntry 51 }

    m3uaAspSctpRoundTripTime OBJECT-TYPE
        SYNTAX  SctpRoundTripTime
        ACCESS  read-write
        STATUS  mandatory
        DESCRIPTION
            "Current value of the round trip time (RTT) for primary address of 
            the SCTP association that TextPass maintains with the remote M3UA 
            ASP."
        ::= { m3uaAspEntry 52 }

    m3uaAspSctpRetransmissionTimeout OBJECT-TYPE
        SYNTAX  SctpRetransmitTimeout
        ACCESS  read-write
        STATUS  mandatory
        DESCRIPTION
            "Current value of the retransmission timeout (RTO) for the primary 
            destination of the SCTP association that TextPass maintains with the 
            remote M3UA ASP."
        ::= { m3uaAspEntry 53 }

    m3uaAspSctpSmoothedLinkQuality OBJECT-TYPE
        SYNTAX  SctpSmoothedLinkQuality
        ACCESS  read-write
        STATUS  mandatory
        DESCRIPTION
            "Current value of the smoothed link quality indicator for the 
            primary destination of the SCTP association that TextPass maintains 
            with the remote M3UA ASP. Smoothed link quality is a proprietary 
            measurement that indicates the quality of a path."
        ::= { m3uaAspEntry 54 }

    m3uaAspSctpT3RtxBasedRetransmitCounter OBJECT-TYPE
        SYNTAX  Counter
        ACCESS  read-write
        STATUS  mandatory
        DESCRIPTION
            "Counter specifying the number of retransmits resulting from an 
            expiration of T3-rtx timer on the SCTP association that TextPass 
            maintains with the remote M3UA ASP." 
        ::= { m3uaAspEntry 55 }

    m3uaAspSctpSackBasedRetransmitCounter OBJECT-TYPE
        SYNTAX  Counter
        ACCESS  read-write
        STATUS  mandatory
        DESCRIPTION
            "Counter specifying the number of retransmits resulting from errors 
            reported by a SACK chunk on the SCTP association that TextPass 
            maintains with the remote M3UA ASP." 
        ::= { m3uaAspEntry 56 }

    m3uaAspSctpDataChunkRetransmitCounter OBJECT-TYPE
        SYNTAX  Counter
        ACCESS  read-write
        STATUS  mandatory
        DESCRIPTION
            "Counter specifying the number of DATA chunks retransmits on the 
            SCTP association that TextPass maintains with the remote M3UA ASP."
        ::= { m3uaAspEntry 57 }

    m3uaAspSctpPrimaryChangeOverCounter OBJECT-TYPE
        SYNTAX  Counter
        ACCESS  read-write
        STATUS  mandatory
        DESCRIPTION
            "Counter specifying the number of primary path changeovers on the 
            SCTP association that TextPass maintains with the remote M3UA ASP."
        ::= { m3uaAspEntry 58 }

    m3uaAspSctpSentDataByteCounter OBJECT-TYPE
        SYNTAX  Counter
        ACCESS  read-write
        STATUS  mandatory
        DESCRIPTION
            "Counter specifying the number of data bytes sent on the SCTP 
            association that TextPass maintains with the remote M3UA ASP."
        ::= { m3uaAspEntry 71 }

    m3uaAspSctpRecvDataByteCounter OBJECT-TYPE
        SYNTAX  Counter
        ACCESS  read-write
        STATUS  mandatory
        DESCRIPTION
            "Counter specifying the number of data bytes received on the SCTP 
            association that TextPass maintains with the remote M3UA ASP."
        ::= { m3uaAspEntry 72 }

    m3uaAspSctpSentSackWithGapCounter OBJECT-TYPE
        SYNTAX  Counter
        ACCESS  read-write
        STATUS  mandatory
        DESCRIPTION
            "Counter specifying the number of SACK chunks sent with a gap on the 
            SCTP association that TextPass maintains with the remote M3UA ASP."
        ::= { m3uaAspEntry 73 }

    m3uaAspSctpRecvSackWithGapCounter OBJECT-TYPE
        SYNTAX  Counter
        ACCESS  read-write
        STATUS  mandatory
        DESCRIPTION
            "Counter specifying the number of SACK chunks received with a gap on  
            the SCTP association that TextPass maintains with the remote M3UA 
            ASP."
        ::= { m3uaAspEntry 74 }

    m3uaAspSctpRecvDataChunkDiscardedCounter OBJECT-TYPE
        SYNTAX  Counter
        ACCESS  read-write
        STATUS  mandatory
        DESCRIPTION
            "Counter specifying the number of received DATA chunks that have 
            been discarded for the SCTP association that TextPass maintains with 
            the remote M3UA ASP."
        ::= { m3uaAspEntry 75 }

    m3uaAspSctpSentDataChunkDroppedCounter OBJECT-TYPE
        SYNTAX  Counter
        ACCESS  read-write
        STATUS  mandatory
        DESCRIPTION
            "Counter specifying the number of sent DATA chunks that have been 
            dropped for the SCTP association that TextPass maintains with the 
            remote M3UA ASP."
        ::= { m3uaAspEntry 76 }

    m3uaAspSctpSentDataChunkCounter OBJECT-TYPE
        SYNTAX  Counter
        ACCESS  read-write
        STATUS  mandatory
        DESCRIPTION
            "Counter specifying the number of DATA chunks sent on the SCTP 
            association that TextPass maintains with the remote M3UA ASP."
        ::= { m3uaAspEntry 81 }

    m3uaAspSctpRecvDataChunkCounter OBJECT-TYPE
        SYNTAX  Counter
        ACCESS  read-write
        STATUS  mandatory
        DESCRIPTION
            "Counter specifying the number of DATA chunks received on the SCTP 
            association that TextPass maintains with the remote M3UA ASP."
        ::= { m3uaAspEntry 82 }

    m3uaAspSctpSentInitChunkCounter OBJECT-TYPE
        SYNTAX  Counter
        ACCESS  read-write
        STATUS  mandatory
        DESCRIPTION
            "Counter specifying the number of INIT chunks sent on the SCTP 
            association that TextPass maintains with the remote M3UA ASP."
        ::= { m3uaAspEntry 83 }

    m3uaAspSctpRecvInitChunkCounter OBJECT-TYPE
        SYNTAX  Counter
        ACCESS  read-write
        STATUS  mandatory
        DESCRIPTION
            "Counter specifying the number of INIT chunks received on the SCTP 
            association that TextPass maintains with the remote M3UA ASP."
        ::= { m3uaAspEntry 84 }

    m3uaAspSctpSentInitAckChunkCounter OBJECT-TYPE
        SYNTAX  Counter
        ACCESS  read-write
        STATUS  mandatory
        DESCRIPTION
            "Counter specifying the number of INIT ACK chunks sent on the SCTP 
            association that TextPass maintains with the remote M3UA ASP."
        ::= { m3uaAspEntry 85 }

    m3uaAspSctpRecvInitAckChunkCounter OBJECT-TYPE
        SYNTAX  Counter
        ACCESS  read-write
        STATUS  mandatory
        DESCRIPTION
            "Counter specifying the number of INIT ACK chunks received on the  
            SCTP association that TextPass maintains with the remote M3UA ASP."
        ::= { m3uaAspEntry 86 }

    m3uaAspSctpSentSackChunkCounter OBJECT-TYPE
        SYNTAX  Counter
        ACCESS  read-write
        STATUS  mandatory
        DESCRIPTION
            "Counter specifying the number of SACK chunks sent on the SCTP 
            association that TextPass maintains with the remote M3UA ASP."
        ::= { m3uaAspEntry 87 }

    m3uaAspSctpRecvSackChunkCounter OBJECT-TYPE
        SYNTAX  Counter
        ACCESS  read-write
        STATUS  mandatory
        DESCRIPTION
            "Counter specifying the number of SACK chunks received on the SCTP 
            association that TextPass maintains with the remote M3UA ASP."
        ::= { m3uaAspEntry 88 }

    m3uaAspSctpSentHeartbeatCounter OBJECT-TYPE
        SYNTAX  Counter
        ACCESS  read-write
        STATUS  mandatory
        DESCRIPTION
            "Counter specifying the number of HEARTBEAT chunks sent on the SCTP 
            association that TextPass maintains with the remote M3UA ASP."
        ::= { m3uaAspEntry 89 }

    m3uaAspSctpRecvHeartbeatCounter OBJECT-TYPE
        SYNTAX  Counter
        ACCESS  read-write
        STATUS  mandatory
        DESCRIPTION
            "Counter specifying the number of HEARTBEAT chunks received on the  
            SCTP association that TextPass maintains with the remote M3UA ASP."
        ::= { m3uaAspEntry 90 }

    m3uaAspSctpSentHeartbeatAckCounter OBJECT-TYPE
        SYNTAX  Counter
        ACCESS  read-write
        STATUS  mandatory
        DESCRIPTION
            "Counter specifying the number of HEARTBEAT ACK chunks sent on the 
            SCTP association that TextPass maintains with the remote M3UA ASP."
        ::= { m3uaAspEntry 91 }

    m3uaAspSctpRecvHeartbeatAckCounter OBJECT-TYPE
        SYNTAX  Counter
        ACCESS  read-write
        STATUS  mandatory
        DESCRIPTION
            "Counter specifying the number of HEARTBEAT ACK chunks received on 
            the SCTP association that TextPass maintains with the remote M3UA 
            ASP."
        ::= { m3uaAspEntry 92 }

    m3uaAspSctpSentAbortChunkCounter OBJECT-TYPE
        SYNTAX  Counter
        ACCESS  read-write
        STATUS  mandatory
        DESCRIPTION
            "Counter specifying the number of ABORT chunks sent on the SCTP 
            association that TextPass maintains with the remote M3UA ASP."
        ::= { m3uaAspEntry 93 }

    m3uaAspSctpRecvAbortChunkCounter OBJECT-TYPE
        SYNTAX  Counter
        ACCESS  read-write
        STATUS  mandatory
        DESCRIPTION
            "Counter specifying the number of ABORT chunks received on the  
            SCTP association that TextPass maintains with the remote M3UA ASP."
        ::= { m3uaAspEntry 94 }

    m3uaAspSctpSentShutdownChunkCounter OBJECT-TYPE
        SYNTAX  Counter
        ACCESS  read-write
        STATUS  mandatory
        DESCRIPTION
            "Counter specifying the number of SHUTDOWN chunks sent on the SCTP 
            association that TextPass maintains with the remote M3UA ASP."
        ::= { m3uaAspEntry 95 }

    m3uaAspSctpRecvShutdownChunkCounter OBJECT-TYPE
        SYNTAX  Counter
        ACCESS  read-write
        STATUS  mandatory
        DESCRIPTION
            "Counter specifying the number of SHUTDOWN chunks received on the  
            SCTP association that TextPass maintains with the remote M3UA ASP."
        ::= { m3uaAspEntry 96 }

    m3uaAspSctpSentShutdownAckChunkCounter OBJECT-TYPE
        SYNTAX  Counter
        ACCESS  read-write
        STATUS  mandatory
        DESCRIPTION
            "Counter specifying the number of SHUTDOWN ACK chunks sent on the  
            SCTP association that TextPass maintains with the remote M3UA ASP."
        ::= { m3uaAspEntry 97 }

    m3uaAspSctpRecvShutdownAckChunkCounter OBJECT-TYPE
        SYNTAX  Counter
        ACCESS  read-write
        STATUS  mandatory
        DESCRIPTION
            "Counter specifying the number of SHUTDOWN ACK chunks received on   
            the SCTP association that TextPass maintains with the remote M3UA 
            ASP."
        ::= { m3uaAspEntry 98 }

    m3uaAspSctpSentErrorChunkCounter OBJECT-TYPE
        SYNTAX  Counter
        ACCESS  read-write
        STATUS  mandatory
        DESCRIPTION
            "Counter specifying the number of ERROR chunks sent on the SCTP 
            association that TextPass maintains with the remote M3UA ASP."
        ::= { m3uaAspEntry 99 }

    m3uaAspSctpRecvErrorChunkCounter OBJECT-TYPE
        SYNTAX  Counter
        ACCESS  read-write
        STATUS  mandatory
        DESCRIPTION
            "Counter specifying the number of ERROR chunks received on the SCTP 
            association that TextPass maintains with the remote M3UA ASP."
        ::= { m3uaAspEntry 100 }

    m3uaAspSctpSentCookieEchoChunkCounter OBJECT-TYPE
        SYNTAX  Counter
        ACCESS  read-write
        STATUS  mandatory
        DESCRIPTION
            "Counter specifying the number of COOKIE ECHO chunks sent on the  
            SCTP association that TextPass maintains with the remote M3UA ASP."
        ::= { m3uaAspEntry 101 }

    m3uaAspSctpRecvCookieEchoChunkCounter OBJECT-TYPE
        SYNTAX  Counter
        ACCESS  read-write
        STATUS  mandatory
        DESCRIPTION
            "Counter specifying the number of COOKIE ECHO chunks received on the  
            SCTP association that TextPass maintains with the remote M3UA ASP."
        ::= { m3uaAspEntry 102 }

    m3uaAspSctpSentCookieAckChunkCounter OBJECT-TYPE
        SYNTAX  Counter
        ACCESS  read-write
        STATUS  mandatory
        DESCRIPTION
            "Counter specifying the number of COOKIE ACK chunks sent on the SCTP 
            association that TextPass maintains with the remote M3UA ASP."
        ::= { m3uaAspEntry 103 }

    m3uaAspSctpRecvCookieAckChunkCounter OBJECT-TYPE
        SYNTAX  Counter
        ACCESS  read-write
        STATUS  mandatory
        DESCRIPTION
            "Counter specifying the number of COOKIE ACK chunks received on the  
            SCTP association that TextPass maintains with the remote M3UA ASP."
        ::= { m3uaAspEntry 104 }

    m3uaAspSctpSentShutdownCompleteChunkCounter OBJECT-TYPE
        SYNTAX  Counter
        ACCESS  read-write
        STATUS  mandatory
        DESCRIPTION
            "Counter specifying the number of SHUTDOWN COMPLETE chunks sent on 
            the SCTP association that TextPass maintains with the remote M3UA ASP."
        ::= { m3uaAspEntry 105 }

    m3uaAspSctpRecvShutdownCompleteChunkCounter OBJECT-TYPE
        SYNTAX  Counter
        ACCESS  read-write
        STATUS  mandatory
        DESCRIPTION
            "Counter specifying the number of SHUTDOWN COMPLETE chunks received 
            on the SCTP association that TextPass maintains with the remote M3UA 
            ASP."
        ::= { m3uaAspEntry 106 }

    m3uaAspSctpInvalidStreamIdErrorCounter OBJECT-TYPE
        SYNTAX  Counter
        ACCESS  read-write
        STATUS  mandatory
        DESCRIPTION
            "Counter specifying the number of 'Invalid Stream Id' ERROR chunks 
            received on the SCTP association that TextPass maintains with the 
            remote M3UA ASP."
        ::= { m3uaAspEntry 121 }

    m3uaAspSctpMissingMandatoryParameterErrorCounter OBJECT-TYPE
        SYNTAX  Counter
        ACCESS  read-write
        STATUS  mandatory
        DESCRIPTION
            "Counter specifying the number of 'Missing Mandatory Parameter' 
            ERROR chunks received on the SCTP association that TextPass 
            maintains with the remote M3UA ASP."
        ::= { m3uaAspEntry 122 }

    m3uaAspSctpStaleCookieErrorCounter OBJECT-TYPE
        SYNTAX  Counter
        ACCESS  read-write
        STATUS  mandatory
        DESCRIPTION
            "Counter specifying the number of 'Stale Cookie' ERROR chunks 
            received on the SCTP association that TextPass maintains with the 
            remote M3UA ASP."
        ::= { m3uaAspEntry 123 }

    m3uaAspSctpOutOfResourceErrorCounter OBJECT-TYPE
        SYNTAX  Counter
        ACCESS  read-write
        STATUS  mandatory
        DESCRIPTION
            "Counter specifying the number of 'Out Of Resource' ERROR chunks 
            received on the SCTP association that TextPass maintains with the 
            remote M3UA ASP."
        ::= { m3uaAspEntry 124 }

    m3uaAspSctpUnresolvableAddressErrorCounter OBJECT-TYPE
        SYNTAX  Counter
        ACCESS  read-write
        STATUS  mandatory
        DESCRIPTION
            "Counter specifying the number of 'Unresolvable Address' ERROR 
            chunks received on the SCTP association that TextPass maintains with 
            the remote M3UA ASP."
        ::= { m3uaAspEntry 125 }

    m3uaAspSctpUnrecognisedChunkTypeErrorCounter OBJECT-TYPE
        SYNTAX  Counter
        ACCESS  read-write
        STATUS  mandatory
        DESCRIPTION
            "Counter specifying the number of 'Unrecognised Chunk Type' ERROR 
            chunks received on the SCTP association that TextPass maintains with 
            the remote M3UA ASP."
        ::= { m3uaAspEntry 126 }

    m3uaAspSctpInvalidMandatoryParameterErrorCounter OBJECT-TYPE
        SYNTAX  Counter
        ACCESS  read-write
        STATUS  mandatory
        DESCRIPTION
            "Counter specifying the number of 'Invalid Mandatory Parameter' 
            ERROR chunks received on the SCTP association that TextPass 
            maintains with the remote M3UA ASP."
        ::= { m3uaAspEntry 127 }

    m3uaAspSctpUnrecognisedParamtersErrorCounter OBJECT-TYPE
        SYNTAX  Counter
        ACCESS  read-write
        STATUS  mandatory
        DESCRIPTION
            "Counter specifying the number of 'Unrecognised Parameters' ERROR
            chunks received on the SCTP association that TextPass maintains with 
            the remote M3UA ASP."
        ::= { m3uaAspEntry 128 }

    m3uaAspSctpNoUserDataErrorCounter OBJECT-TYPE
        SYNTAX  Counter
        ACCESS  read-write
        STATUS  mandatory
        DESCRIPTION
            "Counter specifying the number of 'No User Data' ERROR chunks 
            received on the SCTP association that TextPass maintains with 
            the remote M3UA ASP."
        ::= { m3uaAspEntry 129 }

    m3uaAspSctpCookieRecvWhileShuttingDownErrorCounter OBJECT-TYPE
        SYNTAX  Counter
        ACCESS  read-write
        STATUS  mandatory
        DESCRIPTION
            "Counter specifying the number of 'Cookie Received While Shutting 
            Down' ERROR chunks received on the SCTP association that TextPass 
            maintains with the remote M3UA ASP."
        ::= { m3uaAspEntry 130 }


    -- the M3UA ASP remote IP address table

    m3uaAspRemoteAddressTable OBJECT-TYPE
        SYNTAX  SEQUENCE OF M3uaAspRemoteAddressEntry
        ACCESS  not-accessible
        STATUS  mandatory
        DESCRIPTION
            "Table containing info about IP addresses of remote M3UA Application 
            Servers Processes (ASP's)."
        ::= { m3ua 22 }

    m3uaAspRemoteAddressEntry OBJECT-TYPE
        SYNTAX  M3uaAspRemoteAddressEntry
        ACCESS  not-accessible
        STATUS  mandatory
        DESCRIPTION
            "Entry of table containing info about IP addresses of remote M3UA 
            Application Servers Processes (ASP's)."
        INDEX   { m3uaAspIndex, m3uaAspRemoteAddressIndex }
        ::= { m3uaAspRemoteAddressTable 1 }

    M3uaAspRemoteAddressEntry ::=
        SEQUENCE {
            m3uaAspRemoteAddressIndex               M3uaRemoteAddressTableIndex,
            m3uaAspRemoteAddressAdminState          AdminState,
            m3uaAspRemoteAddressOperationalState    RemoteAddressOperationalState,
            m3uaAspRemoteAddressSpec                IpAddressSpec,
            m3uaAspRemoteAddressSctpErrorCounter    Counter,
            m3uaAspRemoteAddressSctpSentHeartbeatCounter Counter,
            m3uaAspRemoteAddressSctpRecvHeartbeatCounter Counter,
            m3uaAspRemoteAddressSctpSentHeartbeatAckCounter Counter,
            m3uaAspRemoteAddressSctpRecvHeartbeatAckCounter Counter,
            m3uaAspRemoteAddressSctpRoundTripTime   SctpRoundTripTime,
            m3uaAspRemoteAddressSctpRetransmissionTimeout SctpRetransmitTimeout,
            m3uaAspRemoteAddressSctpSmoothedLinkQuality SctpSmoothedLinkQuality
        }    

    m3uaAspRemoteAddressIndex OBJECT-TYPE
        SYNTAX  M3uaRemoteAddressTableIndex
        ACCESS  read-write
        STATUS  mandatory
        DESCRIPTION
            "Index of entry in table with IP addresses for remote M3UA ASP."
        ::= { m3uaAspRemoteAddressEntry 1 }

    m3uaAspRemoteAddressAdminState OBJECT-TYPE
        SYNTAX  AdminState
        ACCESS  read-write
        STATUS  mandatory
        DESCRIPTION
            "Administrative state of IP address of remote M3UA ASP."
        ::= { m3uaAspRemoteAddressEntry 2 }

    m3uaAspRemoteAddressOperationalState OBJECT-TYPE
        SYNTAX  RemoteAddressOperationalState
        ACCESS  read-write
        STATUS  mandatory
        DESCRIPTION
            "Operational state of IP address of remote M3UA ASP."
        ::= { m3uaAspRemoteAddressEntry 3 }

    m3uaAspRemoteAddressSpec OBJECT-TYPE
        SYNTAX  IpAddressSpec
        ACCESS  read-write
        STATUS  mandatory
        DESCRIPTION
            "IPv4 or IPv6 specification for IP address of remote M3UA ASP."
        ::= { m3uaAspRemoteAddressEntry 11 }

    m3uaAspRemoteAddressSctpErrorCounter OBJECT-TYPE
        SYNTAX  Counter
        ACCESS  read-write
        STATUS  mandatory
        DESCRIPTION
            "Counter specifying number of SCTP errors for IP address of
            remote M3UA ASP."
        ::= { m3uaAspRemoteAddressEntry 21 }

    m3uaAspRemoteAddressSctpSentHeartbeatCounter OBJECT-TYPE
        SYNTAX  Counter
        ACCESS  read-write
        STATUS  mandatory
        DESCRIPTION
            "Counter specifying the number of HEARTBEAT chunks sent to IP 
            address of remote M3UA ASP."
        ::= { m3uaAspRemoteAddressEntry 31 }

    m3uaAspRemoteAddressSctpRecvHeartbeatCounter OBJECT-TYPE
        SYNTAX  Counter
        ACCESS  read-write
        STATUS  mandatory
        DESCRIPTION
            "Counter specifying the number of HEARTBEAT chunks received from IP 
            address of remote M3UA ASP."
        ::= { m3uaAspRemoteAddressEntry 32 }

    m3uaAspRemoteAddressSctpSentHeartbeatAckCounter OBJECT-TYPE
        SYNTAX  Counter
        ACCESS  read-write
        STATUS  mandatory
        DESCRIPTION
            "Counter specifying the number of HEARTBEAT ACK chunks sent to IP
            address of remote M3UA ASP."
        ::= { m3uaAspRemoteAddressEntry 33 }

    m3uaAspRemoteAddressSctpRecvHeartbeatAckCounter OBJECT-TYPE
        SYNTAX  Counter
        ACCESS  read-write
        STATUS  mandatory
        DESCRIPTION
            "Counter specifying the number of HEARTBEAT ACK chunks received from
            IP address of remote M3UA ASP."
        ::= { m3uaAspRemoteAddressEntry 34 }

    m3uaAspRemoteAddressSctpRoundTripTime OBJECT-TYPE
        SYNTAX  SctpRoundTripTime
        ACCESS  read-write
        STATUS  mandatory
        DESCRIPTION
            "Current value of the round trip time (RTT) for IP address of remote 
            M3UA ASP."
        ::= { m3uaAspRemoteAddressEntry 41 }

    m3uaAspRemoteAddressSctpRetransmissionTimeout OBJECT-TYPE
        SYNTAX  SctpRetransmitTimeout
        ACCESS  read-write
        STATUS  mandatory
        DESCRIPTION
            "Current value of the retransmission timeout (RTO) for the IP  
            address of remote M3UA ASP."
        ::= { m3uaAspRemoteAddressEntry 42 }

    m3uaAspRemoteAddressSctpSmoothedLinkQuality OBJECT-TYPE
        SYNTAX  SctpSmoothedLinkQuality
        ACCESS  read-write
        STATUS  mandatory
        DESCRIPTION
            ""
        ::= { m3uaAspRemoteAddressEntry 43 }


    -- the M3UA AS table
    
    m3uaAsTable OBJECT-TYPE
        SYNTAX  SEQUENCE OF M3uaAsEntry
        ACCESS  not-accessible
        STATUS  mandatory
        DESCRIPTION
            "Table containing info about remote M3UA Application Servers (AS's)."
        ::= { m3ua 26 }

    m3uaAsEntry OBJECT-TYPE
        SYNTAX  M3uaAsEntry
        ACCESS  not-accessible
        STATUS  mandatory
        DESCRIPTION
            "Entry of table containing info about remote M3UA Application Servers 
            (AS's)."
        INDEX   { m3uaAsIndex }
        ::= { m3uaAsTable 1 }

    M3uaAsEntry ::=
        SEQUENCE {
            m3uaAsIndex                             M3uaAsTableIndex,
            m3uaAsAdminState                        AdminState,
            m3uaAsOperationalState                  M3uaAsOperationalState,
            m3uaAsName                              NameString,
            m3uaAsRoutingContext                    RoutingContext
        }
        

    m3uaAsIndex OBJECT-TYPE
        SYNTAX  M3uaAsTableIndex
        ACCESS  read-write
        STATUS  mandatory
        DESCRIPTION
            "Index of M3UA AS table."
        ::= { m3uaAsEntry 1 }

    m3uaAsAdminState OBJECT-TYPE
        SYNTAX  AdminState
        ACCESS  read-write
        STATUS  mandatory
        DESCRIPTION
            "Administrative state of remote M3UA AS."
        ::= { m3uaAsEntry 2 }

    m3uaAsOperationalState OBJECT-TYPE
        SYNTAX  M3uaAsOperationalState
        ACCESS  read-write
        STATUS  mandatory
        DESCRIPTION
            "Operational state of remote M3UA AS."
        ::= { m3uaAsEntry 3 }

    m3uaAsName OBJECT-TYPE
        SYNTAX  NameString
        ACCESS  read-write
        STATUS  mandatory
        DESCRIPTION
            "Name of remote M3UA AS."
        ::= { m3uaAsEntry 4 }

    m3uaAsRoutingContext OBJECT-TYPE
        SYNTAX  RoutingContext
        ACCESS  read-write
        STATUS  mandatory
        DESCRIPTION
            "Routing context associated with remote M3UA AS."
        ::= { m3uaAsEntry 11 }


    -- the M3UA AS instance table
    
    m3uaAsInstanceTable OBJECT-TYPE
        SYNTAX  SEQUENCE OF M3uaAsInstanceEntry
        ACCESS  not-accessible
        STATUS  mandatory
        DESCRIPTION
            "Table containing info about M3UA AS instances. This table determines
            which remote M3UA AS's are active for each remote M3UA ASP."
        ::= { m3ua 27 }

    m3uaAsInstanceEntry OBJECT-TYPE
        SYNTAX  M3uaAsInstanceEntry
        ACCESS  not-accessible
        STATUS  mandatory
        DESCRIPTION
            "Entry of table containing info about M3UA AS instances."
        INDEX   { m3uaAsIndex, m3uaAspIndex  }
        ::= { m3uaAsInstanceTable 1 }

    M3uaAsInstanceEntry ::=
        SEQUENCE {
            m3uaAsInstanceAsIndex                   M3uaAsTableIndex,
            m3uaAsInstanceAspIndex                  M3uaAspTableIndex,
            m3uaAsInstanceAdminState                AdminState,
            m3uaAsInstanceOperationalState          M3uaAsInstanceOperationalState
        }
        
    m3uaAsInstanceAsIndex OBJECT-TYPE
        SYNTAX  M3uaAsTableIndex
        ACCESS  read-write
        STATUS  mandatory
        DESCRIPTION
            "Index of remote M3UA AS in remote M3UA AS table."
        ::= { m3uaAsInstanceEntry 1 }

    m3uaAsInstanceAspIndex OBJECT-TYPE
        SYNTAX  M3uaAspTableIndex
        ACCESS  read-write
        STATUS  mandatory
        DESCRIPTION
            "Index of remote M3UA ASP in remote M3UA ASP table."
        ::= { m3uaAsInstanceEntry 2 }

    m3uaAsInstanceAdminState OBJECT-TYPE
        SYNTAX  AdminState
        ACCESS  read-write
        STATUS  mandatory
        DESCRIPTION
            "Administrative state of remote AS instance."
        ::= { m3uaAsInstanceEntry 3 }

    m3uaAsInstanceOperationalState OBJECT-TYPE
        SYNTAX  M3uaAsInstanceOperationalState
        ACCESS  read-write
        STATUS  mandatory
        DESCRIPTION
            "Operational state of remote AS instance."
        ::= { m3uaAsInstanceEntry 4 }

     -- the SUA subsystem

    sua    OBJECT IDENTIFIER ::= { textpass 20 }

    -- the SUA local IP address table

    suaLocalAddressTable OBJECT-TYPE
        SYNTAX  SEQUENCE OF SuaLocalAddressEntry
        ACCESS  not-accessible
        STATUS  mandatory
        DESCRIPTION
            "Table containing info about local IP addresses that TextPass 
            uses for SUA."
        ::= { sua 2 }

    suaLocalAddressEntry OBJECT-TYPE
        SYNTAX  SuaLocalAddressEntry
        ACCESS  not-accessible
        STATUS  mandatory
        DESCRIPTION
            "Entry of table containing info about local IP addresses that  
            TextPass uses for SUA."
        INDEX   { suaLocalAddressIndex }
        ::= { suaLocalAddressTable 1 }

    SuaLocalAddressEntry ::=
        SEQUENCE {
            suaLocalAddressIndex                   SuaLocalAddressTableIndex,
            suaLocalAddressAdminState              AdminState,
            suaLocalAddressSpec                    IpAddressSpec
        }
        
    suaLocalAddressIndex OBJECT-TYPE
        SYNTAX  SuaLocalAddressTableIndex
        ACCESS  read-write
        STATUS  mandatory
        DESCRIPTION
            "Index of entry in table with local IP addresses for SUA."
        ::= { suaLocalAddressEntry 1 }

    suaLocalAddressAdminState OBJECT-TYPE
        SYNTAX  AdminState
        ACCESS  read-write
        STATUS  mandatory
        DESCRIPTION
            "Administrative state of the local IP address for SUA."
        ::= { suaLocalAddressEntry 2 }

    suaLocalAddressSpec OBJECT-TYPE
        SYNTAX  IpAddressSpec
        ACCESS  read-write
        STATUS  mandatory
        DESCRIPTION
            "IPv4 or IPv6 specification for local IP address for SUA."
        ::= { suaLocalAddressEntry 11 }

        
    -- the SUA ASP table
    
    suaAspTable OBJECT-TYPE
        SYNTAX  SEQUENCE OF SuaAspEntry
        ACCESS  not-accessible
        STATUS  mandatory
        DESCRIPTION
            "Table containing info about remote SUA Application Server 
            Processes (ASP)."
        ::= { sua 21 }

    suaAspEntry OBJECT-TYPE
        SYNTAX  SuaAspEntry
        ACCESS  not-accessible
        STATUS  mandatory
        DESCRIPTION
            "Entry of table containing info about remote SUA Application Server 
            Processes (ASP)."
        INDEX   { suaAspIndex }
        ::= { suaAspTable 1 }

    SuaAspEntry ::=
        SEQUENCE {
            suaAspIndex                            SuaAspTableIndex,
            suaAspAdminState                       AdminState,
            suaAspOperationalState                 SuaAspOperationalState,
            suaAspName                             NameString,
            suaAspAspIdentifier                    AspIdentifier,
            suaAspFillInRoutingContextField        Boolean,
            suaAspSctpLocalPort                    SctpPort,
            suaAspSctpRemotePort                   SctpPort,
            suaAspSctpMaxOutboundPduSize           SctpMaxPduSize,
            suaAspSctpMaxInboundPduSize            SctpMaxPduSize,
            suaAspSctpTimerT1Init                  SctpTimerT1Init,
            suaAspSctpTimerT3Rtx                   SctpTimerT3Rtx,
            suaAspSctpTimerHeartbeat               SctpTimerHeartbeat,
            suaAspSctpTimerT1Cookie                SctpTimerT1Cookie,
            suaAspSctpMaxRetransmitTimeout         SctpRetransmitTimeout,
            suaAspSctpMaxPathRetransmits           SctpRetransmits,
            suaAspSctpMaxAssociationRetransmits    SctpRetransmits,
            suaAspSctpMaxConnectAttempts           SctpMaxConnectAttempts,
            suaAspSctpMaxAllowedInboundStreams     SctpStreams,
            suaAspSctpPreferredOutboundStreams     SctpStreams,
            suaAspSctpInitiatingStartupEnabled     Boolean,
            suaAspSctpSackDelay                    SctpSackDelay,
            suaAspSctpOperationalState             SctpOperationalState,
            suaAspSctpNegotiatedInboundStreams     SctpStreams,
            suaAspSctpNegotiatedOutboundStreams    SctpStreams,
            suaAspSctpUpTime                       Gauge,
            suaAspSctpDownTime                     Gauge,
            suaAspSctpInboundTsn                   SctpTsn,
            suaAspSctpOutboudTsn                   SctpTsn,
            suaAspSctpTsnCumulativeAck             SctpTsn,
            suaAspSctpLocalReceiveWindow           SctpWindowSize,
            suaAspSctpRemoteReceiveWindow          SctpWindowSize,
            suaAspSctpCongestionWindow             SctpWindowSize,
            suaAspSctpRoundTripTime                SctpRoundTripTime,
            suaAspSctpRetransmissionTimeout        SctpRetransmitTimeout,
            suaAspSctpSmoothedLinkQuality          SctpSmoothedLinkQuality,
            suaAspSctpT3RtxBasedRetransmitCounter  Counter,
            suaAspSctpSackBasedRetransmitCounter   Counter,
            suaAspSctpDataChunkRetransmitCounter   Counter,
            suaAspSctpPrimaryChangeOverCounter     Counter,
            suaAspSctpSentDataByteCounter          Counter,
            suaAspSctpRecvDataByteCounter          Counter,
            suaAspSctpSentSackWithGapCounter       Counter,
            suaAspSctpRecvSackWithGapCounter       Counter,
            suaAspSctpRecvDataChunkDiscardedCounter Counter,
            suaAspSctpSentDataChunkDroppedCounter  Counter,
            suaAspSctpSentDataChunkCounter         Counter,
            suaAspSctpRecvDataChunkCounter         Counter,
            suaAspSctpSentInitChunkCounter         Counter,
            suaAspSctpRecvInitChunkCounter         Counter,
            suaAspSctpSentInitAckChunkCounter      Counter,
            suaAspSctpRecvInitAckChunkCounter      Counter,
            suaAspSctpSentSackChunkCounter         Counter,
            suaAspSctpRecvSackChunkCounter         Counter,
            suaAspSctpSentHeartbeatCounter         Counter,
            suaAspSctpRecvHeartbeatCounter         Counter,
            suaAspSctpSentHeartbeatAckCounter      Counter,
            suaAspSctpRecvHeartbeatAckCounter      Counter,
            suaAspSctpSentAbortChunkCounter        Counter,
            suaAspSctpRecvAbortChunkCounter        Counter,
            suaAspSctpSentShutdownChunkCounter     Counter,
            suaAspSctpRecvShutdownChunkCounter     Counter,
            suaAspSctpSentShutdownAckChunkCounter  Counter,
            suaAspSctpRecvShutdownAckChunkCounter  Counter,
            suaAspSctpSentErrorChunkCounter        Counter,
            suaAspSctpRecvErrorChunkCounter        Counter,
            suaAspSctpSentCookieEchoChunkCounter   Counter,
            suaAspSctpRecvCookieEchoChunkCounter   Counter,
            suaAspSctpSentCookieAckChunkCounter    Counter,
            suaAspSctpRecvCookieAckChunkCounter    Counter,
            suaAspSctpSentShutdownCompleteChunkCounter Counter,
            suaAspSctpRecvShutdownCompleteChunkCounter Counter,
            suaAspSctpInvalidStreamIdErrorCounter  Counter,
            suaAspSctpMissingMandatoryParameterErrorCounter Counter,
            suaAspSctpStaleCookieErrorCounter      Counter,
            suaAspSctpOutOfResourceErrorCounter    Counter,
            suaAspSctpUnresolvableAddressErrorCounter Counter,
            suaAspSctpUnrecognisedChunkTypeErrorCounter Counter,
            suaAspSctpInvalidMandatoryParameterErrorCounter Counter,
            suaAspSctpUnrecognisedParamtersErrorCounter Counter,
            suaAspSctpNoUserDataErrorCounter       Counter,
            suaAspSctpCookieRecvWhileShuttingDownErrorCounter Counter
        }
        
    suaAspIndex OBJECT-TYPE
        SYNTAX  SuaAspTableIndex
        ACCESS  read-write
        STATUS  mandatory
        DESCRIPTION
            "Index of entry in SUA ASP table."
        ::= { suaAspEntry 1 }

    suaAspAdminState OBJECT-TYPE
        SYNTAX  AdminState
        ACCESS  read-write
        STATUS  mandatory
        DESCRIPTION
            "Administrative state of the SUA ASP."
        ::= { suaAspEntry 2 }

    suaAspOperationalState OBJECT-TYPE
        SYNTAX  SuaAspOperationalState
        ACCESS  read-write
        STATUS  mandatory
        DESCRIPTION
            "Operational state of the SUA ASP."
        ::= { suaAspEntry 3 }

    suaAspName OBJECT-TYPE
        SYNTAX  NameString
        ACCESS  read-write
        STATUS  mandatory
        DESCRIPTION
            "Name of SUA ASP."
        ::= { suaAspEntry 4 }

    suaAspAspIdentifier OBJECT-TYPE
        SYNTAX  AspIdentifier
        ACCESS  read-write
        STATUS  mandatory
        DESCRIPTION
            "Value of ASP identifier that remote SUA ASP has sent in its last
            ASP-UP message."
        ::= { suaAspEntry 11 }

    suaAspFillInRoutingContextField OBJECT-TYPE
        SYNTAX  Boolean
        ACCESS  read-write
        STATUS  mandatory
        DESCRIPTION
            "Identifier specifying whether TextPass includes Routing Context in 
            messages towards M3UA ASP. When set to 'true', the field is always 
            specified. When set to to 'false', the field in never specified. 
            Default is 'true'."
        ::= { suaAspEntry 14 }

    suaAspSctpLocalPort OBJECT-TYPE
        SYNTAX  SctpPort
        ACCESS  read-write
        STATUS  mandatory
        DESCRIPTION
            "Local SCTP port for the SCTP association that TextPass maintains 
            with the remote SUA ASP. Default is 14001."
        ::= { suaAspEntry 21 }

    suaAspSctpRemotePort OBJECT-TYPE
        SYNTAX  SctpPort
        ACCESS  read-write
        STATUS  mandatory
        DESCRIPTION
            "Remote SCTP port for the SCTP association that TextPass maintains 
            with the remote SUA ASP. Default is 14001."
        ::= { suaAspEntry 22 }

    suaAspSctpMaxOutboundPduSize OBJECT-TYPE
        SYNTAX  SctpMaxPduSize
        ACCESS  read-write
        STATUS  mandatory
        DESCRIPTION
            "Maximum outbound PDU size for the SCTP association that TextPass 
            maintains with the remote SUA ASP. Default is 1500."
        ::= { suaAspEntry 23 }

    suaAspSctpMaxInboundPduSize OBJECT-TYPE
        SYNTAX  SctpMaxPduSize
        ACCESS  read-write
        STATUS  mandatory
        DESCRIPTION
            "Maximum inbound PDU size for the SCTP association that TextPass 
            maintains with the remote SUA ASP. Default is 1500."
        ::= { suaAspEntry 24 }

    suaAspSctpTimerT1Init OBJECT-TYPE
        SYNTAX  SctpTimerT1Init
        ACCESS  read-write
        STATUS  mandatory
        DESCRIPTION
            "Value for T1-init timer for the SCTP association that TextPass 
            maintains with the remote SUA ASP, expressed in units of 
            milliseconds. Default is 3000."
        ::= { suaAspEntry 25 }

    suaAspSctpTimerT3Rtx OBJECT-TYPE
        SYNTAX  SctpTimerT3Rtx
        ACCESS  read-write
        STATUS  mandatory
        DESCRIPTION
            "Value for T3-rtx timer for the SCTP association that TextPass 
            maintains with the remote SUA ASP, expressed in units of 
            milliseconds. Default is 2000."
        ::= { suaAspEntry 26 }

    suaAspSctpTimerHeartbeat OBJECT-TYPE
        SYNTAX  SctpTimerHeartbeat
        ACCESS  read-write
        STATUS  mandatory
        DESCRIPTION
            "SCTP heartbeat interval for the SCTP association that TextPass 
            maintains with the remote SUA ASP, expressed in units of 
            milliseconds. Default is 1000."
        ::= { suaAspEntry 27 }

    suaAspSctpTimerT1Cookie OBJECT-TYPE
        SYNTAX  SctpTimerT1Cookie
        ACCESS  read-write
        STATUS  mandatory
        DESCRIPTION
            "Value for T1-cookie timer for the SCTP association that TextPass 
            maintains with the remote SUA ASP, expressed in units of 
            milliseconds. Default is 3000."
        ::= { suaAspEntry 28 }

    suaAspSctpMaxRetransmitTimeout OBJECT-TYPE
        SYNTAX  SctpRetransmitTimeout
        ACCESS  read-write
        STATUS  mandatory
        DESCRIPTION
            "Maximum value of the dynamic retransmit timer (RTO.max) for the 
            SCTP association that TextPass maintains with the remote SUA ASP, 
            expressed in units of milliseconds. Default is 2000." 

        ::= { suaAspEntry 29 }

    suaAspSctpMaxPathRetransmits OBJECT-TYPE
        SYNTAX  SctpRetransmits
        ACCESS  read-write
        STATUS  mandatory
        DESCRIPTION
            "Maximum number of path retries (Path.Max.Retrans) for the SCTP
            association that TextPass maintains with the remote SUA ASP.
            Default is 15." 
        ::= { suaAspEntry 30 }

    suaAspSctpMaxAssociationRetransmits OBJECT-TYPE
        SYNTAX  SctpRetransmits
        ACCESS  read-write
        STATUS  mandatory
        DESCRIPTION
            "Maximum number of association retries (Association.Max.Retrans) for 
            the SCTP association that TextPass maintains with the remote SUA 
            ASP. Default is 20." 
        ::= { suaAspEntry 31 }

    suaAspSctpMaxConnectAttempts OBJECT-TYPE
        SYNTAX  SctpMaxConnectAttempts
        ACCESS  read-write
        STATUS  mandatory
        DESCRIPTION
            "Maximum number of connect attempts (Max.Init.Retransmits) for 
            the SCTP association that TextPass maintains with the remote SUA 
            ASP. Default is 8."         
        ::= { suaAspEntry 32 }

    suaAspSctpMaxAllowedInboundStreams OBJECT-TYPE
        SYNTAX  SctpStreams
        ACCESS  read-write
        STATUS  mandatory
        DESCRIPTION
            "Maximum number of inbound streams that TextPass allows for the SCTP
            SCTP association that TextPass maintains with the remote SUA ASP. 
            Default is 255."         
        ::= { suaAspEntry 33 }

    suaAspSctpPreferredOutboundStreams OBJECT-TYPE
        SYNTAX  SctpStreams
        ACCESS  read-write
        STATUS  mandatory
        DESCRIPTION
            "Number of outbound streams that TextPass prefers for the SCTP
            SCTP association that TextPass maintains with the remote SUA ASP. 
            Default is 2."         
        ::= { suaAspEntry 34 }

    suaAspSctpInitiatingStartupEnabled OBJECT-TYPE
        SYNTAX  Boolean
        ACCESS  read-write
        STATUS  mandatory
        DESCRIPTION
            "Identifier specifying whether TextPass should initiate 
            establishment of SCTP association. When set to 'true', TextPass
            actively tries to establish the association by sending out INIT
            chunks and responding with INIT ACK chunks when receiving INIT
            chunks. When set to 'false', TextPass has a passive role, meaning
            that it will only respond to inbound INIT chunks. Default is 
            'true'."
        ::= { suaAspEntry 35 }

    suaAspSctpSackDelay OBJECT-TYPE
        SYNTAX  SctpSackDelay
        ACCESS  read-write
        STATUS  mandatory
        DESCRIPTION
            "Time (in ms) to wait before acknowledging SCTP DATA chunks. A
            value of 0 (default) means use the system default, which tends
            to be 200ms. This setting only has an effect for newly created
            SCTP associations, and only when running on Linux/TPD. On
            Solaris, this setting is ignored."
        ::= { suaAspEntry 38 }

    suaAspSctpOperationalState OBJECT-TYPE
        SYNTAX  SctpOperationalState
        ACCESS  read-write
        STATUS  mandatory
        DESCRIPTION
            "Operation state of the SCTP association that TextPass maintains
            with the remote SUA ASP."
        ::= { suaAspEntry 41 }

    suaAspSctpNegotiatedInboundStreams OBJECT-TYPE
        SYNTAX  SctpStreams
        ACCESS  read-write
        STATUS  mandatory
        DESCRIPTION
            "Number of inbound streams for the SCTP association that TextPass 
            maintains with the remote SUA ASP. This number results from the 
            negotiation between TextPass and the remote SUA ASP."
        ::= { suaAspEntry 42 }

    suaAspSctpNegotiatedOutboundStreams OBJECT-TYPE
        SYNTAX  SctpStreams
        ACCESS  read-write
        STATUS  mandatory
        DESCRIPTION
            "Number of outbound streams for the SCTP association that TextPass 
            maintains with the remote SUA ASP. This number results from the 
            negotiation between TextPass and the remote SUA ASP."
        ::= { suaAspEntry 43 }

    suaAspSctpUpTime OBJECT-TYPE
        SYNTAX  Gauge
        ACCESS  read-only
        STATUS  mandatory
        DESCRIPTION
            "Up time, expressed in number of seconds, for the SCTP association 
            that TextPass maintains with the remote SUA ASP."
        ::= { suaAspEntry 44 }

    suaAspSctpDownTime OBJECT-TYPE
        SYNTAX  Gauge
        ACCESS  read-only
        STATUS  mandatory
        DESCRIPTION
            "Down time, expressed in number of seconds, for the SCTP association 
            that TextPass maintains with the remote SUA ASP."
        ::= { suaAspEntry 45 }

    suaAspSctpInboundTsn OBJECT-TYPE
        SYNTAX  SctpTsn
        ACCESS  read-write
        STATUS  mandatory
        DESCRIPTION
            "Current value of the Transmission Sequence Number (TSN) for the 
            inbound direction of the association that TextPass maintains with
            the remote SUA ASP."
        ::= { suaAspEntry 46 }

    suaAspSctpOutboudTsn OBJECT-TYPE
        SYNTAX  SctpTsn
        ACCESS  read-write
        STATUS  mandatory
        DESCRIPTION
            "Current value of the Transmission Sequence Number (TSN) for the 
            outbound direction of the association that TextPass maintains with
            the remote SUA ASP."
        ::= { suaAspEntry 47 }

    suaAspSctpTsnCumulativeAck OBJECT-TYPE
        SYNTAX  SctpTsn
        ACCESS  read-write
        STATUS  mandatory
        DESCRIPTION
            "The Transmission Sequence Number (TSN) of the last DATA chunk that 
            the SUA ASP acknowledged via the Cumulative TSN Ack field of a SACK."
        ::= { suaAspEntry 48 }

    suaAspSctpLocalReceiveWindow OBJECT-TYPE
        SYNTAX  SctpWindowSize
        ACCESS  read-write
        STATUS  mandatory
        DESCRIPTION
            "Current value of the receiver window (rwnd) on TextPass for the 
            association that TextPass maintains with the remote SUA ASP."
        ::= { suaAspEntry 49 }

    suaAspSctpRemoteReceiveWindow OBJECT-TYPE
        SYNTAX  SctpWindowSize
        ACCESS  read-write
        STATUS  mandatory
        DESCRIPTION
            "Current value of the receiver window (rwnd) on remote SUA ASP for 
            the association that TextPass maintains with the remote SUA ASP."
        ::= { suaAspEntry 50 }

    suaAspSctpCongestionWindow OBJECT-TYPE
        SYNTAX  SctpWindowSize
        ACCESS  read-write
        STATUS  mandatory
        DESCRIPTION
            "Current value of the congestion window (cwnd) for the association 
            that TextPass maintains with the remote SUA ASP."
        ::= { suaAspEntry 51 }

    suaAspSctpRoundTripTime OBJECT-TYPE
        SYNTAX  SctpRoundTripTime
        ACCESS  read-write
        STATUS  mandatory
        DESCRIPTION
            "Current value of the round trip time (RTT) for primary address of 
            the SCTP association that TextPass maintains with the remote SUA 
            ASP."
        ::= { suaAspEntry 52 }

    suaAspSctpRetransmissionTimeout OBJECT-TYPE
        SYNTAX  SctpRetransmitTimeout
        ACCESS  read-write
        STATUS  mandatory
        DESCRIPTION
            "Current value of the retransmission timeout (RTO) for the primary 
            destination of the SCTP association that TextPass maintains with the 
            remote SUA ASP."
        ::= { suaAspEntry 53 }

    suaAspSctpSmoothedLinkQuality OBJECT-TYPE
        SYNTAX  SctpSmoothedLinkQuality
        ACCESS  read-write
        STATUS  mandatory
        DESCRIPTION
            "Current value of the smoothed link quality indicator for the 
            primary destination of the SCTP association that TextPass maintains 
            with the remote SUA ASP. Smoothed link quality is a proprietary 
            measurement that indicates the quality of a path."
        ::= { suaAspEntry 54 }

    suaAspSctpT3RtxBasedRetransmitCounter OBJECT-TYPE
        SYNTAX  Counter
        ACCESS  read-write
        STATUS  mandatory
        DESCRIPTION
            "Counter specifying the number of retransmits resulting from an 
            expiration of T3-rtx timer on the SCTP association that TextPass 
            maintains with the remote SUA ASP." 
        ::= { suaAspEntry 55 }

    suaAspSctpSackBasedRetransmitCounter OBJECT-TYPE
        SYNTAX  Counter
        ACCESS  read-write
        STATUS  mandatory
        DESCRIPTION
            "Counter specifying the number of retransmits resulting from errors 
            reported by a SACK chunk on the SCTP association that TextPass 
            maintains with the remote SUA ASP." 
        ::= { suaAspEntry 56 }

    suaAspSctpDataChunkRetransmitCounter OBJECT-TYPE
        SYNTAX  Counter
        ACCESS  read-write
        STATUS  mandatory
        DESCRIPTION
            "Counter specifying the number of DATA chunks retransmits on the 
            SCTP association that TextPass maintains with the remote SUA ASP."
        ::= { suaAspEntry 57 }

    suaAspSctpPrimaryChangeOverCounter OBJECT-TYPE
        SYNTAX  Counter
        ACCESS  read-write
        STATUS  mandatory
        DESCRIPTION
            "Counter specifying the number of primary path changeovers on the 
            SCTP association that TextPass maintains with the remote SUA ASP."
        ::= { suaAspEntry 58 }

    suaAspSctpSentDataByteCounter OBJECT-TYPE
        SYNTAX  Counter
        ACCESS  read-write
        STATUS  mandatory
        DESCRIPTION
            "Counter specifying the number of data bytes sent on the SCTP 
            association that TextPass maintains with the remote SUA ASP."
        ::= { suaAspEntry 71 }

    suaAspSctpRecvDataByteCounter OBJECT-TYPE
        SYNTAX  Counter
        ACCESS  read-write
        STATUS  mandatory
        DESCRIPTION
            "Counter specifying the number of data bytes received on the SCTP 
            association that TextPass maintains with the remote SUA ASP."
        ::= { suaAspEntry 72 }

    suaAspSctpSentSackWithGapCounter OBJECT-TYPE
        SYNTAX  Counter
        ACCESS  read-write
        STATUS  mandatory
        DESCRIPTION
            "Counter specifying the number of SACK chunks sent with a gap on the 
            SCTP association that TextPass maintains with the remote SUA ASP."
        ::= { suaAspEntry 73 }

    suaAspSctpRecvSackWithGapCounter OBJECT-TYPE
        SYNTAX  Counter
        ACCESS  read-write
        STATUS  mandatory
        DESCRIPTION
            "Counter specifying the number of SACK chunks received with a gap on  
            the SCTP association that TextPass maintains with the remote SUA 
            ASP."
        ::= { suaAspEntry 74 }

    suaAspSctpRecvDataChunkDiscardedCounter OBJECT-TYPE
        SYNTAX  Counter
        ACCESS  read-write
        STATUS  mandatory
        DESCRIPTION
            "Counter specifying the number of received DATA chunks that have 
            been discarded for the SCTP association that TextPass maintains with 
            the remote SUA ASP."
        ::= { suaAspEntry 75 }

    suaAspSctpSentDataChunkDroppedCounter OBJECT-TYPE
        SYNTAX  Counter
        ACCESS  read-write
        STATUS  mandatory
        DESCRIPTION
            "Counter specifying the number of sent DATA chunks that have been 
            dropped for the SCTP association that TextPass maintains with the 
            remote SUA ASP."
        ::= { suaAspEntry 76 }

    suaAspSctpSentDataChunkCounter OBJECT-TYPE
        SYNTAX  Counter
        ACCESS  read-write
        STATUS  mandatory
        DESCRIPTION
            "Counter specifying the number of DATA chunks sent on the SCTP 
            association that TextPass maintains with the remote SUA ASP."
        ::= { suaAspEntry 81 }

    suaAspSctpRecvDataChunkCounter OBJECT-TYPE
        SYNTAX  Counter
        ACCESS  read-write
        STATUS  mandatory
        DESCRIPTION
            "Counter specifying the number of DATA chunks received on the SCTP 
            association that TextPass maintains with the remote SUA ASP."
        ::= { suaAspEntry 82 }

    suaAspSctpSentInitChunkCounter OBJECT-TYPE
        SYNTAX  Counter
        ACCESS  read-write
        STATUS  mandatory
        DESCRIPTION
            "Counter specifying the number of INIT chunks sent on the SCTP 
            association that TextPass maintains with the remote SUA ASP."
        ::= { suaAspEntry 83 }

    suaAspSctpRecvInitChunkCounter OBJECT-TYPE
        SYNTAX  Counter
        ACCESS  read-write
        STATUS  mandatory
        DESCRIPTION
            "Counter specifying the number of INIT chunks received on the SCTP 
            association that TextPass maintains with the remote SUA ASP."
        ::= { suaAspEntry 84 }

    suaAspSctpSentInitAckChunkCounter OBJECT-TYPE
        SYNTAX  Counter
        ACCESS  read-write
        STATUS  mandatory
        DESCRIPTION
            "Counter specifying the number of INIT ACK chunks sent on the SCTP 
            association that TextPass maintains with the remote SUA ASP."
        ::= { suaAspEntry 85 }

    suaAspSctpRecvInitAckChunkCounter OBJECT-TYPE
        SYNTAX  Counter
        ACCESS  read-write
        STATUS  mandatory
        DESCRIPTION
            "Counter specifying the number of INIT ACK chunks received on the  
            SCTP association that TextPass maintains with the remote SUA ASP."
        ::= { suaAspEntry 86 }

    suaAspSctpSentSackChunkCounter OBJECT-TYPE
        SYNTAX  Counter
        ACCESS  read-write
        STATUS  mandatory
        DESCRIPTION
            "Counter specifying the number of SACK chunks sent on the SCTP 
            association that TextPass maintains with the remote SUA ASP."
        ::= { suaAspEntry 87 }

    suaAspSctpRecvSackChunkCounter OBJECT-TYPE
        SYNTAX  Counter
        ACCESS  read-write
        STATUS  mandatory
        DESCRIPTION
            "Counter specifying the number of SACK chunks received on the SCTP 
            association that TextPass maintains with the remote SUA ASP."
        ::= { suaAspEntry 88 }

    suaAspSctpSentHeartbeatCounter OBJECT-TYPE
        SYNTAX  Counter
        ACCESS  read-write
        STATUS  mandatory
        DESCRIPTION
            "Counter specifying the number of HEARTBEAT chunks sent on the SCTP 
            association that TextPass maintains with the remote SUA ASP."
        ::= { suaAspEntry 89 }

    suaAspSctpRecvHeartbeatCounter OBJECT-TYPE
        SYNTAX  Counter
        ACCESS  read-write
        STATUS  mandatory
        DESCRIPTION
            "Counter specifying the number of HEARTBEAT chunks received on the  
            SCTP association that TextPass maintains with the remote SUA ASP."
        ::= { suaAspEntry 90 }

    suaAspSctpSentHeartbeatAckCounter OBJECT-TYPE
        SYNTAX  Counter
        ACCESS  read-write
        STATUS  mandatory
        DESCRIPTION
            "Counter specifying the number of HEARTBEAT ACK chunks sent on the 
            SCTP association that TextPass maintains with the remote SUA ASP."
        ::= { suaAspEntry 91 }

    suaAspSctpRecvHeartbeatAckCounter OBJECT-TYPE
        SYNTAX  Counter
        ACCESS  read-write
        STATUS  mandatory
        DESCRIPTION
            "Counter specifying the number of HEARTBEAT ACK chunks received on 
            the SCTP association that TextPass maintains with the remote SUA 
            ASP."
        ::= { suaAspEntry 92 }

    suaAspSctpSentAbortChunkCounter OBJECT-TYPE
        SYNTAX  Counter
        ACCESS  read-write
        STATUS  mandatory
        DESCRIPTION
            "Counter specifying the number of ABORT chunks sent on the SCTP 
            association that TextPass maintains with the remote SUA ASP."
        ::= { suaAspEntry 93 }

    suaAspSctpRecvAbortChunkCounter OBJECT-TYPE
        SYNTAX  Counter
        ACCESS  read-write
        STATUS  mandatory
        DESCRIPTION
            "Counter specifying the number of ABORT chunks received on the  
            SCTP association that TextPass maintains with the remote SUA ASP."
        ::= { suaAspEntry 94 }

    suaAspSctpSentShutdownChunkCounter OBJECT-TYPE
        SYNTAX  Counter
        ACCESS  read-write
        STATUS  mandatory
        DESCRIPTION
            "Counter specifying the number of SHUTDOWN chunks sent on the SCTP 
            association that TextPass maintains with the remote SUA ASP."
        ::= { suaAspEntry 95 }

    suaAspSctpRecvShutdownChunkCounter OBJECT-TYPE
        SYNTAX  Counter
        ACCESS  read-write
        STATUS  mandatory
        DESCRIPTION
            "Counter specifying the number of SHUTDOWN chunks received on the  
            SCTP association that TextPass maintains with the remote SUA ASP."
        ::= { suaAspEntry 96 }

    suaAspSctpSentShutdownAckChunkCounter OBJECT-TYPE
        SYNTAX  Counter
        ACCESS  read-write
        STATUS  mandatory
        DESCRIPTION
            "Counter specifying the number of SHUTDOWN ACK chunks sent on the  
            SCTP association that TextPass maintains with the remote SUA ASP."
        ::= { suaAspEntry 97 }

    suaAspSctpRecvShutdownAckChunkCounter OBJECT-TYPE
        SYNTAX  Counter
        ACCESS  read-write
        STATUS  mandatory
        DESCRIPTION
            "Counter specifying the number of SHUTDOWN ACK chunks received on   
            the SCTP association that TextPass maintains with the remote SUA 
            ASP."
        ::= { suaAspEntry 98 }

    suaAspSctpSentErrorChunkCounter OBJECT-TYPE
        SYNTAX  Counter
        ACCESS  read-write
        STATUS  mandatory
        DESCRIPTION
            "Counter specifying the number of ERROR chunks sent on the SCTP 
            association that TextPass maintains with the remote SUA ASP."
        ::= { suaAspEntry 99 }

    suaAspSctpRecvErrorChunkCounter OBJECT-TYPE
        SYNTAX  Counter
        ACCESS  read-write
        STATUS  mandatory
        DESCRIPTION
            "Counter specifying the number of ERROR chunks received on the SCTP 
            association that TextPass maintains with the remote SUA ASP."
        ::= { suaAspEntry 100 }

    suaAspSctpSentCookieEchoChunkCounter OBJECT-TYPE
        SYNTAX  Counter
        ACCESS  read-write
        STATUS  mandatory
        DESCRIPTION
            "Counter specifying the number of COOKIE ECHO chunks sent on the  
            SCTP association that TextPass maintains with the remote SUA ASP."
        ::= { suaAspEntry 101 }

    suaAspSctpRecvCookieEchoChunkCounter OBJECT-TYPE
        SYNTAX  Counter
        ACCESS  read-write
        STATUS  mandatory
        DESCRIPTION
            "Counter specifying the number of COOKIE ECHO chunks received on the  
            SCTP association that TextPass maintains with the remote SUA ASP."
        ::= { suaAspEntry 102 }

    suaAspSctpSentCookieAckChunkCounter OBJECT-TYPE
        SYNTAX  Counter
        ACCESS  read-write
        STATUS  mandatory
        DESCRIPTION
            "Counter specifying the number of COOKIE ACK chunks sent on the SCTP 
            association that TextPass maintains with the remote SUA ASP."
        ::= { suaAspEntry 103 }

    suaAspSctpRecvCookieAckChunkCounter OBJECT-TYPE
        SYNTAX  Counter
        ACCESS  read-write
        STATUS  mandatory
        DESCRIPTION
            "Counter specifying the number of COOKIE ACK chunks received on the  
            SCTP association that TextPass maintains with the remote SUA ASP."
        ::= { suaAspEntry 104 }

    suaAspSctpSentShutdownCompleteChunkCounter OBJECT-TYPE
        SYNTAX  Counter
        ACCESS  read-write
        STATUS  mandatory
        DESCRIPTION
            "Counter specifying the number of SHUTDOWN COMPLETE chunks sent on 
            the SCTP association that TextPass maintains with the remote SUA ASP."
        ::= { suaAspEntry 105 }

    suaAspSctpRecvShutdownCompleteChunkCounter OBJECT-TYPE
        SYNTAX  Counter
        ACCESS  read-write
        STATUS  mandatory
        DESCRIPTION
            "Counter specifying the number of SHUTDOWN COMPLETE chunks received 
            on the SCTP association that TextPass maintains with the remote SUA 
            ASP."
        ::= { suaAspEntry 106 }

    suaAspSctpInvalidStreamIdErrorCounter OBJECT-TYPE
        SYNTAX  Counter
        ACCESS  read-write
        STATUS  mandatory
        DESCRIPTION
            "Counter specifying the number of 'Invalid Stream Id' ERROR chunks 
            received on the SCTP association that TextPass maintains with the 
            remote SUA ASP."
        ::= { suaAspEntry 121 }

    suaAspSctpMissingMandatoryParameterErrorCounter OBJECT-TYPE
        SYNTAX  Counter
        ACCESS  read-write
        STATUS  mandatory
        DESCRIPTION
            "Counter specifying the number of 'Missing Mandatory Parameter' 
            ERROR chunks received on the SCTP association that TextPass 
            maintains with the remote SUA ASP."
        ::= { suaAspEntry 122 }

    suaAspSctpStaleCookieErrorCounter OBJECT-TYPE
        SYNTAX  Counter
        ACCESS  read-write
        STATUS  mandatory
        DESCRIPTION
            "Counter specifying the number of 'Stale Cookie' ERROR chunks 
            received on the SCTP association that TextPass maintains with the 
            remote SUA ASP."
        ::= { suaAspEntry 123 }

    suaAspSctpOutOfResourceErrorCounter OBJECT-TYPE
        SYNTAX  Counter
        ACCESS  read-write
        STATUS  mandatory
        DESCRIPTION
            "Counter specifying the number of 'Out Of Resource' ERROR chunks 
            received on the SCTP association that TextPass maintains with the 
            remote SUA ASP."
        ::= { suaAspEntry 124 }

    suaAspSctpUnresolvableAddressErrorCounter OBJECT-TYPE
        SYNTAX  Counter
        ACCESS  read-write
        STATUS  mandatory
        DESCRIPTION
            "Counter specifying the number of 'Unresolvable Address' ERROR 
            chunks received on the SCTP association that TextPass maintains with 
            the remote SUA ASP."
        ::= { suaAspEntry 125 }

    suaAspSctpUnrecognisedChunkTypeErrorCounter OBJECT-TYPE
        SYNTAX  Counter
        ACCESS  read-write
        STATUS  mandatory
        DESCRIPTION
            "Counter specifying the number of 'Unrecognised Chunk Type' ERROR 
            chunks received on the SCTP association that TextPass maintains with 
            the remote SUA ASP."
        ::= { suaAspEntry 126 }

    suaAspSctpInvalidMandatoryParameterErrorCounter OBJECT-TYPE
        SYNTAX  Counter
        ACCESS  read-write
        STATUS  mandatory
        DESCRIPTION
            "Counter specifying the number of 'Invalid Mandatory Parameter' 
            ERROR chunks received on the SCTP association that TextPass 
            maintains with the remote SUA ASP."
        ::= { suaAspEntry 127 }

    suaAspSctpUnrecognisedParamtersErrorCounter OBJECT-TYPE
        SYNTAX  Counter
        ACCESS  read-write
        STATUS  mandatory
        DESCRIPTION
            "Counter specifying the number of 'Unrecognised Parameters' ERROR
            chunks received on the SCTP association that TextPass maintains with 
            the remote SUA ASP."
        ::= { suaAspEntry 128 }

    suaAspSctpNoUserDataErrorCounter OBJECT-TYPE
        SYNTAX  Counter
        ACCESS  read-write
        STATUS  mandatory
        DESCRIPTION
            "Counter specifying the number of 'No User Data' ERROR chunks 
            received on the SCTP association that TextPass maintains with 
            the remote SUA ASP."
        ::= { suaAspEntry 129 }

    suaAspSctpCookieRecvWhileShuttingDownErrorCounter OBJECT-TYPE
        SYNTAX  Counter
        ACCESS  read-write
        STATUS  mandatory
        DESCRIPTION
            "Counter specifying the number of 'Cookie Received While Shutting 
            Down' ERROR chunks received on the SCTP association that TextPass 
            maintains with the remote SUA ASP."
        ::= { suaAspEntry 130 }


    -- the SUA ASP remote IP address table

    suaAspRemoteAddressTable OBJECT-TYPE
        SYNTAX  SEQUENCE OF SuaAspRemoteAddressEntry
        ACCESS  not-accessible
        STATUS  mandatory
        DESCRIPTION
            "Table containing info about IP addresses of remote SUA Application 
            Servers Processes (ASP's)."
        ::= { sua 22 }

    suaAspRemoteAddressEntry OBJECT-TYPE
        SYNTAX  SuaAspRemoteAddressEntry
        ACCESS  not-accessible
        STATUS  mandatory
        DESCRIPTION
            "Entry of table containing info about IP addresses of remote SUA 
            Application Servers Processes (ASP's)."
        INDEX   { suaAspIndex, suaAspRemoteAddressIndex }
        ::= { suaAspRemoteAddressTable 1 }

    SuaAspRemoteAddressEntry ::=
        SEQUENCE {
            suaAspRemoteAddressIndex               SuaRemoteAddressTableIndex,
            suaAspRemoteAddressAdminState          AdminState,
            suaAspRemoteAddressOperationalState    RemoteAddressOperationalState,
            suaAspRemoteAddressSpec                IpAddressSpec,
            suaAspRemoteAddressSctpErrorCounter    Counter,
            suaAspRemoteAddressSctpSentHeartbeatCounter Counter,
            suaAspRemoteAddressSctpRecvHeartbeatCounter Counter,
            suaAspRemoteAddressSctpSentHeartbeatAckCounter Counter,
            suaAspRemoteAddressSctpRecvHeartbeatAckCounter Counter,
            suaAspRemoteAddressSctpRoundTripTime   SctpRoundTripTime,
            suaAspRemoteAddressSctpRetransmissionTimeout SctpRetransmitTimeout,
            suaAspRemoteAddressSctpSmoothedLinkQuality SctpSmoothedLinkQuality
        }    

    suaAspRemoteAddressIndex OBJECT-TYPE
        SYNTAX  SuaRemoteAddressTableIndex
        ACCESS  read-write
        STATUS  mandatory
        DESCRIPTION
            "Index of entry in table with IP addresses for remote SUA ASP."
        ::= { suaAspRemoteAddressEntry 1 }

    suaAspRemoteAddressAdminState OBJECT-TYPE
        SYNTAX  AdminState
        ACCESS  read-write
        STATUS  mandatory
        DESCRIPTION
            "Administrative state of IP address of remote SUA ASP."
        ::= { suaAspRemoteAddressEntry 2 }

    suaAspRemoteAddressOperationalState OBJECT-TYPE
        SYNTAX  RemoteAddressOperationalState
        ACCESS  read-write
        STATUS  mandatory
        DESCRIPTION
            "Operational state of IP address of remote SUA ASP."
        ::= { suaAspRemoteAddressEntry 3 }

    suaAspRemoteAddressSpec OBJECT-TYPE
        SYNTAX  IpAddressSpec
        ACCESS  read-write
        STATUS  mandatory
        DESCRIPTION
            "IPv4 or IPv6 specification for IP address of remote SUA ASP."
        ::= { suaAspRemoteAddressEntry 11 }

    suaAspRemoteAddressSctpErrorCounter OBJECT-TYPE
        SYNTAX  Counter
        ACCESS  read-write
        STATUS  mandatory
        DESCRIPTION
            "Counter specifying number of SCTP errors for IP address of
            remote SUA ASP."
        ::= { suaAspRemoteAddressEntry 21 }

    suaAspRemoteAddressSctpSentHeartbeatCounter OBJECT-TYPE
        SYNTAX  Counter
        ACCESS  read-write
        STATUS  mandatory
        DESCRIPTION
            "Counter specifying the number of HEARTBEAT chunks sent to IP 
            address of remote SUA ASP."
        ::= { suaAspRemoteAddressEntry 31 }

    suaAspRemoteAddressSctpRecvHeartbeatCounter OBJECT-TYPE
        SYNTAX  Counter
        ACCESS  read-write
        STATUS  mandatory
        DESCRIPTION
            "Counter specifying the number of HEARTBEAT chunks received from IP 
            address of remote SUA ASP."
        ::= { suaAspRemoteAddressEntry 32 }

    suaAspRemoteAddressSctpSentHeartbeatAckCounter OBJECT-TYPE
        SYNTAX  Counter
        ACCESS  read-write
        STATUS  mandatory
        DESCRIPTION
            "Counter specifying the number of HEARTBEAT ACK chunks sent to IP
            address of remote SUA ASP."
        ::= { suaAspRemoteAddressEntry 33 }

    suaAspRemoteAddressSctpRecvHeartbeatAckCounter OBJECT-TYPE
        SYNTAX  Counter
        ACCESS  read-write
        STATUS  mandatory
        DESCRIPTION
            "Counter specifying the number of HEARTBEAT ACK chunks received from
            IP address of remote SUA ASP."
        ::= { suaAspRemoteAddressEntry 34 }

    suaAspRemoteAddressSctpRoundTripTime OBJECT-TYPE
        SYNTAX  SctpRoundTripTime
        ACCESS  read-write
        STATUS  mandatory
        DESCRIPTION
            "Current value of the round trip time (RTT) for IP address of remote 
            SUA ASP."
        ::= { suaAspRemoteAddressEntry 41 }

    suaAspRemoteAddressSctpRetransmissionTimeout OBJECT-TYPE
        SYNTAX  SctpRetransmitTimeout
        ACCESS  read-write
        STATUS  mandatory
        DESCRIPTION
            "Current value of the retransmission timeout (RTO) for the IP  
            address of remote SUA ASP."
        ::= { suaAspRemoteAddressEntry 42 }

    suaAspRemoteAddressSctpSmoothedLinkQuality OBJECT-TYPE
        SYNTAX  SctpSmoothedLinkQuality
        ACCESS  read-write
        STATUS  mandatory
        DESCRIPTION
            ""
        ::= { suaAspRemoteAddressEntry 43 }


    -- the SUA AS table
    
    suaAsTable OBJECT-TYPE
        SYNTAX  SEQUENCE OF SuaAsEntry
        ACCESS  not-accessible
        STATUS  mandatory
        DESCRIPTION
            "Table containing info about remote SUA Application Servers (AS's)."
        ::= { sua 26 }

    suaAsEntry OBJECT-TYPE
        SYNTAX  SuaAsEntry
        ACCESS  not-accessible
        STATUS  mandatory
        DESCRIPTION
            "Entry of table containing info about remote SUA Application Servers 
            (AS's)."
        INDEX   { suaAsIndex }
        ::= { suaAsTable 1 }

    SuaAsEntry ::=
        SEQUENCE {
            suaAsIndex                             SuaAsTableIndex,
            suaAsAdminState                        AdminState,
            suaAsOperationalState                  SuaAsOperationalState,
            suaAsName                              NameString,
            suaAsRoutingContext                    RoutingContext
        }
        

    suaAsIndex OBJECT-TYPE
        SYNTAX  SuaAsTableIndex
        ACCESS  read-write
        STATUS  mandatory
        DESCRIPTION
            "Index of SUA AS table."
        ::= { suaAsEntry 1 }

    suaAsAdminState OBJECT-TYPE
        SYNTAX  AdminState
        ACCESS  read-write
        STATUS  mandatory
        DESCRIPTION
            "Administrative state of remote SUA AS."
        ::= { suaAsEntry 2 }

    suaAsOperationalState OBJECT-TYPE
        SYNTAX  SuaAsOperationalState
        ACCESS  read-write
        STATUS  mandatory
        DESCRIPTION
            "Operational state of remote SUA AS."
        ::= { suaAsEntry 3 }

    suaAsName OBJECT-TYPE
        SYNTAX  NameString
        ACCESS  read-write
        STATUS  mandatory
        DESCRIPTION
            "Name of remote SUA AS."
        ::= { suaAsEntry 4 }

    suaAsRoutingContext OBJECT-TYPE
        SYNTAX  RoutingContext
        ACCESS  read-write
        STATUS  mandatory
        DESCRIPTION
            "Routing context associated with remote SUA AS."
        ::= { suaAsEntry 11 }


    -- the SUA AS instance table
    
    suaAsInstanceTable OBJECT-TYPE
        SYNTAX  SEQUENCE OF SuaAsInstanceEntry
        ACCESS  not-accessible
        STATUS  mandatory
        DESCRIPTION
            "Table containing info about SUA AS instances. This table determines
            which remote SUA AS's are active for each remote SUA ASP."
        ::= { sua 27 }

    suaAsInstanceEntry OBJECT-TYPE
        SYNTAX  SuaAsInstanceEntry
        ACCESS  not-accessible
        STATUS  mandatory
        DESCRIPTION
            "Entry of table containing info about SUA AS instances."
        INDEX   { suaAsIndex, suaAspIndex  }
        ::= { suaAsInstanceTable 1 }

    SuaAsInstanceEntry ::=
        SEQUENCE {
            suaAsInstanceAsIndex                   SuaAsTableIndex,
            suaAsInstanceAspIndex                  SuaAspTableIndex,
            suaAsInstanceAdminState                AdminState,
            suaAsInstanceOperationalState          SuaAsInstanceOperationalState
        }
        
    suaAsInstanceAsIndex OBJECT-TYPE
        SYNTAX  SuaAsTableIndex
        ACCESS  read-write
        STATUS  mandatory
        DESCRIPTION
            "Index of remote SUA AS in remote SUA AS table."
        ::= { suaAsInstanceEntry 1 }

    suaAsInstanceAspIndex OBJECT-TYPE
        SYNTAX  SuaAspTableIndex
        ACCESS  read-write
        STATUS  mandatory
        DESCRIPTION
            "Index of remote SUA ASP in remote SUA ASP table."
        ::= { suaAsInstanceEntry 2 }

    suaAsInstanceAdminState OBJECT-TYPE
        SYNTAX  AdminState
        ACCESS  read-write
        STATUS  mandatory
        DESCRIPTION
            "Administrative state of remote AS instance."
        ::= { suaAsInstanceEntry 3 }

    suaAsInstanceOperationalState OBJECT-TYPE
        SYNTAX  SuaAsInstanceOperationalState
        ACCESS  read-write
        STATUS  mandatory
        DESCRIPTION
            "Operational state of remote AS instance."
        ::= { suaAsInstanceEntry 4 }

    -- the MTP traps
    
    trunkOperationalStateChanged TRAP-TYPE
        ENTERPRISE mtp
        VARIABLES { mtpTrunkOperationalState, deviceType }
        DESCRIPTION
            "Operational state of SS7 trunk has changed"
        ::= 1
    
    linkOperationalStateChanged TRAP-TYPE
        ENTERPRISE mtp
        VARIABLES { mtpLinkOperationalState, mtpLinkSetName, mtpLinkCode, mtpLinkTrunk, mtpLinkTimeSlot, deviceType }
        DESCRIPTION
            "Operational state of MTP link has changed"
        ::= 2
    
    linkSetOperationalStateChanged TRAP-TYPE
        ENTERPRISE mtp
        VARIABLES { mtpLinkSetOperationalState, mtpLinkSetName, deviceType }
        DESCRIPTION
            "Operational state of MTP linkset has changed"
        ::= 3
    
    destinationOperationalStateChanged TRAP-TYPE
        ENTERPRISE mtp
        VARIABLES { mtpDestinationOperationalState, mtpDestinationName, mtpDestinationPointCode, deviceType }
        DESCRIPTION
            "Operational state of MTP destination has changed"
        ::= 4
    
    routeOperationalStateChanged TRAP-TYPE
        ENTERPRISE mtp
        VARIABLES { mtpRouteOperationalState, mtpDestinationName, mtpRouteLinkSet, deviceType }
        DESCRIPTION
            "Operational state of MTP route has changed"
        ::= 5
          
    linkCodeMismatch TRAP-TYPE
        ENTERPRISE mtp
        VARIABLES { mtpLinkCodeError, mtpLinkSetName, mtpLinkCode, mtpLinkTrunk, mtpLinkTimeSlot, deviceType }
        DESCRIPTION
            "Mismatch in configuration of link's SLC. Value for SLC as 
             configured on TextPass device and value for SLC as configured on 
             adjacent differ."
        ::= 6
        
    linkTextPassPcMismatch TRAP-TYPE
        ENTERPRISE mtp
        VARIABLES { mtpLinkTextPassPcError, mtpLinkSetName, mtpLinkCode, mtpLinkTrunk, mtpLinkTimeSlot, deviceType }
        DESCRIPTION
            "Mismatch in configuration of TextPass's point code. Value for this 
            point code as configured on TextPass device and value for this point 
            code as configured on adjacent differ."
        ::= 7
        
    linkAdjacentPcMismatch TRAP-TYPE
        ENTERPRISE mtp
        VARIABLES { mtpLinkAdjacentPcError, mtpLinkSetName, mtpLinkCode, mtpLinkTrunk, mtpLinkTimeSlot, deviceType }
        DESCRIPTION
            "Mismatch in configuration of TextPass's point code. Value for this 
            point code as configured on TextPass device and value for this point 
            code as configured on adjacent differ."
        ::= 8
        
    linkNetworkIndicatorMismatch TRAP-TYPE
        ENTERPRISE mtp
        VARIABLES { mtpLinkNetworkIndicatorError, mtpLinkSetName, mtpLinkCode, mtpLinkTrunk, mtpLinkTimeSlot, deviceType }
        DESCRIPTION
            "Mismatch in configuration of TextPass's point code. Value for this 
            point code as configured on TextPass device and value for this point 
            code as configured on adjacent differ."
        ::= 9 
        
    linkRxUtilisationGrowing TRAP-TYPE
        ENTERPRISE mtp
        VARIABLES { mtpLinkRxUtilisation, mtpLinkSetName, mtpLinkCode, mtpLinkTrunk, mtpLinkTimeSlot, deviceType }
        DESCRIPTION
            "Link utilisation on the receiving stream is growing and just hit a 
            threshold. Thresholds can be configured at mtpProperties."
        ::= 10

    linkRxUtilisationShrinking TRAP-TYPE
        ENTERPRISE mtp
        VARIABLES { mtpLinkRxUtilisation, mtpLinkSetName, mtpLinkCode, mtpLinkTrunk, mtpLinkTimeSlot, deviceType }
        DESCRIPTION
            "Link utilisation on the receiving stream is shrinking and just hit a 
            threshold. Thresholds can be configured at mtpProperties."
        ::= 11

    linkTxUtilisationGrowing TRAP-TYPE
        ENTERPRISE mtp
        VARIABLES { mtpLinkTxUtilisation, mtpLinkSetName, mtpLinkCode, mtpLinkTrunk, mtpLinkTimeSlot, deviceType }
        DESCRIPTION
            "Link utilisation on the transmitting stream is growing and just hit a 
            threshold. Thresholds can be configured at mtpProperties."
        ::= 12

    linkTxUtilisationShrinking TRAP-TYPE
        ENTERPRISE mtp
        VARIABLES { mtpLinkTxUtilisation, mtpLinkSetName, mtpLinkCode, mtpLinkTrunk, mtpLinkTimeSlot, deviceType }
        DESCRIPTION
            "Link utilisation on the transmitting stream is shrinking and just hit a 
            threshold. Thresholds can be configured at mtpProperties."
        ::= 13

    -- the SCCP traps
    
    stpOperationalStateChanged TRAP-TYPE
        ENTERPRISE sccp
        VARIABLES { sccpStpOperationalState, sccpStpName, sccpStpMtpDestination, deviceType }
        DESCRIPTION
            "Operational state of SCCP STP has changed"
        ::= 1

    -- the m3ua traps
    
    m3uaSgpOperationalStateChanged TRAP-TYPE
        ENTERPRISE m3ua
        VARIABLES { m3uaSgpOperationalState, deviceType }
        DESCRIPTION
            "Operational state of a M3UA SGP changed"
        ::= 1
    
    m3uaSgpSctpOperationalStateChanged TRAP-TYPE
        ENTERPRISE m3ua
        VARIABLES { m3uaSgpSctpOperationalState, deviceType }
        DESCRIPTION
            "Operational state of the SCTP association of a M3UA SGP changed"
        ::= 2

    m3uaSgpRemoteAddressOperationalStateChanged TRAP-TYPE
        ENTERPRISE m3ua
        VARIABLES { m3uaSgpRemoteAddressOperationalState, deviceType }
        DESCRIPTION
            "Operational state of a remote address of a M3UA SGP changed."
        ::= 3
    
    m3uaSgpActualSpcOperationalStateChanged TRAP-TYPE
        ENTERPRISE m3ua
        VARIABLES { m3uaSgpActualSpcOperationalState, deviceType }
        DESCRIPTION
            "Operational state of a M3UA SGP for the actual SPC of TextPass 
            changed."
        ::= 4
    
    m3uaSgpVirtualSpcOperationalStateChanged TRAP-TYPE
        ENTERPRISE m3ua
        VARIABLES { m3uaSgpVirtualSpcOperationalState, deviceType }
        DESCRIPTION
            "Operational state of a M3UA SGP for the virtual SPC of TextPass 
            changed."
        ::= 5

    m3uaAspOperationalStateChanged TRAP-TYPE
        ENTERPRISE m3ua
        VARIABLES { m3uaAspOperationalState, deviceType }
        DESCRIPTION
            "Operational state of a M3UA ASP changed"
        ::= 11
    
    m3uaAspSctpOperationalStateChanged TRAP-TYPE
        ENTERPRISE m3ua
        VARIABLES { m3uaAspSctpOperationalState, deviceType }
        DESCRIPTION
            "Operational state of the SCTP association of a M3UA ASP changed"
        ::= 12

    m3uaAspRemoteAddressOperationalStateChanged TRAP-TYPE
        ENTERPRISE m3ua
        VARIABLES { m3uaAspRemoteAddressOperationalState, deviceType }
        DESCRIPTION
            "Operational state of a remote address of a M3UA ASP changed."
        ::= 13
    
    m3uaAsOperationalStateChanged TRAP-TYPE
        ENTERPRISE m3ua
        VARIABLES { m3uaAsOperationalState, deviceType }
        DESCRIPTION
            "Operational state of a M3UA AS changed."
        ::= 14
    
    m3uaAsInstanceOperationalStateChanged TRAP-TYPE
        ENTERPRISE m3ua
        VARIABLES { m3uaAsInstanceOperationalState, deviceType }
        DESCRIPTION
            "Operational state of a M3UA AS instance changed."
        ::= 15

    -- the sua traps
    
    suaAspOperationalStateChanged TRAP-TYPE
        ENTERPRISE sua
        VARIABLES { suaAspOperationalState, deviceType }
        DESCRIPTION
            "Operational state of a SUA ASP changed"
        ::= 11
    
    suaAspSctpOperationalStateChanged TRAP-TYPE
        ENTERPRISE sua
        VARIABLES { suaAspSctpOperationalState, deviceType }
        DESCRIPTION
            "Operational state of the SCTP association of a SUA ASP changed"
        ::= 12

    suaAspRemoteAddressOperationalStateChanged TRAP-TYPE
        ENTERPRISE sua
        VARIABLES { suaAspRemoteAddressOperationalState, deviceType }
        DESCRIPTION
            "Operational state of a remote address of a SUA ASP changed."
        ::= 13
    
    suaAsOperationalStateChanged TRAP-TYPE
        ENTERPRISE sua
        VARIABLES { suaAsOperationalState, deviceType }
        DESCRIPTION
            "Operational state of a SUA AS changed."
        ::= 14
    
    suaAsInstanceOperationalStateChanged TRAP-TYPE
        ENTERPRISE sua
        VARIABLES { suaAsInstanceOperationalState, deviceType }
        DESCRIPTION
            "Operational state of a SUA AS instance changed."
        ::= 15
        
END

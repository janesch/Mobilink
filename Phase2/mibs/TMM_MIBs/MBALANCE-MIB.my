------------------------------------------------------------------------------
--
-- (c) Copyright 2001-2005 mBalance.
-- 
--  This MIB is proprietary to and embodies the confidential technology of
--  mBalance. Possession, use, duplication or dissemination of this MIB is 
--  authorized only pursuant to a valid written license from mBalance.
--
------------------------------------------------------------------------------
--
-- File    : MBALANCE-MIB.my
-- Release : R03.01
-- $Id: MBALANCE-MIB.my,v 1.5 2005/09/12 14:29:02 rgr Exp $
--
------------------------------------------------------------------------------

    MBALANCE-MIB DEFINITIONS ::= BEGIN
    
        IMPORTS
            enterprises
                FROM RFC1155-SMI;

        mbalance OBJECT IDENTIFIER ::= { enterprises 9679 }  
        textpass OBJECT IDENTIFIER ::= { mbalance 1 }
        textprobe OBJECT IDENTIFIER ::= { mbalance 2 }
        datastation OBJECT IDENTIFIER ::= { mbalance 3 }
    END

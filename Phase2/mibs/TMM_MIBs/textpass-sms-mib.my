------------------------------------------------------------------------------
--
-- (c) Copyright 2001-2007 mBalance.
--
--  This MIB is proprietary to and embodies the confidential technology of
--  mBalance. Possession, use, duplication or dissemination of this MIB is
--  authorized only pursuant to a valid written license from mBalance.
--
------------------------------------------------------------------------------
--
-- File    : textpass-sms-mib.my
-- Release : R04.01
-- $Id: textpass-sms-mib.my,v 1.412 2010/06/17 08:50:16 psheer Exp $
-- $Revision: 1.412 $
--------------------------------------------------------------------------------

TEXTPASS-SMS-MIB DEFINITIONS ::= BEGIN

    ----------------------------------------------------------------------------
    --                              I M P O R T S                             --
    ----------------------------------------------------------------------------

    IMPORTS
        IpAddress, Gauge, Counter
            FROM RFC1155-SMI
        TEXTUAL-CONVENTION
            FROM SNMPv2-TC
        textpass
            FROM MBALANCE-MIB
        deviceType, Boolean, IntervalTime, E164Address, NameString,
        OperationalState, TypeOfNumber, NumberingPlanIdentification,
        Throughput, Weight, Priority, TcpPort
            FROM TEXTPASS-GEN-MIB
        AmsQueueIndex,
        ApplicationTableIndex,
        ApplicationTimer,
        ApplicationAddressFormat,
        NotificationType,
        SmppError,
        SmppRetErrCode,
        X121Address,
        AddressString
            FROM TEXTPASS-APC-MIB
        OBJECT-TYPE
            FROM RFC-1212
        TRAP-TYPE
            FROM RFC-1215;

    ----------------------------------------------------------------------------
    --                                T Y P E S                               --
    ----------------------------------------------------------------------------

    ----------------------------------------------------------------------------
    --
    --  AddressFormat specifies how an address is encoded in an AT/SM or MT/SM.
    --  Possible encodings are:
    --  - transparent, address is taken from MO/SM or AO/SM without any 
    --    modification
    --  - national, address from MO/SM or AO/SM is converted to national format
    --  - international, address from MO/SM or AO/SM is converted to 
    --    international format
    --
    ----------------------------------------------------------------------------

    AddressFormat ::=
        INTEGER {
            transparent(0),
            national(1),
            international(2)
        }

    ----------------------------------------------------------------------------
    --
    --  AdminState has different meanings for reading and writing. When reading,
    --  the administrative state of a table entry is returned (which is either
    --  'active' or 'inactive'). Writing triggers an action as specified below:
    --
    --   ~~~~~~~~~~~~~~~~~~~~~~~~~~~~~~~~~~~~~~~~~~~~~~~~~~~~~~~~~~~~~~~~~~~~~~~
    --    Action              Description
    --   ~~~~~~~~~~~~~~~~~~~~~~~~~~~~~~~~~~~~~~~~~~~~~~~~~~~~~~~~~~~~~~~~~~~~~~~
    --    inactive            transit to 'inactive' state
    --    active              transit to 'active' state
    --    destroy             remove entry from table
    --    validateTransition  verify conditions that need to be satisfied to
    --                        transit the administrative state; in case the
    --                        state is 'inactive', conditions for a transition
    --                        to the 'active' state are checked; in case the
    --                        state is 'active', conditions for a transition to
    --                        the 'inactive' state are checked
    --    validateDestroy     verify conditions that need to be satisfied to
    --                        remove an entry form the table
    --   ~~~~~~~~~~~~~~~~~~~~~~~~~~~~~~~~~~~~~~~~~~~~~~~~~~~~~~~~~~~~~~~~~~~~~~~
    --
    ----------------------------------------------------------------------------

    AdminState ::=
        INTEGER {
            inactive(0),
            active(1),
            destroy(2),
            validateTransition(3),
            validateDestroy(4)
        }

    ----------------------------------------------------------------------------
    --
    --  AliasString defines the string used for application aliases
    --
    ----------------------------------------------------------------------------

    AliasString ::= TEXTUAL-CONVENTION
        DISPLAY-HINT "11a"
        STATUS mandatory
        DESCRIPTION "Strings used for application aliases"
        SYNTAX OCTET STRING (SIZE (0..11))
                                                            
    ----------------------------------------------------------------------------
    --
    --  AliasTableIndex defines the index for the appAliasTable
    --
    ----------------------------------------------------------------------------

    AliasTableIndex ::=
        INTEGER (1..10)
        
    ----------------------------------------------------------------------------
    --
    --  ExternalConditionIPIndex defines the index for the 
    --  externalConditionIPTable
    --
    ----------------------------------------------------------------------------

    ExternalConditionIPIndex ::=
        INTEGER (1..100)
        
    ----------------------------------------------------------------------------
    --
    --  AlphanumInConstruct defines how alphanumeric addresses are encoded
    --  in the construct version (MSISDN field) of an address in FCDRs.
    --
    ----------------------------------------------------------------------------

    AlphanumInConstruct ::=
        INTEGER {
            empty(0),
            numeric(1),
            alphanumeric(2)
        }

    ----------------------------------------------------------------------------
    --
    --  AnySmscTableIndex defines the range for the index of the largest 
    --  currently defined SMSC table. SMSC tables are:
    --
    --  1) smscTable
    --
    ----------------------------------------------------------------------------

    AnySmscTableIndex ::=
        INTEGER(1..500)

    ----------------------------------------------------------------------------
    --
    --  IcacheSupport indicates whether to store billing info for an SMSC to
    --  be used on delivery notification to generate CDRs.
    --
    ----------------------------------------------------------------------------

    IcacheSupport ::=
        INTEGER {
            noIcacheSupport(0),
            icacheStoreAndLookup(1),
            icacheLookupOnly(2)
        }

    ----------------------------------------------------------------------------
    --
    --  AoAction defines how an SM originated by an application should be routed.
    --
    --  TextPass supports the following routing actions:
    --
    --   1) Route SM to an SMSC (routeToSmsc);
    --   2) Bypass SMSC initially and deliver SMSC SM directly to MS. On delivery
    --      failure, route SM to SMSC (routeToMsFallbackToSMSC);
    --   3) Return an error to originator (discardWithNak)
    --   4) Return an ack to originator and discard message (discardWithAck)
    --   5) Store SM for delivery to MS (storeForDeliveryToMs)
    --   6) Deliver SM directly to MS. On delivery failure, store SM in AMS
    --      (routeToMsFallbackToStorage)
    --
    ----------------------------------------------------------------------------

    AoAction ::=
        INTEGER {
            routeToSmsc(0),
            routeToApplication(1),
            routeToMs(2),              
            routeToMsFallbackToSmsc(3),
            discardWithNak(4),
            discardWithAck(5),
            storeForDeliveryToMs(6),
            routeToMsFallbackToStorage(7),
            storeForDeliveryToApplication(8),
            routeToApplicationFallbackToStorage(9),
            storeForForwardingAsAo(10),
            routeToSmscFallbackToStorage(11)
        }

    ----------------------------------------------------------------------------
    --
    --  AoCntRuleTableIndex defines the range for the index of the AO counting
    --  rule table.
    --
    ----------------------------------------------------------------------------

    AoCntRuleTableIndex ::=
        INTEGER(1..500)

    ----------------------------------------------------------------------------
    --
    --  AoExtCondRuleTableIndex defines the range for the index of the AO
    --  ExternalCondition rule table.
    --
    ----------------------------------------------------------------------------

    AoExtCondRuleTableIndex ::=
        INTEGER(1..500)

    ----------------------------------------------------------------------------
    --
    --  AoModifierTableIndex defines the range for the index of the AO modifier
    --  table.
    --
    ----------------------------------------------------------------------------

    AoModifierTableIndex ::=
        INTEGER(1..100)

    ----------------------------------------------------------------------------
    --
    --  AoModifierRef defines the reference to an AO modifier. Value 0 is
    --  used to clear a reference. Any other value refers to the index of a
    --  modifier in the AO modifier table.
    --
    ----------------------------------------------------------------------------

    AoModifierRef ::=
        Gauge(0..100)

    ----------------------------------------------------------------------------
    --
    --  AoRtgRuleTableIndex defines the range for the index of the AO routing
    --  rule table.
    --
    ----------------------------------------------------------------------------

    AoRtgRuleTableIndex ::=
        INTEGER(1..500)

    ----------------------------------------------------------------------------
    --
    --  AppCharIndex defines the range for the index of a character conversion
    --  table.
    --
    ----------------------------------------------------------------------------

    AppCharIndex ::=
        INTEGER(1..256)

    ----------------------------------------------------------------------------
    --
    --  AppOriginatorListConditionTableIndex defines the range for the index of 
    --  the AppOriginatorListCondition table.
    --
    ----------------------------------------------------------------------------

    AppOriginatorListConditionTableIndex ::=
        INTEGER(1..10000)


    ----------------------------------------------------------------------------
    --
    --  AreaCodeIndex defines the range for the index of the area code table.
    --
    ----------------------------------------------------------------------------

    AreaCodeIndex ::=
        INTEGER(1..500)

    ----------------------------------------------------------------------------
    --
    --  AreaCodeLength specifies the length of the area code.
    --
    ----------------------------------------------------------------------------

    AreaCodeLength ::=
        Gauge(0..6)

    ----------------------------------------------------------------------------
    --
    --  AreaCodeSting specifies an area code.
    --
    ----------------------------------------------------------------------------

    AreaCodeString ::=                             -- should contain digits only
        OCTET STRING (SIZE (0..6))
        
    ----------------------------------------------------------------------------
    --
    --  AsciiCharCode defines characters from the IA5 (7-bit ASCII) or
    --  Latin/ISO-8859-1 (8-bit ASCII) character set.
    --
    ----------------------------------------------------------------------------

    AsciiCharCode ::= TEXTUAL-CONVENTION
        DISPLAY-HINT "1a"
        STATUS mandatory
        DESCRIPTION "ASCII Character Code"
        SYNTAX OCTET STRING (SIZE (1..1))

    ----------------------------------------------------------------------------
    --
    --  AtAction defines how an SM originated by an SMSC should be routed.
    --
    --  TextPass supports the following routing actions:
    --
    --  1) Block SM by returning an error to the SMSC that causes the SMSC to
    --     consider the recipient as temporarily unavailable and will lead to
    --     another delivery attempt at a later time (blockWithTemporaryError).
    --  2) Block SM by returning an error to the SMSC that causes the SMSC to
    --     consider the SM as undeliverable and will not lead to any further
    --     delivery attempts for this SM (blockWithPermanentError).
    --  3) Block SM and return a success response to the SMSC, which cases the
    --     SMSC to treat the SM as being delivered to the destination.
    --
    ----------------------------------------------------------------------------

    AtAction ::=
        INTEGER {
            pass(0),
            blockWithTemporaryError(1),
            blockWithPermanentError(2),
            blockWithAck(3)
        }

    ----------------------------------------------------------------------------
    --
    --  AtCntRuleTableIndex defines the range for the index of the AT counting
    --  rule table.
    --
    ----------------------------------------------------------------------------

    AtCntRuleTableIndex ::=
        INTEGER(1..500)

    ----------------------------------------------------------------------------
    --
    --  AtExtCondRuleTableIndex defines the range for the index of the AT
    --  ExternalCondition rule table.
    --
    ----------------------------------------------------------------------------

    AtExtCondRuleTableIndex ::=
        INTEGER(1..500)

    ----------------------------------------------------------------------------
    --
    --  AtiAction defines how an incoming AT message should be routed.
    --
    ----------------------------------------------------------------------------

    AtiAction ::=
        INTEGER {
            discardWithAck(0),
            discardWithTempError(1),
            discardWithPermMessageError(2),
            discardWithPermRecipientError(3),
            routeToApplication(4),
            routeToApplicationFallbackToStorage(5),
            storeForDeliveryToApplication(6),
            routeToSmscAsAo(7),
            routeToSmscAsAoFallbackToStorage(8),
            storeForForwardingToSmscAsAo(9)
        }

    ----------------------------------------------------------------------------
    --
    --  AtiDestinationApplication defines how the router must determine the
    --  destination application for incoming AT messages that are to be routed
    --  to an application.
    --
    ----------------------------------------------------------------------------

    AtiDestinationApplication ::=
        INTEGER {
            incomingApplication(0),
            recipientBasedApplication(1),
            specifiedApplication(2),
            icacheApplication(3)
        }

    ----------------------------------------------------------------------------
    --
    --  AtiRuleTableIndex defines the range for the index of the ATI
    --  rule tables.
    --
    ----------------------------------------------------------------------------

    AtiRuleTableIndex ::=
        INTEGER(1..500)

    ----------------------------------------------------------------------------
    --
    --  AtModifierTableIndex defines the range for the index of the AT modifier
    --  table. Currently not implemented.
    --
    ----------------------------------------------------------------------------

    AtModifierTableIndex ::=
        INTEGER(1..100)

    ----------------------------------------------------------------------------
    --
    --  RelativeTime is a number of seconds in the future, e.g. 86400 for 1 day
    --  from now. The value -1 has special meaning according to the setting.
    --
    ----------------------------------------------------------------------------

    RelativeTime ::=
        INTEGER(-1..16000000)

    ----------------------------------------------------------------------------
    --
    --  DeliveryPriority is a priority setting for modifications being the
    --  amalgamation of various specs.
    --
    ----------------------------------------------------------------------------

    DeliveryPriority ::=
        INTEGER {
            noChange (-1),
            background (0),
            bulk (1),
            low (2),
            normal (3),
            interactive (4),
            medium (5),
            urgent (6),
            high (7),
            emergency (8)
        }

    ----------------------------------------------------------------------------
    --
    --  NotificationProtocolModifier is the setting for the notification
    --  protocol id.
    --
    ----------------------------------------------------------------------------

    NotificationProtocolModifier ::=
        INTEGER {
            noChange (-1),
            none (0),
            mobileStation (100),
            faxGroup3 (122),
            x400 (131),
            menuOverPstn (138),
            pcApplOverPstn (139),
            pcApplOverX25 (339),
            pcApplOverIsdn (439),
            pcApplOverTcpIp (539)
        }

    ----------------------------------------------------------------------------
    --
    --  ReplyPathIndicator setting for modifications. For CIMD and SMPP the
    --  value 'request' equates to 'true'. The value 'response' applies to
    --  UCP only.
    --
    ----------------------------------------------------------------------------

    ReplyPathIndicator ::=
        INTEGER {
            noChange (-1),
            none (0),
            request (1),
            response (2)
        }

    ----------------------------------------------------------------------------
    --
    --  AtModifierRef defines the reference to an AT modifier. Value 0 is
    --  used to clear a reference. Any other value refers to the index of a
    --  modifier in the AT modifier table.
    --
    ----------------------------------------------------------------------------

    AtModifierRef ::=
        Gauge(0..100)

    ----------------------------------------------------------------------------
    --
    --  AtRtgRuleTableIndex defines the range for the index of the AT routing
    --  rule table.
    --
    ----------------------------------------------------------------------------

    AtRtgRuleTableIndex ::=
        INTEGER(1..500)

    ----------------------------------------------------------------------------
    --
    --  BilAffectedMessageTypes defines for each message type whether the billing
    --  profile pertains or does not pertain. The definition is done using a bit
    --  string. Each bit in the bit string relates to a specific message type. If
    --  the bit is 1, the message type applies. Otherwise, if the bit is 0, the
    --  message type does not apply.
    --
    --    Bit                     Message Type
    --    -------------------------------------
    --     0 (most significant)   MO
    --     1                      MT
    --     2                      AO
    --     3 (least significant)  AT
    --
    ----------------------------------------------------------------------------

    BilAffectedMessageTypes ::=
        OCTET STRING (SIZE (4..4))

    ----------------------------------------------------------------------------
    --
    --  BilFileDuration defines the legitimate values for the duration of a
    --  billing file, expressed in units of seconds.
    --
    ----------------------------------------------------------------------------

    BilFileDuration ::=
        Gauge(1..2678400)                                             -- 1 month

    ----------------------------------------------------------------------------
    --
    --  BilFileFormat defines the format of billing file.
    --
    ----------------------------------------------------------------------------

    BilFileFormat ::=
        INTEGER{
            fcdr(1),                                                -- CMG ASN.1
            ncdr(2),                                                    -- Nokia
            ecdr(3),                                                 -- Ericsson
            ccdr(4),                                                 -- Comverse
            scdr(5),                                                      -- SS8 
            lcdr(6),                                                   -- Logica
            hcdr(7)                                                    -- Huawei
        }

    ----------------------------------------------------------------------------
    --
    --  BilFileRecords defines the legitimate values for the maximum number of
    --  records in a billing file.
    --
    ----------------------------------------------------------------------------

    BilFileRecords ::=
        Gauge(1..10000000)

    ----------------------------------------------------------------------------
    --
    --  BilFileSize defines the legitimate values for the size of a billing
    --  file, expressed in bytes.
    --
    ----------------------------------------------------------------------------

    BilFileSize ::=
        Gauge(2048..1073741824)                                       -- 2K - 1G

    ----------------------------------------------------------------------------
    --
    --  BilProfile specifies whether billing is generated at all. When billing
    --  is generated, BilProfile specifies whether the default billing profile
    --  is to be used or a specific billing profile is to be applied. In the
    --  latter case, BilProfile specifies a reference to the billing profile
    --  that is to be applied.
    --
    --  The following table defines the legitimate values of BilProfile:
    --
    --    Value      Description
    --    ---------------------------------------------------------------------
    --      0        No billing is to be generated
    --    1-100      Billing is to be generated using a specific billing
    --               profile. The value determines which billing profile as it
    --               contains the SNMP table index of the billing profile in the
    --               billing profile table.
    --     1000      Billing is to be generated using the default billing
    --               profile.
    --
    ----------------------------------------------------------------------------

    BilProfile ::=
        Gauge (0..1000)

    ----------------------------------------------------------------------------
    --
    --  BilProfileTableIndex defines the index for the BilProfileTable
    --
    ----------------------------------------------------------------------------

    BilProfileTableIndex ::=
        INTEGER (1..100)

    ----------------------------------------------------------------------------
    --
    --  BitValueModifier defines the legitimate values (0-1) that can be
    --  assigned to a modifier that operates on an SMS field that is implemented
    --  as a single bit. BitValueModifier includes a specific value (-1) to clear
    --  such a modifier.
    --
    ----------------------------------------------------------------------------

    BitValueModifier ::=
        INTEGER(-1..1)

    ----------------------------------------------------------------------------
    --
    --  BooleanResultFilter specifies the supported values of a filter on a
    --  boolean value.
    --
    ----------------------------------------------------------------------------

    BooleanResultFilter ::=
        INTEGER {
            any(0),
            trueOnly(1),
            falseOnly(2)
        }

    ----------------------------------------------------------------------------
    --
    --  ByteValueModifier defines the legitimate values (0-255) that can be
    --  assigned to a modifier that operates on an SMS field that is implemented
    --  as a single byte. ByteValueModifier includes a specific value (-1) to
    --  clear such a modifier.
    --
    ----------------------------------------------------------------------------

    ByteValueModifier ::=
        INTEGER(-1..255)
                 
    ----------------------------------------------------------------------------
    --
    --  CapPhase defines the CAP phase that TextPass should for a CAMEL trigger.
    --
    ----------------------------------------------------------------------------

    CapPhase ::=
        INTEGER {
            cap1(1),
            cap2(2),
            cap3(3)
        }

    ----------------------------------------------------------------------------
    --
    --  CcdrRouterId defines an ID for router that is used in the generation of 
    --  the ISN field of a Comverse CDR.
    --
    ----------------------------------------------------------------------------
    
    CcdrRouterId ::= 
        Gauge(0..31)    

    ----------------------------------------------------------------------------
    --
    --  ScdrRouterId defines an ID for router that is used in the generation of 
    --  the Message ID field of a SS8 CDR.
    --
    ----------------------------------------------------------------------------
    
    ScdrRouterId ::= 
        INTEGER(0..255)    

    ----------------------------------------------------------------------------
    --
    --  ScdrRouterNum defines the number of routers that are used in the 
    --  generation of the Message ID field of a SS8 CDR.
    --
    ----------------------------------------------------------------------------
    
    ScdrRouterNum ::= 
        INTEGER(1..256)    

    ----------------------------------------------------------------------------
    --
    --  ScdrRouterSmPerSecond defines the number of messages expected per router
    --  and second for the generation of the Message ID field of a SS8 CDR.
    --
    ----------------------------------------------------------------------------
    
    ScdrSmPerSecond ::= 
        INTEGER(1..10000)    

    ----------------------------------------------------------------------------
    --
    --  Character defines a character string of length 1
    --
    ----------------------------------------------------------------------------

    Character ::= TEXTUAL-CONVENTION
        DISPLAY-HINT "1a"
        STATUS mandatory
        DESCRIPTION "String comprising one ASCII Character Code"
        SYNTAX OCTET STRING (SIZE (1..1))

    ----------------------------------------------------------------------------
    --
    --  CimdRetErrCode defines the error range which can be returned in error
    --  message.
    --
    ----------------------------------------------------------------------------

    CimdRetErrCode ::=
        Gauge (0..999)

    CimdServiceDescription ::=
        Gauge (0..100)

    CimdTariffClass ::=
        Gauge (0..100)

    ----------------------------------------------------------------------------
    --
    --  CodeMatchMode specifies whether or not a specific code need to match.
    --
    ----------------------------------------------------------------------------

    CodeMatchMode ::=
        INTEGER {
            matchSpecificCode(0),
            matchAnyCode(1)
        }

    ----------------------------------------------------------------------------
    --
    --  ConditionSpec specifies a condition that needs to be satisfied in order
    --  for a rule to match. A condition pertains to the value of an SMS field.
    --
    --  The default for each condition specification is NONE (which always
    --  evaluates to true).
    --
    --  ========================================================================
    --
    --  Format:
    --      NONE
    --
    --  Contents:
    --      zero-length (empty) string
    --
    --  Evaluation:
    --      The condition always satisfies.
    --
    --  ========================================================================
    --
    --  Format:
    --      SINGLEMSISDN
    --
    --  Contents:
    --      a) an optional exclamation mark (!), followed by
    --      b) the letter M, followed by
    --      c) an internationally encoded E164 address excluding the
    --         international prefix of at most 38 digits.
    --
    --  Evaluation:
    --      When the exclamation mark is not specified, the condition should
    --      evaluate to true in order for a rule to match. When the exclamation
    --      mark is specified, the condition should evaluate to false in order
    --      for a rule to match.
    --
    --      The condition evaluates to true when:
    --      a) the SMS field contains an E164 address encoded with a
    --         type-of-number equal to unknown, national or international, and
    --      b) the SMS field specifies the same address as the E164 address from
    --         the condition specification
    --
    --      note: when type-of-number of SMS field is not international, a
    --            conversion is applied before the evaluation of b)

    --
    --  Example:
    --      The specification for the Dutch MISDN +31 627 093 038 looks like:
    --
    --          M31627093038
    --
    --      The specification for all MSISDN's excluding the Dutch MISDN +31 627
    --      093 038 looks like:
    --
    --          !M31627093038
    --
    --  ========================================================================
    --
    --  Format:
    --      MSISDNRANGE
    --
    --  Contents:
    --      a) an optional exclamation mark (!), followed by
    --      b) the letter M, followed by
    --      c) an internationally encoded E164 address excluding the
    --         international prefix of at most 38 digits,
    --         followed by
    --      d) a dash (-), followed by
    --      e) an internationally encoded E164 address excluding the
    --         international prefix of at most 38 digits
    --
    --  Evaluation:
    --      When the exclamation mark is not specified, the condition should
    --      evaluate to true in order for a rule to match. When the exclamation
    --      mark is specified, the condition should evaluate to false in order
    --      for a rule to match.
    --
    --      The condition evaluates to true when:
    --      a) the SMS field contains an E164 address encoded with a
    --         type-of-number equal to unknown, national or international, and
    --      b) the SMS field specifies an address which is in range from (and
    --         including) the two E164 addresses of the condition specification.
    --
    --      note: when type-of-number of SMS field is not international, a
    --            conversion is applied before the evaluation of b)
    --
    --  Example:
    --      The specification for the Dutch MISDN range from +31 621 000 000
    --      till +31 621 999 999 looks like:
    --
    --          M31621000000-31621999999
    --
    --      The specification for all MSISDN's exclude the Dutch MISDN range

    --      from +31 621 000 000 till +31 621 999 999 looks like:

    --
    --          !M31621000000-31621999999
    --
    --  ========================================================================
    --
    --  Format:
    --      MSISDNPREFIX
    --
    --  Contents:
    --      a) an optional exclamation mark (!), followed by
    --      b) the letter M, followed by
    --      c) an internationally encoded E164 address excluding the
    --         international prefix of at least 0 and at most 38 digits,
    --         followed by
    --      d) a star (*)
    --
    --  Evaluation:
    --      When the exclamation mark is not specified, the condition should
    --      evaluate to true in order for a rule to match. When the exclamation
    --      mark is specified, the condition should evaluate to false in order
    --      for a rule to match.
    --
    --      The condition evaluates to true when:
    --      a) the SMS field contains an E164 address encoded with a
    --         type-of-number equal to unknown, national or international, and
    --      b) the SMS field specifies an address which starts with the number
    --         of the condition specification.
    --
    --      note: when type-of-number of SMS field is not international, a
    --            conversion is applied before the evaluation of b)
    --
    --  Example:
    --      The specification for numbers starting with +31 653 looks like:
    --
    --          M31653*
    --
    --      The specification for all MSISDN's excluding those starting with

    --      +31 621 looks like:
    --
    --          !M31621*
    --
    --  ========================================================================
    --
    --  Format:
    --      COUNTRY
    --
    --  Contents:
    --      a) an optional exclamation mark (!), followed by
    --      b) the letter C, followed by
    --      c) the two-letter country code as defined in ISO 3166.
    --
    --      or 
    --
    --      a) an optional exclamation mark (!), followed by
    --      b) the letter c, followed by
    --      c) the SNMP-index of the applicable entry in the countryTable
    -- 
    --  Evaluation:
    --      When the exclamation mark is not specified, the condition should
    --      evaluate to true in order for a rule to match. When the exclamation
    --      mark is specified, the condition should evaluate to false in order
    --      for a rule to match.
    --
    --      The condition evaluates to true when:
    --      a) the SMS field contains an E164 address encoded with a
    --         type-of-number equal to unknown, national or international, and
    --      b) the SMS field specifies an E164 address belonging to the country
    --         specified in the condition specification
    --      or
    --         when the SMS field contains an IMSI belonging to the country
    --         specified in the condition specification
    --
    --      note: when type-of-number of SMS field is not international, a
    --            conversion is applied before the evaluation of b)
    --
    --  Example:
    --      The specification for Germany looks like:
    --
    --          Cde
    --
    --      The specification for all countries excluding Germany looks like:
    --
    --          !Cde
    --
    --      Assuming that 34 is the SNMP index for the countryTable entry 
    --      representing Germany, then alternatives for the above specifications 
    --      are: c34 (for Cde) and !c34 (for !Cde).
    --
    --  ========================================================================
    --
    --  Format:
    --      NETWORK
    --
    --  Contents:
    --      a) an optional exclamation mark (!), followed by
    --      b) the letter N, followed by
    --      c) the two-letter country code as defined in ISO 3166, followed by
    --      d) a dash (-), followed by
    --      e) the name of one of the mobile networks defined in mobNetworkTable
    --
    --      or 
    --
    --      a) an optional exclamation mark (!), followed by
    --      b) the letter n, followed by
    --      c) the SNMP-index of the applicable entry in the networkTable
    --
    --  Evaluation:
    --      When the exclamation mark is not specified, the condition should
    --      evaluate to true in order for a rule to match. When the exclamation
    --      mark is specified, the condition should evaluate to false in order
    --      for a rule to match.
    --
    --      The condition evaluates to true when:
    --      a) the SMS field contains an E164 address encoded with a
    --         type-of-number equal to unknown, national or international, and
    --      b) the SMS field specifies an E164 address belonging to the number
    --         range of the mobile operator that is specified in the condition
    --         specification
    --      or
    --         when the SMS field contains an IMSI belonging to the mobile
    --         network specified in the condition specification
    --
    --      note: when type-of-number of SMS field is not international, a
    --            conversion is applied before the evaluation of b)
    --
    --  Example:
    --      The specification for KPN looks like:
    --
    --          Nnl-KPN
    --
    --      The specification for all networks excluding KPN looks like:
    --
    --          !Nnl-KPN
    --
    --      Assuming that 78 is the SNMP index for the networkTable entry 
    --      representing KPN, then alternatives for the above specifications 
    --      are: n78 (for Nnl-KPN) and !n78 (for !Nnl-KPN).
    --
    --  ========================================================================
    --
    --  Format:
    --      SINGLESHORTNUMBER
    --
    --  Contents:
    --      a) an optional exclamation mark (!), followed by
    --      b) the letter S, followed by
    --      c) an E164 address of at least 1 and at most 38 digits.
    --
    --  Evaluation:
    --      When the exclamation mark is not specified, the condition should
    --      evaluate to true in order for a rule to match. When the exclamation
    --      mark is specified, the condition should evaluate to false in order
    --      for a rule to match.
    --
    --      The condition evaluates to true when:
    --      a) the SMS field contains an E164 address encoded with a
    --         type-of-number equal to unknown or national, and
    --      b) the SMS field specifies the same address as the E164 address from
    --         the condition specification
    --
    --  Example:
    --      The specification for short number 2200 looks like:
    --
    --          S2200
    --
    --      The specification for all short numbers excluding short number 2200
    --      looks like:
    --
    --          !S2200
    --
    --  ========================================================================
    --
    --  Format:
    --      SHORTNUMBERRANGE
    --
    --  Contents:
    --      a) an optional exclamation mark (!), followed by
    --      b) the letter S, followed by
    --      d) an E164 address  of at least 1 and at most 38 digits, followed by
    --      d) a dash (-), followed by
    --      e) an E164 address  of at least 1 and at most 38 digits.
    --
    --  Evaluation:
    --      When the exclamation mark is not specified, the condition should
    --      evaluate to true in order for a rule to match. When the exclamation
    --      mark is specified, the condition should evaluate to false in order
    --      for a rule to match.
    --
    --      The condition evaluates to true when:
    --      a) the SMS field contains an E164 address encoded with a
    --         type-of-number equal to unknown or national, and
    --      b) the SMS field specifies an address which is in range from (and
    --         including) the two E164 addresses of the condition specification.
    --
    --  Example:
    --      The specification for the short number range from 4096 till 4103
    --      looks like:
    --
    --          S4096-4103
    --
    --      The specification for all short numbers excluding the short number
    --      range from 4096 till 4103 looks like:
    --
    --          !S4096-4103
    --
    --  ========================================================================
    --
    --  Format:
    --      SHORTNUMBERPREFIX
    --
    --  Contents:
    --      a) an optional exclamation mark (!), followed by
    --      b) the letter S, followed by
    --      d) an E164 address  of at least 1 and at most 38 digits, followed by
    --      d) a star (*)
    --
    --  Evaluation:
    --      When the exclamation mark is not specified, the condition should
    --      evaluate to true in order for a rule to match. When the exclamation
    --      mark is specified, the condition should evaluate to false in order
    --      for a rule to match.
    --
    --      The condition evaluates to true when:
    --      a) the SMS field contains an E164 address encoded with a
    --         type-of-number equal to unknown, national or international, and
    --      b) the SMS field specifies an address which starts with the number
    --         of the condition specification.
    --
    --  Example:
    --      The specification for numbers starting with 11 looks like:
    --
    --          S11*
    --
    --      The specification for all MSISDN's excluding those starting with

    --      254 looks like:
    --
    --          !S254*
    --
    --  ========================================================================
    --
    --  Format:
    --      APPLICATION
    --
    --  Contents:
    --      a) an optional exclamation mark (!), followed by
    --      b) the letter A, followed by
    --      c) the name of one of the applications defined in applicationTable
    --
    --      or 
    --
    --      a) an optional exclamation mark (!), followed by
    --      b) the letter a, followed by
    --      c) the SNMP-index of the applicable entry in the applicationTable
    --
    --  Evaluation:
    --      When the exclamation mark is not specified, the condition should
    --      evaluate to true in order for a rule to match. When the exclamation
    --      mark is specified, the condition should evaluate to false in order
    --      for a rule to match.
    --
    --      The condition evaluates to true when:
    --      a) the SMS field contains an E164 address encoded with a
    --         type-of-number equal to unknown or national, and
    --      b) the SMS field specifies the short number of the application
    --         specified in the condition specification
    --
    --  Example:
    --      The specification for an application called Big Brother looks like:
    --
    --          ABig Brother
    --
    --      The specification for all applications excluding Big Brother looks
    --      like:
    --
    --          !ABig Brother
    --
    --      Assuming that 963 is the SNMP index for the applicationTable entry 
    --      representing Big Brother, then alternatives for the above 
    --      specifications are: a963 (for ABig Brother) and !a963 (for 
    --      !ABig Brother).
    --
    --  ========================================================================
    --
    --  Format:
    --      SINGLEIMSI
    --
    --  Contents:
    --      a) an optional exclamation mark (!), followed by
    --      b) the letter I, followed by
    --      c) an IMSI of at least 5 and at most 15 digits.
    --
    --  Evaluation:
    --      When the exclamation mark is not specified, the condition should
    --      evaluate to true in order for a rule to match. When the exclamation
    --      mark is specified, the condition should evaluate to false in order
    --      for a rule to match.
    --
    --      The condition evaluates to true when:
    --      a) the SMS field contains an IMSI, and
    --      b) the SMS field specifies the same IMSI as the IMSI from
    --         the condition specification
    --
    --  Example:
    --      The specification for the IMSI 204 12 45454545 looks like:
    --
    --          I2041245454545
    --
    --      The specification for all IMSI's excluding IMSI 204 12 45454545 looks
    --      like:
    --
    --          !I2041245454545
    --
    --  ========================================================================
    --
    --  Format:
    --      IMSIRANGE
    --
    --  Contents:
    --      a) an optional exclamation mark (!), followed by
    --      b) the letter I, followed by
    --      c) an IMSI of at least 5 and at most 15 digits, followed by
    --      d) a dash (-), followed by
    --      e) an IMSI of at least 5 and at most 15 digits.
    --
    --  Evaluation:
    --      When the exclamation mark is not specified, the condition should
    --      evaluate to true in order for a rule to match. When the exclamation
    --      mark is specified, the condition should evaluate to false in order
    --      for a rule to match.
    --
    --      The condition evaluates to true when:

    --      a) the SMS field contains an IMSI, and
    --      b) the SMS field specifies an IMSI which is in range from (and
    --         including) the two IMSI's of the condition specification.
    --
    --  Example:
    --      The specification for the IMSI range from 204 20 4004000 till
    --      204 20 4005000 looks like:
    --
    --          I204204004000-204204005000
    --
    --      The specification for all IMSI's excluding the IMSI range from 204
    --      20 4004000 till 204 20 4005000 looks like:
    --
    --          !I204204004000-204204005000
    --
    --  ========================================================================
    --
    --  Format:
    --      SINGLEPOINTCODE
    --
    --  Contents:
    --      a) an optional exclamation mark (!), followed by
    --      b) the letter P, followed by
    --      c) a point code 
    --
    --      The point code can be specified in three ways:
    --      - as a value between 0 and 16777215
    --      - as a string with the format "network-cluster-member" (e.g. 1-29-4)
    --      - as a string with the format "network.cluster.member" (e.g. 1.29.4)
    --
    --      Following table gives the range of values that are allowed for the
    --      subfields of the string formats:
    --
    --                       -------------------------
    --                       subfield   ANSI    ITU-T
    --                       -------------------------
    --                       network    1-255   0-7 
    --                       cluster    0-255   0-255
    --                       member     0-255   0-7 
    --                       -------------------------
    --
    --  Evaluation:
    --
    --      When the exclamation mark is not specified, the condition should
    --      evaluate to true in order for a rule to match. When the exclamation
    --      mark is specified, the condition should evaluate to false in order
    --      for a rule to match.
    --
    --      The condition evaluates to true when:
    --      a) the SM is routed using PC/SSN, and
    --      b) the SM is transferred from/to the same point code as the point
    --         code from the condition specification
    --
    --  Example:
    --      The specification for point code 2056 looks like:
    --
    --          P2056 
    --
    --      Alternative notations for this condition are: 
    --
    --          P0-8-8     (ANSI)
    --          P0.8.8     (ANSI)
    --          P1-1-0     (ITU-T)
    --          P1.1.0     (ITU-T)
    --
    --      The specification for point codes excluding point code 2056 looks
    --      like:
    --
    --          !P2056
    --
    --  ========================================================================
    --
    --  Format:
    --      POINTCODERANGE
    --
    --  Contents:
    --      a) an optional exclamation mark (!), followed by
    --      b) the letter P, followed by
    --      c) a point code 
    --      d) a dash (-), followed by
    --      e) a point code 
    --
    --      The point code can be specified in three ways:
    --      - as a value between 0 and 16777215
    --      - as a string with the format "network-cluster-member" (e.g. 1-29-4)
    --      - as a string with the format "network.cluster.member" (e.g. 1.29.4)
    --
    --      Following table gives the range of values that are allowed for the
    --      subfields of the string formats:
    --
    --                       -------------------------
    --                       subfield   ANSI    ITU-T
    --                       -------------------------
    --                       network    1-255   0-7 
    --                       cluster    0-255   0-255
    --                       member     0-255   0-7 
    --                       -------------------------
    --
    --       Within a condition specification, both point codes need to be 
    --       specified with the same format.
    --
    --  Evaluation:
    --      When the exclamation mark is not specified, the condition should
    --      evaluate to true in order for a rule to match. When the exclamation
    --      mark is specified, the condition should evaluate to false in order
    --      for a rule to match.
    --

    --      The condition evaluates to true when:
    --      a) the SM is routed using PC/SSN, and
    --      b) the SM is transferred from/to a point code which is in range from
    --         (and including) the two point codes of the condition
    --         specification.
    --
    --  Example:
    --      The specification for the point code range from 16000 till
    --      16383 looks like:
    --
    --          P16000-16383
    --
    --      Alternative notations for this condition are: 
    --
    --          P7-208-0-7-255-7     (ITU-T)
    --          P7.208.0-7.255.7     (ITU-T)
    --
    --      For ANSI, the point code range 16000-16383 is invalid!
    --
    --      The specification for all point codes excluding the point code range
    --      from 16000 till 16383 looks like:
    --
    --          !P16000-16383
    --
    --  ========================================================================
    --
    --  Format:
    --      BYTEVALUE
    --
    --  Contents:
    --      a) an optional exclamation mark (!), followed by
    --      b) the letter B, followed by
    --      c) two hex digits
    --
    --  Evaluation:
    --      When the exclamation mark is not specified, the condition should
    --      evaluate to true in order for a rule to match. When the exclamation
    --      mark is specified, the condition should evaluate to false in order
    --      for a rule to match.
    --
    --      The condition evaluates to true when:
    --      a) the SMS field has the value specified
    --
    --  Example:
    --      The specification for a value of 160 looks like:
    --
    --          BA0
    --
    --      The specification for all values excluding 100 looks like:
    --
    --          !B64
    --
    --  ========================================================================
    --
    --  Format:
    --      BITVALUE
    --
    --  Contents:
    --      a) an optional exclamation mark (!), followed by
    --      b) the letter b, followed by
    --      c) 0 or 1
    --
    --  Evaluation:
    --      When the exclamation mark is not specified, the condition should
    --      evaluate to true in order for a rule to match. When the exclamation
    --      mark is specified, the condition should evaluate to false in order
    --      for a rule to match.
    --
    --      The condition evaluates to true when:
    --      a) the SMS field has the value specified
    --
    --  Example:
    --      The specification for a value of 1 looks like:
    --
    --          b1 or !b0
    --
    --  ========================================================================
    --
    --  Format:
    --      BITSTRING
    --
    --  Contents:
    --      a) an optional exclamation mark (!), followed by
    --      b) the letter s, followed by
    --      c) a string of zeros and ones
    --
    --  Evaluation:
    --      When the exclamation mark is not specified, the condition should
    --      evaluate to true in order for a rule to match. When the exclamation
    --      mark is specified, the condition should evaluate to false in order
    --      for a rule to match.
    --
    --      The condition evaluates to true when:
    --      a) the SMS field has the value specified
    --
    --  Example:
    --      The specification for a value of 1 looks like:
    --
    --          s00001001 or !s0100100011000011
    --
    --  ========================================================================
    --
    --  Format:
    --      EXTERNALATTRIBUTES
    --
    --  Contents:
    --      a) an optional exclamation mark (!), followed by
    --      b) the letter e, followed by
    --      c) a string of zeros and ones indicating the bit value string, followed 
    --         by
    --      d) a comma, followed by
    --      e) a string of zeros and ones indicating the bit mask string
    --
    --  Evaluation:
    --      When the exclamation mark is not specified, the condition should
    --      evaluate to true in order for a rule to match. When the exclamation
    --      mark is specified, the condition should evaluate to false in order
    --      for a rule to match.
    --
    --      The condition evaluates to true when:
    --      a) the selected external attributes match the specified values
    --
    --  Example:
    --
    --      The specification for attribute 0 equal to 0 and attribute 1 equal to 
    --      1 looks like:
    --
    --        e00000000000000000000000000000010,00000000000000000000000000000011
    --
    --  ========================================================================
    --
    --  Format:
    --      FULLTEXT
    --
    --  Contents:
    --      a) an optional exclamation mark (!), followed by
    --      b) the letter T, followed by
    --      c) a text string to be processed by the appCharAsciiToGsmTable 
    --         (which is Latin/ISO-8859-1 by default).
    --
    --      or 
    --
    --      a) an optional exclamation mark (!), followed by
    --      b) the letter V, followed by
    --      c) a text string in utf8.
    --
    --  Evaluation:
    --      When the exclamation mark is not specified, the condition should
    --      evaluate to true in order for a rule to match. When the exclamation
    --      mark is specified, the condition should evaluate to false in order
    --      for a rule to match.
    --
    --      The condition evaluates to true when:
    --      a) the SMS field contains the text string (and not anymore text)
    --
    --      The check of SMS field against text string is case-insensitive.
    --
    --  Example:
    --      The specification for a text string 'Ruud van Nistelrooy' looks
    --      like:
    --
    --          TRuud van Nistelrooy
    --
    --      The specification for all text strings excluding  'Ruud van
    --      Nistelrooy' looks like:
    --
    --          !TRuud van Nistelrooy
    --
    --  ========================================================================
    --
    --  Format:
    --      TEXTTAG
    --
    --  Contents:
    --      a) an optional exclamation mark (!), followed by
    --      b) the letter t, followed by
    --      c) a text string to be processed by the appCharAsciiToGsmTable 
    --         (which is Latin/ISO-8859-1 by default).
    --
    --      or 
    --
    --      a) an optional exclamation mark (!), followed by
    --      b) the letter v, followed by
    --      c) a text string in utf8.
    --
    --  Evaluation:
    --      When the exclamation mark is not specified, the condition should
    --      evaluate to true in order for a rule to match. When the exclamation
    --      mark is specified, the condition should evaluate to false in order
    --      for a rule to match.
    --
    --      The condition evaluates to true when:
    --      a) the SMS field starts with the text string
    --
    --      The check of SMS field against text string is case-insensitive.
    --
    --  Example:
    --      The specification for a text string starting with *LONG# looks
    --      like:
    --
    --          t*LONG#
    --
    --      The specification for all text strings excluding the text strings
    --      starting with *LONG# looks like:
    --
    --          !t*LONG#
    --
    --  ========================================================================
    --
    --  Format:
    --      SUBTEXT
    --
    --  Contents:
    --      a) an optional exclamation mark (!), followed by
    --      b) the letter u, followed by
    --      c) a number indicating the start position and a comma (","), followed by
    --      d) a number indicating the end position and a comma (","), followed by
    --      e) a text string to be processed by the appCharAsciiToGsmTable 
    --         (which is Latin/ISO-8859-1 by default).
    --
    --      or 
    --
    --      a) an optional exclamation mark (!), followed by
    --      b) the letter U, followed by
    --      c) a number indicating the start position and a comma (","), followed by
    --      d) a number indicating the end position and a comma (","), followed by
    --      e) a text string in utf8
    --
    --  Evaluation:
    --      When the exclamation mark is not specified, the condition should
    --      evaluate to true in order for a rule to match. When the exclamation
    --      mark is specified, the condition should evaluate to false in order
    --      for a rule to match.
    --
    --      The condition evaluates to true when:
    --      a) the SMS field contains the text string within the specified
    --         boundries (inclusive the boundary character).
    --
    --      The check of SMS field against text string is case-insensitive.
    --
    --  Example:
    --      The specification for a text string containing BYE looks
    --      like:
    --
    --          u1,160,BYE
    --
    --      The specification for all text strings excluding the text strings
    --      containing BYE looks like:
    --
    --          !u1,160,BYE
    --
    --  ========================================================================
    --
    --  Format:
    --      SINGLETCPIPADDRESS
    --
    --  Contents:
    --      a) an optional exclamation mark (!), followed by
    --      b) the letter i, followed by
    --      c) an IP address in the format x.x.x.x, or
    --         a TCP/IP address in the format x.x.x.x:y
    --
    --  Evaluation:
    --      When the exclamation mark is not specified, the condition should
    --      evaluate to true in order for a rule to match. When the exclamation
    --      mark is specified, the condition should evaluate to false in order
    --      for a rule to match.
    --
    --      When the condition contains an IP address, the condition evaluates
    --      to true when:
    --      a) the SMS field specifies the same IP address as the IP address
    --         from the condition specification
    --
    --      When the condition contains a TCP/IP address, the condition
    --      evaluates to true when:
    --      a) the SMS field specifies the same IP address as the IP address
    --         from the condition specification, and
    --      b) the SMS field specifies the same TCP port as the TCP port
    --         from the condition specification
    --
    --  Example:
    --      The specification for IP address 10.0.0.1 looks like:
    --
    --          i10.0.0.1
    --
    --      The specification for all TCP/IP addresses excluding TCP/IP address
    --      192.168.1.1:9000 looks like:
    --
    --          !i192.168.1.1:9000
    --
    --  ========================================================================
    --
    --  Format:
    --      SINGLEX121ADDRESS
    --
    --  Contents:
    --      a) an optional exclamation mark (!), followed by
    --      b) the letter x, followed by
    --      c) an internationally encoded X121 address excluding the
    --         international prefix and consisting of at most 38 digits.
    --
    --  Evaluation:
    --      When the exclamation mark is not specified, the condition should
    --      evaluate to true in order for a rule to match. When the exclamation
    --      mark is specified, the condition should evaluate to false in order
    --      for a rule to match.
    --
    --      The condition evaluates to true when:
    --      a) the SMS field specifies the same address as the X121 address from
    --         the condition specification
    --
    --      note: when type-of-number of SMS field is not international, a
    --            conversion is applied before the evaluation of a)
    --
    --  Example:
    --      The specification for the Dutch X121 address 204 1248736 looks like:
    --
    --          x2041248736
    --
    --      The specification for all MSISDN's excluding the Dutch MISDN 204
    --      0985301 looks like:
    --
    --          !x2040985301
    --
    --  ========================================================================
    --
    --  Format:
    --      TEXTLENGTH
    --
    --  Contents:
    --      a) an optional exclamation mark (!), followed by
    --      b) the letter l, followed by
    --      c) the minimum length expressed in number of characters or octects,
    --         followed by
    --      d) a comma, followed by
    --      e) the maximum length expressed in number of characters or octects
    --
    --      The length indicators are expressed in number of characters when the
    --      SM is encoded with the GSM default alphabet. A character from the
    --      default extension table (consisting of an ESC character followed by
    --      another character) count as a single character.
    --
    --      When the SM is encoded as binary or as UCS2, the length indicators
    --      are expressed in number of octets.
    --
    --  Evaluation:
    --      When the exclamation mark is not specified, the condition should
    --      evaluate to true in order for a rule to match. When the exclamation
    --      mark is specified, the condition should evaluate to false in order
    --      for a rule to match.
    --
    --      The condition evaluates to true when:
    --      a) the number of septets/octets is equal to or greater than the
    --         minimum length
    --      b) the number of septets/octets is equal to or smaller than the
    --         maximum length
    --
    --  Example:
    --      The specification for a length from 100 to 120 septets/octets looks
    --      like:
    --
    --          l100,120
    --
    --      The specification for all lengths excluding 100 looks like:
    --
    --          !l100,100
    --
    --  ========================================================================
    --
    --  Format:
    --      RELATIVETIME
    --
    --  Contents:
    --      a) an optional exclamation mark (!), followed by
    --      b) the letter r, followed by
    --      c) the start of the time frame specified by means of an offset from
    --         the current time expressed in number of seconds, followed by
    --      d) a comma, followed by
    --      e) the end of the time frame specified by means of an offset from
    --         the current time expressed in number of seconds, followed by
    --
    --      The offset is any number between -100000000 and 100000000. Negative
    --      offsets indicate a timestamp in the past, positve offsets indicate a
    --      timestamp in the future.
    --
    --  Evaluation:
    --      When the exclamation mark is not specified, the condition should
    --      evaluate to true in order for a rule to match. When the exclamation
    --      mark is specified, the condition should evaluate to false in order
    --      for a rule to match.
    --
    --      The condition evaluates to true when:
    --      a) the difference between the time specified in the SM and the
    --         current time is equal to or greater than the offset for the start
    --         of the time frame, and
    --      b) the difference between the time specified in the SM and the
    --         current time is equal to or smaller than the offset for the end
    --         of the time frame
    --
    --  Example:
    --      The specification for a time frame from now up to 2 hours looks
    --      like:
    --
    --          r0,7200
    --
    --      The specification for any time apart from the next hour looks like:
    --
    --          !r0,3600
    --
    --  ========================================================================
    --
    --  Format:
    --      DIGITSTRING
    --
    --  Contents:
    --      a) an optional exclamation mark (!), followed by
    --      b) the letter D, followed by
    --      c) a string with digits
    --
    --  Evaluation:
    --      When the exclamation mark is not specified, the condition should
    --      evaluate to true in order for a rule to match. When the exclamation
    --      mark is specified, the condition should evaluate to false in order
    --      for a rule to match.
    --
    --      The condition evaluates to true when:
    --      a) the SM fields matches the digit string
    --
    --  Example:
    --      The specification for a digit string 123456789 looks like:
    --
    --          D123456789
    --
    --      The specification for any digit string apart from 123456789 looks
    --      like:
    --
    --          !D123456789
    --
    --  ========================================================================
    --
    -- Format:
    --     LIST
    --
    -- Contents:
    --     a) an optional exclamation mark (!), followed by
    --     b) the letter L, followed by
    --     c) the SNMP-index of the applicable entry in the listTable
    --
    -- Evaluation:
    --      When the exclamation mark is not specified, the condition should
    --      evaluate to true in order for a rule to match. When the exclamation
    --      mark is specified, the condition should evaluate to false in order
    --      for a rule to match.
    --
    --      The condition evaluates to true when:
    --      a) one or more conditions in the referenced list evaluate to true.
    --
    --  Example:
    --      The specification for a list with SNMP-index of 42 looks like:
    --
    --               L42
    --
    --  ========================================================================
    --
    --  Format:
    --      EXTERNALCONDITION
    --
    --  Contents:
    --      a) an optional exclamation mark (!), followed by
    --      b) the letter E, followed by
    --      c) the name of one of the externalConditions defined in the
    --         externalConditionTable
    --
    --      or 
    --
    --      a) an optional exclamation mark (!), followed by
    --      b) the letter f, followed by
    --      c) the SNMP-index of the applicable entry in the 
    --         externalConditionTable
    --
    --  Evaluation:
    --      When the exclamation mark is not specified, the condition should
    --      evaluate to true in order for a rule to match. When the exclamation
    --      mark is specified, the condition should evaluate to false in order
    --      for a rule to match.
    --
    --      The condition evaluates to true when:
    --      a) the external condition responds with 'TRUE' on a evaluationRequest
    --
    --  Example:
    --      The specification for an external condition called Big Brother
    --      looks like:
    --
    --          EBig Brother
    --
    --      The specification for inverting the response of external condition
    --      Big Brother looks like:
    --
    --          !EBig Brother
    --
    --      Assuming that 7 is the SNMP index for the externalConditionTable 
    --      entry representing Big Brother, then alternatives for the above 
    --      specifications are: f7 (for EBig Brother) and !f7 (for 
    --      !EBig Brother).
    --
    --  ========================================================================
    --
    --  Format:
    --      ALPHANUMADDRESS
    --
    --  Contents:
    --      a) an optional exclamation mark (!), followed by
    --      b) the letter W, followed by
    --      c) an alphanumeric string of UTF8-encoded unicode characters.
    --         When converted into the GSM 7-bit alphabet, the string length
    --         must not exceed the length of 11 characters.
    --
    --  Evaluation:
    --      When the exclamation mark is not specified, the condition should
    --      evaluate to true in order for a rule to match. When the exclamation
    --      mark is specified, the condition should evaluate to false in order
    --      for a rule to match.
    --
    --      The condition evaluated to true when:
    --      a) the SMS field contains an alphanumeric string, and
    --      b) the SMS field matches the alphanumeric string.
    --
    --      The check of SMS field against text string is case-insensitive.
    --
    --  Example:
    --      The specification for an alphanumeric string 'big feet' looks like:
    --
    --          Wbig feet
    --
    --      The specification for anything except for the alphanumeric string
    --      'big feet' looks like:
    --
    --          !Wbig feet
    --
    --  ========================================================================
    --
    --  Format:
    --      TIMESPEC
    --
    --  Contents:
    --      a) an optional exclamation mark (!), followed by
    --      b) the letter p, followed by
    --      c) six tokens separated by a single space character. The total 
    --         string must not be longer than 100 characters.
    --
    --  Evaluaton:
    --      The first 5 tokens must have one of the following formats:
    --          a) a single asterisk (*), representing the entire range of
    --             valid numbers.
    --          b) a single number from the range of valid numbers.
    --          c) a list of numbers from the range of valid numbers,
    --             separated by a comma (,).
    --          d) a range of numbers, separated by a dash (-).
    --             Both start and end number are included in the range of
    --             numbers. Both start and end number are in the range of
    --             valid numbers. The start number must not be higher than 
    --             the end number.
    --      The tokens have the following meaning:
    --          1) token 1 specifies minutes after a full hour. The range of 
    --             valid numbers is 0 - 59.
    --          2) token 2 specifies hours after midnight. The range of valid
    --             numbers is 0 - 23.
    --          3) token 3 specifies days of the month. The range of valid
    --             values is 1 - 31.
    --          4) token 4 specifies months of the year. The range of valid
    --             values is 1 - 12.
    --          5) token 5 specifies days of the week. The range of valid
    --             values is 1 - 7, where 1 represents sunday.
    --          6) token 6 specifies a duration in minutes. It must be specified
    --             as a single number in the range of 0 - 527040. An asterisk is
    --             interpreted as a value of 0. The duration starts after the
    --             most recent period specified by tokens 1 to 5.
    --
    --      When the exclamation mark is not specified, the condition should
    --      evaluate to true in order for a rule to match. When the exclamation
    --      mark is specified, the condition should evaluate to false in order
    --      for a rule to match.
    --
    --  Example:
    --      The specification for each tuesday looks like
    --
    --      "p* * * * 3 *"
    --
    --      The specification for monday to friday from 9 to 5 looks like
    --
    --      "p* 9-16 * * 2-6 *"
    --
    --      The specification for one minute every half hour looks like
    --
    --      "p0,30 * * * * *"
    --
    --      The specification for friday 5pm to monday 9am looks like
    --
    --      "p0 17 * * 6 3840"
    --
    --  ========================================================================
    --
    --  Format:
    --      SINGLEMIN
    --
    --  Contents:
    --      a) an optional exclamation mark (!), followed by
    --      b) the letter m, followed by
    --      c) a 10-digit MIN number.
    --
    --  Evaluation
    --      When the exclamation mark is not specified, the condition should
    --      evaluate to true in order for a rule to match. When the exclamation
    --      mark is specified, the condition should evaluate to false in order
    --      for a rule to match.
    --
    --      The condition evaluated to true when:
    --      a) the SMS field contains a MIN, and
    --      b) the SMS field matches the specified MIN.
    --
    --  Example:
    --      The specification for a MIN value of '9382716054 looks like:
    --
    --          m9382716054
    --
    --      The specification for anything except for a MIN value of
    --      6958473120 looks like:
    --
    --          !m6958473120
    --
    --  ========================================================================
    --
    --  Format:
    --      MINRANGE
    --
    --  Contents:
    --      a) an optional exclamation mark (!), followed by
    --      b) the letter m, followed by
    --      c) a 10-digit MIN, followed by
    --      d) a dash (-), followed by
    --      e) a 10-digit MIN.
    --
    --  Evaluation:
    --      When the exclamation mark is not specified, the condition should
    --      evaluate to true in order for a rule to match. When the exclamation
    --      mark is specified, the condition should evaluate to false in order
    --      for a rule to match.
    --
    --      The condition evaluates to true when:

    --      a) the SMS field contains a MIN, and
    --      b) the SMS field specifies a MIN which is in the range specified
    --         by the two MINs of the condition specification. Note that the
    --         range includes the two MINs specified in the condition. 
    --
    --  Example:
    --      The specification for a MIN range of 1234000111 till 1234009444
    --      looks like:
    --
    --          m1234000111-1234009444
    --
    --      The specification for all MINs excluding the MIN range from 
    --      1234000000 till 1234009999 looks like:
    --
    --          !m1234000000-1234009999
    --
    --  ========================================================================
    --
    --  Format:
    --      SNMPINDEX
    --
    --  Contents:
    --      a) an optional exclamation mark (!), followed by
    --      b) the letter X, followed by
    --      c) an index into an SNMP table or 0. The index is a decimal number,
    --         encoded in ASCII/UTF-8.
    --
    --  Evaluation:
    --      The (non-inverted) condition holds true if the table entry pointed
    --      to by the SNMP index matches with the corresponding field of the
    --      message under consideration. The condition itself shall specify
    --      which SNMP table and which message parameter are considered. A
    --      value of 0 means that none of the table entries is applicable for
    --      the message. The exclamation mark has the effect of inverting the
    --      condition.
    --
    --  Example:
    --      The following specification evaluates to true if message parameter
    --      A corresponds with parameter B of column 266 of SNMP table C.
    --      A, B and C are described whenever the SNMPINDEX condition spec is
    --      used.
    --
    --           X266
    --
    --      The following specification evaluates to true if message parameter
    --      A does correspond with parameter B of any entry of SNMP table C.
    --
    --          !X0
    --
    ----------------------------------------------------------------------------

    ConditionSpec ::= TEXTUAL-CONVENTION
        DISPLAY-HINT "1290a"
        STATUS mandatory
        DESCRIPTION "Condition specification"
        SYNTAX OCTET STRING(SIZE (0..1290))

    ----------------------------------------------------------------------------
    --
    --  CopyAction defines how a copied SM is to be routed to an MS or an 
    --  application.
    --
    --  TextPass supports the following routing actions:
    --
    --   1) Delivery of copied SM to destination (route);
    --   2) Store in AMS for delivery to destination (store);
    --   8) Single shot delivery of copied SM to destination . On delivery 
    --      failure, store copied SM in AMS (routeFallbackToStorage)
    --
    ----------------------------------------------------------------------------

    CopyAction ::=
        INTEGER {
            route(0),
            store(1),
            routeFallbackToStorage(2)
        }

    ----------------------------------------------------------------------------
    --
    --  Country specifies a two letter country code as defined in ISO 3166.
    --
    --  Some samples of the two letter country codes are:
    --
    --    nl for the Netherlands
    --    be for Belgium
    --    fr for France
    --    uk for United Kingdom
    --    de for Germany
    --
    --    Refer to http://ftp.ics.uci.edu/pub/ietf/http/related/iso3166.txt for
    --    more two letter country codes.
    --
    ----------------------------------------------------------------------------

    Country ::=
        OCTET STRING(SIZE (2..2))

    ----------------------------------------------------------------------------
    --
    --  CountryAreaCodeTableIndex1 defines the range for the first index of the 
    --  country area code table.
    --
    ----------------------------------------------------------------------------

    CountryAreaCodeTableIndex1 ::=
        INTEGER(1..500)

    ----------------------------------------------------------------------------
    --
    --  CountryAreaCodeTableIndex2 defines the range for the second index of the 
    --  country area code table.
    --
    ----------------------------------------------------------------------------

    CountryAreaCodeTableIndex2 ::=
        INTEGER(1..1000)

    ----------------------------------------------------------------------------
    --
    --  CountryTableIndex defines the range for the index of the country table.
    --
    ----------------------------------------------------------------------------

    CountryTableIndex ::=
        INTEGER(1..500)

    ----------------------------------------------------------------------------
    --
    --  Decimation specifies the rate of the MO/SM's that need to be delivered
    --  to an application and the total number of the MO/SM's received for the
    --  application. A result of decimation is that TextPass will drop a subset
    --  of the MO/SM's for an application.
    --
    --  Decimation also refers the ratio of passes to skipped in an MT rule.
    --
    --  The format for the specification of decimation is: M/N. Both M and N are
    --  integers in a range of 1-9999. Always, N should be equal to or greater
    --  than M.
    --
    --  Example:
    --      When decimation is specified as 2/3, TextPass will send two MO/SM's
    --      to the application, drop one MO/SM, send two MO/SM's to the
    --      application, drop one MO/SM, etc.
    --
    --      Alternatively, if decimation is used for an MT rule, 2/3 means
    --      TextPass will apply the rule for 2 MT messages and defer to
    --      subsequent rules for 1 MT message, etc.
    --
    ----------------------------------------------------------------------------

    Decimation ::=
        OCTET STRING(SIZE (3..9))

    ----------------------------------------------------------------------------
    --
    --  DefaultSmsHandling defines how TextPass should act when TextPass does a 
    --  CAMEL trigger for an SM and a communications error occurs with SCF.
    --
    ----------------------------------------------------------------------------

    DefaultSmsHandling ::= 
        INTEGER {
            continueTransaction (0),
            releaseTransaction (1)
        }

    ----------------------------------------------------------------------------
    --
    --  EcdrChargedParty defines the type for the chargedParty field in an 
    --  Ericsson CDR.
    --
    ----------------------------------------------------------------------------

    EcdrChargedParty ::= 
        INTEGER {
            chargingOfCallingSubscriber(0),
            chargingOfCalledSubscriber(1),
            noCharging(2)
        }
                    
    ----------------------------------------------------------------------------
    --
    --  EcdrExchangeIdentity defines the type for the exchangeIdentity field in 
    --  an Ericsson CDR.
    --
    ----------------------------------------------------------------------------

    EcdrExchangeIdentity ::=
        OCTET STRING (SIZE (1..15))
        
    ----------------------------------------------------------------------------
    --
    --  EcdrGsmTeleServiceCode defines the type for the gsmTeleServiceCode field 
    --  in an Ericsson CDR.
    --
    ----------------------------------------------------------------------------

    EcdrGsmTeleServiceCode ::=
        INTEGER {
            allSms(32),
            mtSms(33),
            moSms(34)
        }
        
    ----------------------------------------------------------------------------
    --
    --  EcdrOriginForCharging defines the type for the originForCharging field 
    --  in an Ericsson CDR.
    --
    ----------------------------------------------------------------------------

    EcdrOriginForCharging ::=
        Gauge(0..127)
        
    ----------------------------------------------------------------------------
    --
    --  EcdrRecordType defines the CDR types in an Ericsson CDR that are to be 
    --  used for SMS.
    --
    ----------------------------------------------------------------------------

    EcdrRecordType ::=
        INTEGER {
            msOriginatingSmsInMsc(0), 
            msOriginatingSmsInSmsIwMsc(1),
            msTerminatingSmsInMsc(2),
            msTerminatingSmsInSmsGmsc(3)
        }

    ----------------------------------------------------------------------------
    --
    --  EcdrRoute defines the type for the incomingRoute and outgoingRoute 
    --  fields in an Ericsson CDR.
    --
    ----------------------------------------------------------------------------

    EcdrRoute ::=
        OCTET STRING (SIZE (1..7)) 
        
    ----------------------------------------------------------------------------
    --
    --  EcdrToi defines the type for the TOI subfield of the TAC field in an
    --  Ericsson CDR.
    --
    ----------------------------------------------------------------------------

    EcdrToi ::=
        Gauge(0..255)
    
    ----------------------------------------------------------------------------
    --
    --  EcdrTos defines the type for the TOS subfield of the TAC field in an
    --  Ericsson CDR.
    --
    ----------------------------------------------------------------------------

    EcdrTos ::=
        Gauge(0..255)
        
    ----------------------------------------------------------------------------
    --
    --  EcdrTos defines the type for the TOS subfield of the TSC field in an
    --  Ericsson CDR.
    --
    ----------------------------------------------------------------------------

    EcdrTsc ::=
        Gauge(0..255)
        
    ----------------------------------------------------------------------------
    --
    --  EcdrRoute defines the type for the typeOfCallingSubscriber field in an 
    --  Ericsson CDR.
    --
    ----------------------------------------------------------------------------

    EcdrTypeOfCallingSubscriber ::=
        Gauge(0..15)

    ----------------------------------------------------------------------------
    --
    --  EciConnections defines the number of connections for an ExtCondition
    --  application.
    --
    ----------------------------------------------------------------------------

    EciConnections ::=
        Gauge (0..255)

    ----------------------------------------------------------------------------
    --
    --  ExternalConditionMessageField specifies a field to be checked when
    --  generating external condition messages.
    --
    ----------------------------------------------------------------------------

    ExternalConditionMessageField ::=
        INTEGER {
            noFieldSelected(0),
            messageKey(1),
            diameterStatus(2)
        }

    ----------------------------------------------------------------------------
    --
    --  externalConditionMessageTableIndex defines the index in the 
    --  externalConditionMessageTable
    --
    ----------------------------------------------------------------------------

    ExternalConditionMessageTableIndex ::=
        INTEGER (1..1000)

    ----------------------------------------------------------------------------
    --
    --  EciPassword defines an MD5 encoded password for a ExtCondition application.
    --
    --  Supplying a zero-length string for the encoded password results in
    --  TextPass to accept any password.
    --
    ----------------------------------------------------------------------------

    EciPassword ::=
        OCTET STRING (SIZE (0..16))

    ----------------------------------------------------------------------------
    --
    --  EciPriority is defined in the following matter:
    --
    --  1) The lowest possible priority has the minimum priority value
    --  2) The highest possible priority has the maximum priority value
    --
    ----------------------------------------------------------------------------

    EciPriority ::=
        Gauge(100..199)

    ----------------------------------------------------------------------------
    --
    --  EciTimer is used for ExternalCondition related timers
    --
    ----------------------------------------------------------------------------

    EciTimer ::=
        Gauge(0..3600)

    ----------------------------------------------------------------------------
    --
    --  EciUserIdentity defines the user identity for a ExternalCondition appl.
    --
    ----------------------------------------------------------------------------

    EciUserIdentity ::=
        OCTET STRING (SIZE (0..16))

    ----------------------------------------------------------------------------
    --
    --  ErrorClassification specifies how an error from an MT delivery attempt
    --  of an MO/SM should be treated. In case the error is permanentForMessage, 
    --  TextPass discards the SM. In case the error is permanentForRecipient, 
    --  TextPass discards the SM and all other pending messages for the 
    --  recipient. In case the error is temporary, TextPass forwards the SM to a 
    --  backup destination. This destination is either an SMSC, an application,
    --  or storage.
    --
    ----------------------------------------------------------------------------

    ErrorClassification ::=
        INTEGER {
            temporary(0),
            permanentForRecipient(1),
            permanentForMessage(2)
        }

    ----------------------------------------------------------------------------
    --
    --  ErrorString specifies a string containing an error message.
    --
    ----------------------------------------------------------------------------

    ErrorString ::= TEXTUAL-CONVENTION
        DISPLAY-HINT "0124a"
        STATUS mandatory
        DESCRIPTION "String containing an error message"
        SYNTAX OCTET STRING (SIZE (0..1024))

    ----------------------------------------------------------------------------
    --
    --  EventLoggingType specifies how an event should be reported.
    --
    ----------------------------------------------------------------------------

    EventReportingType ::=
        INTEGER {
            asTrap(0),
            asLogMessage(1),
            ignore(2)
        }

    ----------------------------------------------------------------------------
    --
    --  ExtAttrTableIndex defines the index for the ExtAttrTable
    --
    ----------------------------------------------------------------------------

    ExtAttrTableIndex ::=
        INTEGER (1..32)

    ----------------------------------------------------------------------------
    --
    --  ExtAttrId defines an ID that can be used to refer to an external 
    --  attribute.
    --
    --  Value 0 means that no external attribute is referred to.
    --
    ----------------------------------------------------------------------------

    ExtAttrId ::=
        Gauge (0..32)

    ----------------------------------------------------------------------------
    --
    --
    --  ExtCondAoAction defines the action to be taken on failure of evaluating
    --  an aoExtCondRule.
    --
    --  The following failure actions are supported:
    --
    --  1) Do nothing (i.e. ignore the ExtCondition result)
    --  2) Return an error to originator
    --  3) Return an ack to originator and discard message
    --
    ----------------------------------------------------------------------------

    ExtCondAoAction ::=
        INTEGER {
            none(0),
            discardWithNak(1),
            discardWithAck(2)
        }

    ----------------------------------------------------------------------------
    --
    --  ExtCondAtAction defines the action to be taken on failure of evaluating
    --  an atExtCondRule.
    --
    --  The following failure actions are supported:
    --
    --  1) Do nothing (i.e. ignore the ExtCondition result)
    --  2) Block SM by returning an error to the SMSC that causes the SMSC to
    --     consider the recipient as temporarily unavailable and will lead to
    --     another delivery attempt at a later time (blockWithTemporaryError).
    --  3) Block SM by returning an error to the SMSC that causes the SMSC to
    --     consider the SM as undeliverable and will not lead to any further
    --     delivery attempts for this SM (blockWithPermanentError).
    --  4) Block SM and return a success response to the SMSC, which cases the
    --     SMSC to treat the SM as being delivered to the destination.
    --
    ----------------------------------------------------------------------------

    ExtCondAtAction ::=
        INTEGER {
            none(0),
            blockWithTemporaryError(1),
            blockWithPermanentError(2),
            blockWithAck(3)
        }

    ----------------------------------------------------------------------------
    --
    --  ExtCondMoAction defines the action to be taken on failure of evaluating
    --  an moExtCondRule.
    --
    --  The following failure actions are supported:
    --
    --  1) Do nothing (i.e. ignore the ExtCondition result)
    --  2) Return an error to originator
    --  3) Return an ack to originator and discard message
    --
    ----------------------------------------------------------------------------

    ExtCondMoAction ::=
        INTEGER {
            none(0),
            discardWithNak(1),
            discardWithAck(2),
            discardWithNoResponse(3)
        }

    ----------------------------------------------------------------------------
    --
    --  ExtCondMtAction defines the action to be taken on failure of evaluating
    --  an mtExtCondRule.
    --
    --  The following failure actions are supported:
    --
    --  1) Do nothing (i.e. ignore the ExtCondition result)
    --  2) Block SM by returning an error to the SMSC that causes the SMSC to
    --     consider the recipient as temporarily unavailable and will lead to
    --     another delivery attempt at a later time (blockWithTemporaryError).
    --  3) Block SM by returning an error to the SMSC that causes the SMSC to
    --     consider the SM as undeliverable and will not lead to any further
    --     delivery attempts for this SM (blockWithPermanentError).
    --
    ----------------------------------------------------------------------------

    ExtCondMtAction ::=
        INTEGER {
            none(0),
            blockWithTemporaryError(1),
            blockWithPermanentError(2),
            blockWithNoResponse(3),
            blockWithAck(4)
        }

    ----------------------------------------------------------------------------
    --
    --  ExternalConditionTableIndex defines the index for the ExternalConditionTable
    --
    ----------------------------------------------------------------------------

    ExternalConditionTableIndex ::=
        INTEGER (1..100)

    ----------------------------------------------------------------------------
    --
    --  ExternalConditionAttributeTableIndex defines the index for the 
    --  ExternalConditionAttributeTable. Currently not implemented.
    --
    ----------------------------------------------------------------------------

    ExternalConditionAttributeTableIndex ::=
        INTEGER (1..32)

    ----------------------------------------------------------------------------
    --
    --  ExternalConditionRef defines the reference to an ExternalCondition in 
    --  ExternalConditionTable. 
    --  Value 0 is used to indicate no index is specified. 
    --  Any other value refers to the index of a ExternalCondition in the 
    --  ExternalConditionTable.
    -- 
    ----------------------------------------------------------------------------

    ExternalConditionRef ::=
        INTEGER(0..100)

    ----------------------------------------------------------------------------
    --
    --  ExternalConditionClientTableIndex defines the index for the ExternalConditionClientTable
    --
    ----------------------------------------------------------------------------
    
    ExternalConditionClientTableIndex ::=
        INTEGER (1..65535)

    ----------------------------------------------------------------------------
    --
    --  FileSpec specifies a full filename or full directory name.
    --
    ----------------------------------------------------------------------------

    FileSpec ::= TEXTUAL-CONVENTION
        DISPLAY-HINT "255a"
        STATUS mandatory
        DESCRIPTION "File name speification"
        SYNTAX OCTET STRING (SIZE (0..255))
        
    ----------------------------------------------------------------------------
    --
    --  FcdrStatus defines the values used for the 'Status field in a FCDR.
    --
    ----------------------------------------------------------------------------

    FcdrStatus ::=
        INTEGER {
            delivered(0),
            expired(1),
            deleted(2),
            replaced(3),
            submitted(4)
        }

    ----------------------------------------------------------------------------
    --
    --  FcdrMaxPeriod defines a threshold for the maximum that is used for 
    --  "period" fields in FCDR-formatted billing records. it is expressed in
    --  number of hours.
    --
    ----------------------------------------------------------------------------

    FcdrMaxPeriod ::= 
        Gauge(0..8760)                                                 -- 1 year

    ----------------------------------------------------------------------------
    --
    --  ForwardExceptionAction defines how an SM that is subject to forwarding 
    --  should be handled for an exceptional case
    --
    --  TextPass supports the following blocking actions:
    --
    --  1) Forward SM to forwarded address
    --  2) Block SM by returning an error to the SMSC that causes the SMSC to
    --     consider the recipient as temporarily unavailable and will lead to
    --     another delivery attempt at a later time (blockWithTemporaryError).
    --  3) Block SM by returning an error to the SMSC that causes the SMSC to
    --     consider the SM as undeliverable and will not lead to any further
    --     delivery attempts for this SM (blockWithPermanentError).
    --  4) Block SM and return a success response to the SMSC, which cases the
    --     SMSC to treat the SM as being delivered to the destination 
    --     (blockWithAck).
    --
    --  Note that blockWithTemporaryError has the benefit that the current 
    --  SM will have another chance to get delivered (providing forwarding is
    --  conditional). However, it will block any other SM that is pending in the
    --  SMSC for the recipient. The actions blockWithAck and 
    --  blockWithPermanentError do not block any other pending SM-s. It will, 
    --  however, bluntly discard the current SM.
    -- 
    ----------------------------------------------------------------------------

    ForwardExceptionAction ::=
        INTEGER {
            pass(0),
            blockWithTemporaryError(1),
            blockWithPermanentError(2),
            blockWithAck(4)
        }

    ----------------------------------------------------------------------------
    --
    --  GroupType specifies the type of members a group may have.
    --
    ----------------------------------------------------------------------------

    GroupType ::=
        INTEGER {
            undefined(0),
            application(1)
        }

    ----------------------------------------------------------------------------
    --
    --  GsmAcTableIndex defines the index for the gsmAcTable
    --
    ----------------------------------------------------------------------------

    GsmAcTableIndex ::=
        INTEGER (1..1000)

    ----------------------------------------------------------------------------
    --
    --  GsmAcOutputType indicates how an address should be treated by the rule
    --  processor. The rule processor maintains two address types: SHORTNUMBER
    --  and MSISDN. 
    --
    --  Possible values for GsmAcOutputType are:
    --  - determinedByLength, implying that the address type is determined on 
    --    the basis of the address length. If the length exceeds the threshold
    --    that has been configured for the maximum length of a short number, the
    --    rule processor will treat the address as an MSISDN. Otherwise, it will
    --    be treates as a SHORTNUMBER. 
    --  - msisdn, indicating that the rule processor should treat the address as
    --    an MSISDN
    --  - shortNumber, indicating that the rule processor should treat the 
    --    address as a SHORTNUMBER.
    --
    ----------------------------------------------------------------------------

    GsmAcOutputType ::=
        INTEGER {
            determinedByLength(0),
            msisdn(1),
            shortNumber(2)
        }

    ----------------------------------------------------------------------------
    --
    --  GsmAddress specifies any address that can be specified in GSM
    --
    ----------------------------------------------------------------------------

    GsmAddress ::=                                -- should contain digits only
        OCTET STRING(SIZE (0..38))

    ----------------------------------------------------------------------------
    --
    --  GsmAddressPrefixWithAreaCodeSpecifier specifies any address that can be 
    --  specified in GSM, optionally including one at sign (@), which 
    --  represents the area code as present in the originator of the message.
    --
    ----------------------------------------------------------------------------

    GsmAddressPrefixWithAreaCodeSpecifier ::=      -- should contain digits and
        OCTET STRING(SIZE (0..38))                          -- optionally one @

    ----------------------------------------------------------------------------
    --
    --  GsmAddressLength specifies the length for a GSM address
    --
    ----------------------------------------------------------------------------

    GsmAddressLength ::=
        Gauge(0..38)

    ----------------------------------------------------------------------------
    --
    --  GsmAddressRange specifies a number range formatted as following:
    --
    --  a) an internationally encoded address excluding the international prefix
    --     of at most 38 digits, followed by
    --  b) a dash (-), followed by
    --  c) an internationally encoded address excluding the international prefix
    --     of at most 38 digits
    --
    --  To clear a number range, overwrite it with a zero-length string.
    --
    ----------------------------------------------------------------------------

    GsmAddressRange ::=
        OCTET STRING (SIZE (0..77))

    ----------------------------------------------------------------------------
    --
    --  GsmCharCode defines characters from the GSM default alphabet.
    --
    --  The GSM default alphabet consists of a basic table and an extension
    --  table. The basic table defines the coding for the characters that are
    --  encoded by a single septet. The extension table defines the coding for
    --  characters that are encoded by means of two septets; the first septet
    --  being an escape character and the second septet indentifying a special
    --  character (e.g. the EURO sign).
    --
    ----------------------------------------------------------------------------

    GsmCharCode ::=
        OCTET STRING (SIZE (1..2))

    ----------------------------------------------------------------------------
    --
    --  GsmError defines the errors as used in GSM
    --
    ----------------------------------------------------------------------------

    GsmError ::=
        INTEGER {
            unknownSubscriber(0),
            absentSubscriber(1),
            systemFailure(2),
            facilityNotSupported(3),
            memoryCapacityExceeded(4),
            equipmentProtocolError(5),
            equipmentNotSmEquipped(6),
            unknownServiceCentre(7),
            scCongestion(8),
            invalidSmeAddress(9),
            subscriberNotScSubscriber(10)
        }

    ----------------------------------------------------------------------------
    --
    --  Number of digits in a Global Title
    --
    ----------------------------------------------------------------------------

    GtDigitCount ::= INTEGER(0..31)

    ----------------------------------------------------------------------------
    --
    --  HexAddressString defines a hexadecimal string to be used for addresses.
    --
    ----------------------------------------------------------------------------

    HexAddressString ::= 
        OCTET STRING(SIZE (0..15))                              -- 0-9, A-F only

    ----------------------------------------------------------------------------
    --
    --  Imsi defines an IMSI
    --
    ----------------------------------------------------------------------------

    Imsi ::=                                       -- should contain digits only
        OCTET STRING(SIZE (0..15))

    ----------------------------------------------------------------------------
    --
    --  IncludeMscAddrIndicator defines configuration options for feature that
    --  includes MSC address in SCCP calling party address of MO Forward SM
    --  operation towards SMSC.
    --
    ----------------------------------------------------------------------------

    IncludeMscAddrIndicator ::=
        INTEGER {
            never(0),
            always(1),
            foreignOnly(2)
        }

    ----------------------------------------------------------------------------
    --
    --   A sequence of decimal numbers each of them preceded by an @ sign.
    --   Each of the numbers signifies the presence of one corresponding
    --   CDR field as specified in the section "Logica CDR (LCDR) Formatting"
    --   in the Tekelec Billing Manual.
    --
    --   EG @6@20@15@13
    --
    --   The actual appearance of a field value may be  adjusted by using 
    --   "printf" style formatting. Each field has a pre-determined type. 
    --   The actual type of each field can be found in sub-section "Supported
    --   Parameters" in the Tekelec Billing Manual.
    --   The following example explains the mechanism:
    --
    --   EG @6$%-20s@20$%03d@15$%dC@13$%12.12s
    --	
    --   This format string will make sure that LCDR output contains 4 fields: 
    --     field 6, 20, 15 and 13:
	--	   Field 6 of type string will appear left aligned and will use the
	--     space of 20 characters.
    --     Field 20 of type integer will use the space of 3 characters and will 
    --     be padded with zeros on the left.
    --     Field 15 of type integer will have the character 'C' after it.
    --     Field 13 of type string will always take the space of 12 characters, 
    --     even if the original variable was shorter or longer than that.
    --   Sub-section "Supported Parameters" in the section "Logica CDR (LCDR) 
    --   Formatting" describes all fields as they can be used in the LCDR.
    --
    ----------------------------------------------------------------------------

    LcdrCustomFormat ::=
        OCTET STRING(SIZE(0..300))

    ----------------------------------------------------------------------------
    --
    --  LcdrRouterId defines an ID for router that is used in the generation of 
    --  the ISN field of a Logica CDR.
    --
    ----------------------------------------------------------------------------
    
    LcdrRouterId ::= 
        Gauge(0..31)

    ----------------------------------------------------------------------------
    --
    --  ListTableIndex defines the range for the index of the list table.
    --
    ----------------------------------------------------------------------------

    ListTableIndex ::=
        INTEGER(1..1000)

    ----------------------------------------------------------------------------
    --
    --  ListTableRef defines a reference into the list table (by index).
    --
    ----------------------------------------------------------------------------

    ListTableRef ::=
        INTEGER(0..1000)

    ----------------------------------------------------------------------------
    --
    --  ListConditionTableIndex defines the range for the index of the
    --  listCondition table.
    --
    ----------------------------------------------------------------------------

    ListConditionTableIndex ::=
        INTEGER(1..10000)

    ----------------------------------------------------------------------------
    --  ListType specifies whether the originator list that
    --  is associated with the application is a white list or a black list.
    ----------------------------------------------------------------------------

    ListType ::=
        INTEGER {
            whiteList(0),
            blackList(1)
        }

    ----------------------------------------------------------------------------
    --
    --  ListTypeBits is a 32-bit bitmask for indicating the condition types
    --  contained in the list.
    --  Mapping of types onto the bits (values in hex):
    --  0x0001 = MSISDN
    --  0x0002 = IMSI
    --  0x0004 = PointCode
    --  0x0008 = ShortNumber
    --  future use:
    --  0x0010 = Country
    --  0x0020 = Network
    --  0x0040 = Application
    --  0x0080 = PID
    --  0x0100 = TON
    --  0x0200 = NPI
    --  0x0400 = DCS
    --  0x0800 = Alphanumeric 
    --  0x1000 - 0x8000 = reserve
    --

    ----------------------------------------------------------------------------
    ListTypeBits ::=
        Gauge

    ----------------------------------------------------------------------------
    --
    --  LoadBalancingGroupMemberTableIndex defines the range for the (second)
    --  index of the loadBalancingGroupMemberTable. It shall cover the range
    --  of the largest table referred to by the group's type parameter.
    --  Currently, this is the applicationTable.
    --
    ----------------------------------------------------------------------------

    LoadBalancingGroupMemberTableIndex ::=
        INTEGER(1..10000)

    ----------------------------------------------------------------------------
    --
    --  LoadBalancingGroupReference specifies a reference to a load balancing
    --  group. The value '0' means that no group is referenced.
    --
    ----------------------------------------------------------------------------

    LoadBalancingGroupReference ::=
        INTEGER(0..1000)

    ----------------------------------------------------------------------------
    --
    --  LoadBalancingGroupTableIndex defines the range for the index of the
    --  loadBalancingGroupTable.
    --
    ----------------------------------------------------------------------------

    LoadBalancingGroupTableIndex ::=
        INTEGER(1..1000)

    ----------------------------------------------------------------------------
    --
    --  LogAcceptedAndRejectedMessages determines logging of accepted and
    --  rejected messages.
    --
    ----------------------------------------------------------------------------

    LogAcceptedAndRejectedMessages ::=
        INTEGER {
            acceptedAndRejected(0),
            acceptedOnly(1),
            rejectedOnly(2)
        }

    ----------------------------------------------------------------------------
    --
    --  LogAffectedMessageTypes defines for each message type whether the logging
    --  profile pertains or does not pertain. The definition is done using a bit
    --  string. Each bit in the bit string relates to a specific message type. If
    --  the bit is 1, the message type applies. Otherwise, if the bit is 0, the
    --  message type does not apply.
    --
    --    Bit                     Message Type
    --    -------------------------------------
    --     0 (most significant)   inbound MO
    --     1                      inbound MT
    --     2                      inbound SriSm
    --     3                      inbound AO
    --     4                      inbound AT
    --     5                      AMS delivery attempt or
    --                            intermediate notification
    --     6                      inbound CO (CDMA MO)
    --     7                      sms command MO
    --     8                      sms command AO
    --     9                      MNP violation
    --     10                     reserved-for-future-use
    --     11                     reserved-for-future-use
    --     12                     reserved-for-future-use
    --     13                     reserved-for-future-use
    --     14                     reserved-for-future-use
    --     15 (least significant) reserved-for-future-use
    --
    --     All bits thatare reserved for future use should be set to 0.
    --
    ----------------------------------------------------------------------------

    LogAffectedMessageTypes ::=
        OCTET STRING (SIZE (16..16))

    ----------------------------------------------------------------------------
    --
    --  LogFailedAndSucceededMessages determines logging of failed and succeeded
    --  messages.
    --
    ----------------------------------------------------------------------------

    LogFailedAndSucceededMessages ::=
        INTEGER {
            failedAndSucceeded(0),
            failedOnly(1),
            succeededOnly(2)
        }

    ----------------------------------------------------------------------------
    --
    --  LogFileDuration defines the legitimate values for the duration of a
    --  logging file, expressed in units of seconds.
    --
    ----------------------------------------------------------------------------

    LogFileDuration ::=
        Gauge(1..2678400)                                             -- 1 month

    ----------------------------------------------------------------------------
    --
    --  LogFileFormat defines the format of logging file.
    --
    ----------------------------------------------------------------------------

    LogFileFormat ::=
        INTEGER{
            asn1Extended(1),
            asn1ExtendedWithCountryAndNetworkInfo(2)
        }

    ----------------------------------------------------------------------------
    --
    --  LogFileRecords defines the legitimate values for the maximum number of
    --  records in a logging file.
    --
    ----------------------------------------------------------------------------

    LogFileRecords ::=
        Gauge(1..10000000)

    ----------------------------------------------------------------------------
    --
    --  LogFileSize defines the legitimate values for the size of a logging
    --  file, expressed in bytes.
    --
    ----------------------------------------------------------------------------

    LogFileSize ::=
        Gauge(1024..1073741824)                                       -- 1K - 1G

    ----------------------------------------------------------------------------
    --
    --  LogLegitimateAndViolatedMessages determines logging of legitimated and
    --  violated messages.
    --
    ----------------------------------------------------------------------------

    LogLegitimateAndViolatedMessages ::=
        INTEGER {
            legitimateAndViolated(0),
            legitimateOnly(1),
            violatedOnly(2)
        }

    ----------------------------------------------------------------------------
    --
    --  LogExpirdDltdRplacdMessageTypes determines logging of expired, deleted
    --  and replaced messages (also called Terminated messages).
    --
    ----------------------------------------------------------------------------

    LogExpirdDltdRplacdMessageTypes ::=
        INTEGER {
            doNotLog(0),
            expired(1),
            deleted(2),
            expiredDeleted(3),
            replaced(4),
            expiredReplaced(5),
            deletedReplaced(6),
            expiredDeletedReplaced(7)
        }

    ----------------------------------------------------------------------------
    --
    --  LogStatusReportMessageTypes determines logging of status reports.
    --
    ----------------------------------------------------------------------------

    LogStatusReportMessageTypes ::=
        INTEGER {
            doNotLog(0),
            statusReports(1)
        }

    ----------------------------------------------------------------------------
    --
    --  LogCopiedForwardedMessageTypes determines logging of copied and
    --  forwarded messages.
    --
    ----------------------------------------------------------------------------

    LogCopiedForwardedMessageTypes ::=
        INTEGER {
            doNotLog(0),
            copied(1),
            forwarded(2),
            copiedForwarded(3)
        }

    ----------------------------------------------------------------------------
    --
    --  LogProfile specifies whether logging is generated at all. When logging
    --  is generated, LogProfile specifies whether the default logging profile
    --  is to be used or a specific logging profile is to be applied. In the
    --  latter case, LogProfile specifies a reference to the logging profile
    --  that is to be applied.
    --
    --  The following table defines the legitimate values of LogProfile:
    --
    --    Value      Description
    --    ---------------------------------------------------------------------
    --      0        No logging is to be generated
    --    1-100      Logging is to be generated using a specific logging
    --               profile. The value determines which logging profile as it
    --               contains the SNMP table index of the logging profile in the
    --               logging profile table.
    --     1000      Logging is to be generated using the default logging
    --               profile.
    --
    ----------------------------------------------------------------------------

    LogProfile ::=
        Gauge (0..1000)

    ----------------------------------------------------------------------------
    --
    --  EventProfile specifies the event log profile or 0 for disabled.
    --
    ----------------------------------------------------------------------------

    EventProfile ::=
        Gauge (0..100)

    ----------------------------------------------------------------------------
    --
    --  LogProfileTableIndex defines the index for the LogProfileTable
    --
    ----------------------------------------------------------------------------

    LogProfileTableIndex ::=
        INTEGER (1..100)

    ----------------------------------------------------------------------------
    --
    --  LogSuspectAndTrustedMessages determines logging of suspect and trusted
    --  messages.
    --
    ----------------------------------------------------------------------------

    LogSuspectAndTrustedMessages ::=
        INTEGER{
            suspectAndTrusted(0),
            suspectOnly(1),
            trustedOnly(2)
        }

    ----------------------------------------------------------------------------
    --
    --  LogTransparentUserDataLevel determines in which cases the log files show 
    --  the User Data transparantly. For the case where the User Data is not shown 
    --  transparently, it will contain X-s.
    --
    ----------------------------------------------------------------------------
    
    LogTransparentUserDataLevel ::=
        INTEGER{
            always(0),
            protocolViolationsOnly(1),
            never(2)
        }
    
    ----------------------------------------------------------------------------
    --
    --  MapPhase defines the MAP phase to be used
    --
    ----------------------------------------------------------------------------

    MapPhase ::=
        INTEGER {
           phase1(1),
           phase2(2),
           phase2plus(3)
        }

    ----------------------------------------------------------------------------
    --
    --  MaxStatusReportRetries defines the range for the number of retries for 
    --  the status reports.
    --
    ----------------------------------------------------------------------------

    MaxStatusReportRetries ::= 
        Gauge(1..20)

    ----------------------------------------------------------------------------
    --
    --  MessageKeyWeights defines a format for specifying the weights to be used
    --  when calculating a key for a message. The format consists of two weight-
    --  lists, separated by a colon. The weight-list before the colon specifies
    --  the weights for the originator number, the weight-list after the colon
    --  specifies the weights for the destination number. Each weight-list is
    --  a comma-separated list of unsigned integer weights. Each list may be
    --  empty. Only decimal digits and comma characters are allowed in the
    --  string. The first weight parsed is considered to be the weight for the
    --  last/least significant digit of the message's originator or destination
    --  number. The second weight is considered to be the weight for the second
    --  least significant digit, and so on. A maximum of 20 weights per number
    --  is supported. If the number has more digits than the number of weights
    --  specified for that number, then, the remaining digits have a weight of 0,
    --  i.e. they have no effect. The key is calculated as the weighted sum of
    --  the originator and destination digits.
    --
    --  Examples:
    --
    --  1)  originator number   '12345678'
    --      destination number  '87654321'
    --      MessageKeyWeights   "2,15:1,10"
    --
    --      Key = 2 * orig(0) + 15 * orig(1) + 1 * dest(0) + 10 * dest(1)
    --          = 2 * 8       + 15 * 7       + 1 * 1       + 10 * 2
    --          = 16          + 105          + 1           + 20
    --          = 142
    --
    --  2)  originator number   '12345678'
    --      destination number  '87654321'
    --      MessageKeyWeights   ":1000,100,10,1"
    --
    --      Key = 1000 * dest(0) + 100 * dest(1) + 10 * dest(2) + 1 * dest(3)
    --          = 1000 * 1       + 100 * 2       + 10 * 3       + 1 * 4
    --          = 1000           + 200           + 30           + 4
    --          = 1234
    --
    ----------------------------------------------------------------------------

    MessageKeyWeights ::=
        OCTET STRING(SIZE (1..255))

    ----------------------------------------------------------------------------
    --
    --  MessageTemplate is the UTF-8 encoded template for generating a message.
    --
    ----------------------------------------------------------------------------

    MessageTemplate ::=
        OCTET STRING(SIZE (0..480))

    ----------------------------------------------------------------------------
    --
    --  MessageTypeFilter is a bitmask made of '0' and '1' characters that
    --  specifies which message types shall be filtered. The bit positions
    --  have been assigned as follows:
    --
    --      0 MO message (right-most and last in the string)
    --      1 MT message
    --      2 AO message
    --      3 AT message
    --      4 HLR query (SRI-SM)
    --      5 HLR response (SRI-SM)
    --      6 MT status report
    --      7 AT notification (left-most)
    --
    --  Example: A filter that filters MO and AT messages could use the bitmask
    --           "1001" or "00001001". A filter that filters status reports and
    --          notifications must use "11000000".
    --
    ----------------------------------------------------------------------------

    MessageTypeFilter ::=
        OCTET STRING(SIZE (0..8))


    ----------------------------------------------------------------------------
    --
    --  MobileCountryCode specifies the country code as used in mobile networks.
    --  This country code is used in, for example, the IMSI.
    --
    --  Some samples of the mobile country codes are:
    --
    --    204 for the Netherlands
    --    206 for Belgium
    --    208 for France
    --    234 for United Kingdom
    --    262 for Germany
    --
    --    Refer to http://users.zipworld.com.au/~rmills/MCCandMNCValues.htm for
    --    more mobile country codes.
    --
    ----------------------------------------------------------------------------

    MobileCountryCode ::=                          -- should contain digits only
        OCTET STRING(SIZE (3..3))

    ----------------------------------------------------------------------------
    --
    --  MobileCountryCodes specifies a comma-seperated list of mobile country
    --  codes. The list contains at least one mobile country code and at most 16
    --  mobile country codes.
    --
    ----------------------------------------------------------------------------

    MobileCountryCodes ::=                         
        OCTET STRING(SIZE (3..63))

    ----------------------------------------------------------------------------
    --
    --  MobileNetworkCode identifies a mobile network in a country. This
    --  network code is used in, for example, the IMSI
    --
    --  The Dutch mobile network codes are:
    --
    --    04 - Vodafone
    --    08 - KPN mobile
    --    12 - O2
    --    16 - Ben
    --    20 - Dutchtone
    --
    --  Refer to http://users.zipworld.com.au/~rmills/MCCandMNCValues.htm for
    --  mobile network codes in other countries.
    --
    ----------------------------------------------------------------------------

    MobileNetworkCode ::=                          -- should contain digits only
        OCTET STRING(SIZE (2..3))

    ----------------------------------------------------------------------------
    --
    --  MobileNetworkCodes is a comma-seperated list of mobile network codes;
    --  these are valid on a per-country basis and identify a network operator.
    --
    --  An MNC is found inside the IMSI.  So, for example, 
    --
    --  The Dutch mobile network codes are:
    --
    --    04 - Vodafone
    --    08 - KPN mobile
    --    12 - O2
    --    16 - Ben
    --    20 - Dutchtone
    --
    --  These codes are only valid inside Holland.  You know you're inside
    --  Holland by the country code in the IMSI.
    --
    --  The maximum length reflects the fact that an individual code is 2 or 3
    --  numbers long and there is a comma between every element except for the
    --  final element; the string is not NULL terminated.
    --
    --  Refer to http://users.zipworld.com.au/~rmills/MCCandMNCValues.htm for
    --  mobile network codes in other countries.
    --
    ----------------------------------------------------------------------------

    MobileNetworkCodes ::=              -- should contain digits and commas only
        OCTET STRING(SIZE (2..399))

    ----------------------------------------------------------------------------
    --
    --  MobNetworkTableIndex defines the range for the index of the mobile
    --  network table.
    --
    ----------------------------------------------------------------------------

    MobNetworkTableIndex ::=
        INTEGER(1..1000)

    ----------------------------------------------------------------------------
    --
    --  MobNetworkNumberRangeTableIndex defines the range for the index of the
    --  number range table, which is a subordinate table of the mobile network
    --  table.
    --
    ----------------------------------------------------------------------------

    MobNetworkNumberRangeTableIndex ::=
        INTEGER(1..100)

    ----------------------------------------------------------------------------
    --
    --  MoAction defines how an SM originated by an MS should be routed.
    --
    --  TextPass supports the following routing actions:
    --
    --   1) Route SM to an SMSC (routeToSmsc);
    --   2) Bypass SMSC and route SM directly to an application
    --      (routeToApplication)
    --   3) Bypass SMSC initially and deliver SM directly to MS. On delivery
    --      failure, route SM to SMSC (routeToMsFallbackToSMSC)
    --   4) Return an error to originator and
    --   5) Return an ack to originator and discard message
    --   6) Deliver SM directly to MS. On delivery failure, route SM to
    --      application (routeToMsFallbackToApplication)
    --   7) Discard SM silently (discardWithNoResponse)
    --   8) Store SM for delivery to MS (storeForDeliveryToMs)
    --   9) Deliver SM directly to MS. On delivery failure, store SM in AMS
    --      (routeToMsFallbackToStorage)
    --  10) Store SM for delivery to application (storeForDeliveryToApplication)
    --  11) Route SM directly to application. On delivery failure, store SM in 
    --      AMS (routeToApplicationFallbackToStorage)
    --  12) Route SM to an SMSC using the application interface rather than
    --      the SS7 link (routeToSmscAsAo)
    --  13) Bypass SMSC initially and deliver SM directly to MS. On delivery
    --      failure, route SM to SMSC using the application interface rather
    --      than the SS7 link (routeToMsFallbackToSmscAsAo)
    --
    ----------------------------------------------------------------------------

    MoAction ::=
        INTEGER {
            routeToSmsc(0),
            routeToApplication(1),
            routeToMs(2),
            routeToMsFallbackToSmsc(3),
            discardWithNak(4),
            discardWithAck(5),
            routeToMsFallbackToApplication(6),
            discardWithNoResponse(7),
            storeForDeliveryToMs(8),
            routeToMsFallbackToStorage(9),
            storeForDeliveryToApplication(10),
            routeToApplicationFallbackToStorage(11),
            routeToSmscAsAo(12),
            routeToMsFallbackToSmscAsAo(13)
        }

    ----------------------------------------------------------------------------
    --
    --  MoCntRuleTableIndex defines the range for the index of the MO counting
    --  rule table.
    --
    ----------------------------------------------------------------------------

    MoCntRuleTableIndex ::=
        INTEGER(1..500)

    ----------------------------------------------------------------------------
    --
    --  MoExtCondRuleTableIndex defines the range for the index of the MO
    --  ExternalCondition rule table.
    --
    ----------------------------------------------------------------------------

    MoExtCondRuleTableIndex ::=
        INTEGER(1..500)

    ----------------------------------------------------------------------------
    --
    --  MoRtgRuleTableIndex defines the range for the index of the MO routing
    --  rule table.
    --
    ----------------------------------------------------------------------------

    MoRtgRuleTableIndex ::=
        INTEGER(1..500)

    ----------------------------------------------------------------------------
    --
    --  MoModifierTableIndex defines the range for the index of the MO modifier
    --  table.
    --
    ----------------------------------------------------------------------------

    MoModifierTableIndex ::=
        INTEGER(1..100)

    ----------------------------------------------------------------------------
    --
    --  MoModifierRef defines the reference to an MO modifier. Value 0 is
    --  used to clear a reference. Any other value refers to the index of a
    --  modifier in the MO modifier table.
    --
    ----------------------------------------------------------------------------

    MoModifierRef ::=
        Gauge(0..100)

    ----------------------------------------------------------------------------
    --
    --  MoSmscRefOperationalState reflects the operational state of an SMSC in
    --  an MO routing rule.
    --
    ----------------------------------------------------------------------------

    MoSmscRefOperationalState ::=
        INTEGER {
            adminDisabled(0),
            throughputExceeded(1),
            available(2)
        }

    ----------------------------------------------------------------------------
    --
    --  MoSmTrustedOriginatorTableIndex defines the range for the index of the 
    --  MO/SM Trusted Originator table.
    --
    ----------------------------------------------------------------------------

    MoSmTrustedOriginatorTableIndex ::= 
        INTEGER(1..16)

    ----------------------------------------------------------------------------
    --
    --  MoSpoofingAction defines how spoofing for an SM originated by an MS
    --  should be handled.

    --
    --  TextPass supports the following routing actions:
    --
    --  1) Return an error to originator and
    --  2) Return an ack to originator and discard message
    --  3) Discard SM silently
    --
    ----------------------------------------------------------------------------

    MoSpoofingAction ::=
        INTEGER {
            discardWithNak(4),
            discardWithAck(5),
            discardWithNoResponse(7),
            pass(127)
        }

    ----------------------------------------------------------------------------
    --
    --  MoSpoofingCheckCondition determines when an MO spoofing check is done.
    --
    --  The possible settings are:
    --  1) always
    --  2) only when MSC (or SGSN) addresses the SMSC using GT (This enables the
    --     operator to restrict checking of MO spoofing to MO/SM's originated
    --     from outside his own network. It requires that all MSC's and SGSN's
    --     within the operator's network have a GTT rule for the public SMSC
    --     address.
    --  3) never
    --
    ----------------------------------------------------------------------------

    MoSpoofingCheckCondition ::=
        INTEGER {
            always(0),
            whenMscSgsnAddressingSmscOnGt(1),
            never(2)
        }

   ----------------------------------------------------------------------------
    --
    --  MoTagFunction specifies the function that is being triggered by a tag
    --  in an MO/SM.
    --
    --  Note that the availability of an MO tag function is subject to the MO 
    --  tag mode that has been configured. When tag mode is advanced, tag 
    --  functions that require parameters are supported. When tag mode is 
    --  simple, tag functions that require parameters are not supported. 
    --
    ----------------------------------------------------------------------------

    MoTagFunction ::=
        INTEGER {
            phase1StatusReport(0),
            deferredDeliveryRelativeHours(1)           -- requires advanced mode
        }

    ----------------------------------------------------------------------------
    --
    --  MoTagTableIndex defines the index for the moTagTable
    --
    ----------------------------------------------------------------------------

    MoTagTableIndex ::=
        INTEGER (1..100)

    ----------------------------------------------------------------------------
    --
    --  MoTagString specifies the string for a tag in an MO/SM that triggers
    --  a specific function.
    --
    ----------------------------------------------------------------------------

    MoTagString ::= TEXTUAL-CONVENTION
        DISPLAY-HINT "160a"
        STATUS mandatory
        DESCRIPTION "String for a tag in an MO/SM"
        SYNTAX OCTET STRING (SIZE (1..160))

    ----------------------------------------------------------------------------
    --
    --  ImsiRange specifies a range of 0- to 15-digit IMSIs formatted as 
    --- following:
    --
    --  a) a 0- to 15-digit IMSI, followed by
    --  b) a dash (-), followed by
    --  c) a 0- to 15-digit IMSI
    --
    --  The length of a) and c) must be equal, and a) must be lower than or
    --  equal to c). 
    --
    ----------------------------------------------------------------------------

    ImsiRange ::=
        OCTET STRING (SIZE (1..31))
        
    ----------------------------------------------------------------------------
    --
    --  MtAction defines how an SM that is being delivered to an MS should be
    --  blocked.
    --
    --  TextPass supports the following blocking actions:
    --
    --  1) Let SM pass
    --  2) Block SM by returning an error to the SMSC that causes the SMSC to
    --     consider the recipient as temporarily unavailable and will lead to
    --     another delivery attempt at a later time (blockWithTemporaryError).
    --  3) Block SM by returning an error to the SMSC that causes the SMSC to
    --     consider the SM as undeliverable and will not lead to any further
    --     delivery attempts for this SM (blockWithPermanentError).
    --  4) Block SM by not returning a response to the SMSC, which causes the
    --     SMSC to timeout
    --  5) Block SM and return a success response to the SMSC, which cases the
    --     SMSC to treat the SM as being delivered to the destination.
    --  6) Release an SM for further inspection by firewall.
    --
    ----------------------------------------------------------------------------


    MtAction ::=
        INTEGER {
            pass(0),
            blockWithTemporaryError(1),
            blockWithPermanentError(2),
            blockWithNoResponse(3),
            blockWithAck(4),
            release(5)
        }

    ----------------------------------------------------------------------------
    --
    --  MtCntRuleTableIndex defines the range for the index of the MT counting
    --  rule table.
    --
    ----------------------------------------------------------------------------

    MtCntRuleTableIndex ::=
        INTEGER(1..500)

    ----------------------------------------------------------------------------
    --
    --  MtExtCondRuleTableIndex defines the range for the index of the MT
    --  ExternalCondition rule table.
    --
    ----------------------------------------------------------------------------

    MtExtCondRuleTableIndex ::=
        INTEGER(1..500)

    ----------------------------------------------------------------------------
    --
    --  MtModifierTableIndex defines the range for the index of the MT modifier
    --  table.
    --
    ----------------------------------------------------------------------------

    MtModifierTableIndex ::=
        INTEGER(1..100)

    ----------------------------------------------------------------------------
    --
    --  MtModifierRef defines the reference to an MT modifier. Value 0 is
    --  used to clear a reference. Any other value refers to the index of a
    --  modifier in the MT modifier table.
    --
    ----------------------------------------------------------------------------

    MtModifierRef ::=
        Gauge(0..100)

    ----------------------------------------------------------------------------
    --
    --  MtRtgRuleTableIndex defines the range for the index of the MT routing
    --  rule table.
    --
    ----------------------------------------------------------------------------

    MtRtgRuleTableIndex ::=
        INTEGER(1..500)

    ----------------------------------------------------------------------------
    --
    --  MtTimer defines the limits for MT related timers.
    --
    ----------------------------------------------------------------------------

    MtTimer ::=
        Gauge(1..3600)

    ----------------------------------------------------------------------------
    --
    --  NcdrFormat defines the format version for Nokia CDRs.
    --
    ----------------------------------------------------------------------------

    NcdrFormat ::=
        INTEGER {
            sc5b(0),
            sc5b-cd1(1),
            sc5b-cd2(2),
            sc5b-cd3(3)
        }

    ----------------------------------------------------------------------------
    --
    --  NcdrRecordType defines the record types for Nokia CDRs.
    --
    ----------------------------------------------------------------------------

    NcdrRecordType ::=
        Gauge (0..255)

    ----------------------------------------------------------------------------
    --
    --  PreferredMtDestination defines the MT destination TextPass should select
    --  when the HLR provides both the MSC and SGSN as destination.
    --
    --  For details, refer to GSM 09.02.
    --
    ----------------------------------------------------------------------------

    PreferredMtDestination ::=

        INTEGER {
            msc(0),
            sgsn(1)
        }

    ----------------------------------------------------------------------------
    --
    --  RecipientSelector is used to select a recipient for a generated message.
    --
    ----------------------------------------------------------------------------

    RecipientSelector ::=
        INTEGER {
            originalOriginator(0),
            originalRecipient(1),
            chargedParty(2)
        }

    ----------------------------------------------------------------------------
    --
    --  RepublishSriSmNetworks is a string specifying up to 10 networks. Each 
    --  network should be specified as following:
    --
    --    a) the two-letter country code as defined in ISO 3166, followed by
    --    b) a dash (-), followed by
    --    c) the name of one of the mobile networks defined in mobNetworkTable.
    --
    --    When multiple networks are specified, the comma should be used as a
    --    seperator. 
    --
    --    An example of specification (assuming that a country 'nl' has been 
    --    defined with networks 'kpn' and 'vodafone') is:
    --      
    --      nl-kpn,nl-vodafone
    --
    ----------------------------------------------------------------------------
    
    RepublishSriSmNetworks ::= TEXTUAL-CONVENTION
        DISPLAY-HINT "349a"
        STATUS mandatory
        DESCRIPTION "String with networks fo which SRISM is to be republished"
        SYNTAX OCTET STRING (SIZE (0..349))

    ----------------------------------------------------------------------------
    --
    --  RoutingNumber specified a routing number, consisting of the hexadecimal
    --  digits 0-9 and a-f. Only lowercase characters are supported. The
    --  routing number is encoded in ASCII/UTF-8.
    --
    ----------------------------------------------------------------------------

    RoutingNumber ::= OCTET STRING (SIZE (1..8))

    ----------------------------------------------------------------------------
    --
    --  RoutingNumberGroupIndex defines the range for the index of the
    --  Routing Number Group Table.
    --
    ----------------------------------------------------------------------------

    RoutingNumberGroupIndex ::=
        INTEGER(1..100)

    ----------------------------------------------------------------------------
    --
    --  RoutingNumberGroupRef defines a reference to a routing number group.
    --  A value of 0 means that no group is referenced.
    --
    ----------------------------------------------------------------------------

    RoutingNumberGroupRef ::=
        INTEGER(0..100)

    ----------------------------------------------------------------------------
    --
    --  RoutingNumberIndex defines the range for the (second) index of the
    --  Routing Number Table.
    --
    ----------------------------------------------------------------------------

    RoutingNumberIndex ::=
        INTEGER(1..100)

    ----------------------------------------------------------------------------
    --
    --  Timeout for routing data cached in the Routing Data Proxy.
    --
    ----------------------------------------------------------------------------

    RdpTimeout ::=
        INTEGER(0..3600)

    ----------------------------------------------------------------------------
    --
    --  SmscGroupIndex defines the range for the index of the SMSC group table.
    --
    ----------------------------------------------------------------------------

    SmscGroupIndex ::=
        INTEGER(1..500)

    ----------------------------------------------------------------------------
    --
    --  SmscGroupMemberOperationalState reflects the operational state of a
    --  member of an SMSC group.
    --
    ----------------------------------------------------------------------------

    SmscGroupMemberOperationalState ::=
        INTEGER {
            adminDisabled(0),
            throughputExceeded(1),
            available(2)
        }

    ----------------------------------------------------------------------------
    --
    --  SmscGroupType defines the type of an SMSC and maps to exactly one SMSC
    --  table:
    --
    --  type    SMSC table
    --  ------------------
    --  ansi    ANSI SMSC table, see ANSI-MIB (added in the future)
    --  gsm     smscTable (possibly added in the future)
    --  ao      serviceCentreTable
    --
    ----------------------------------------------------------------------------

    SmscGroupType ::=
        INTEGER {
        ansi(0),
        --    gsm(1),
        ao(2)
        }

    ----------------------------------------------------------------------------
    --
    --  SmscOperationalState reflects the operational state of an SMSC.
    --
    ----------------------------------------------------------------------------

    SmscOperationalState ::=
        INTEGER {
            adminDisabled(0),
            unreachable(1),
            throughputExceeded(2),
            available(3)
        }

    ----------------------------------------------------------------------------
    --
    --  SmscTableIndex defines the range for the index of the SMSC table.
    --
    ----------------------------------------------------------------------------

    SmscTableIndex ::=
        INTEGER(1..500)

    ----------------------------------------------------------------------------
    --
    --  SpoofErrorAction defines the behaviour that should result when the 
    --  SendRoutingInfoForSM for an MO spoofing check fails with a call barred 
    --  error.
    --
    --  TextPass supports the following routing actions:
    --
    --  1) Treat as spoofing
    --  2) Check spoofing with MAP-ATI
    --  3) Consider the MO spoofing check as successful and let the SM pass.
    --
    ----------------------------------------------------------------------------

    SpoofErrorAction ::=
        INTEGER {
            treatAsIfSpoofing(125),
            checkWithMapAti(126),
            pass(127)
        }

    ----------------------------------------------------------------------------
    --
    --  MnpErrorAction defines the behaviour that should result when the 
    --  MNP violation check is inconclusive due to an earlier MO spoofing  
    --  check's inability to obtain the IMSI.
    --
    --  TextPass supports the following routing actions:
    --
    --  1) Treat as violation
    --  2) Consider the MNP check as successful and let the SM pass.
    --
    ----------------------------------------------------------------------------

    MnpErrorAction ::=
        INTEGER {
            treatAsIfMnpViolation(126),
            pass(127)
        }

    ----------------------------------------------------------------------------
    --
    --  StatusReportAction defines how a status report is to be routed to an MS
    --  or an application.
    --
    --  TextPass supports the following routing actions:
    --
    --   1) Delivery of status report to destination (route);
    --   2) Store in AMS for delivery to destination (store);
    --   8) Single shot delivery of status report to destination . On delivery 
    --      failure, store status report in AMS (routeFallbackToStorage)
    --
    ----------------------------------------------------------------------------

    StatusReportAction ::=
        INTEGER {
            route(0),
            store(1),
            routeFallbackToStorage(2)
        }

    ----------------------------------------------------------------------------
    --
    --  StatusReportRetryInterval defines the range for the retry interval for 
    --  status reports.
    --
    ----------------------------------------------------------------------------

    StatusReportRetryInterval ::= 
        Gauge(1..900)

    ----------------------------------------------------------------------------
    --
    --  TemplateString specifies a template that is used for formatting a (part
    --  of an) SM.
    --
    ----------------------------------------------------------------------------

    TemplateString ::= TEXTUAL-CONVENTION
        DISPLAY-HINT "160a"
        STATUS mandatory
        DESCRIPTION "SMPP system ID"
        SYNTAX OCTET STRING (SIZE (1..160))

    ----------------------------------------------------------------------------
    --
    --  TestAccessTimer defines the duration of the interval, expressed in units
    --  of seconds, at which test messages are sent to the SMSC to verify if it
    --  is accessible.
    --
    ----------------------------------------------------------------------------

    TestAccessTimer ::=
        Gauge(0..3600)

    ----------------------------------------------------------------------------
    --
    --  TimeZone specifies the timezone to be used. For the specification, an
    --  operator can specify the name of any timezone information file that is
    --  available on the system. On a standard Solaris system, the following
    --  timezone information files are available:
    --
    --    CET, CST6CDT, Cuba, EET, EST, EST5EDT, Egypt, Eire, Factory, GB,
    --    GB-Eire, GMT, GMT+0, GMT+1, GMT+10, GMT+11, GMT+12, GMT+13, GMT+2,
    --    GMT+3, GMT+4, GMT+5, GMT+6, GMT+7, GMT+8, GMT+9, GMT-0, GMT-1,
    --    GMT-10, GMT-11, GMT-12, GMT-2, GMT-3, GMT-4, GMT-5, GMT-6, GMT-7,
    --    GMT-8, GMT-9, Greenwich, HST, Hongkong, Iceland, Iran, Israel,
    --    Jamaica, Japan, Kwajalein, Libya, MET, MST, MST7MDT, NZ, NZ-CHAT,
    --    Navajo, PRC, PST8PDT, Poland, Portugal, ROC, ROK, Singapore,
    --    Turkey, UCT, UTC, Universal, W-SU, WET, Zulu, Asia/Taipei,
    --    Australia/ACT, Australia/Broken_Hill, Australia/LHI, Australia/NSW,
    --    Australia/North, Australia/Queensland, Australia/South,
    --    Australia/Tasmania, Australia/Victoria, Australia/West,
    --    Australia/Yancowinna, Brazil/Acre, Brazil/DeNoronha, Brazil/East,
    --    Brazil/West, Canada/Atlantic, Canada/Central,
    --    Canada/East-Saskatchewan, Canada/Eastern, Canada/Mountain,
    --    Canada/Newfoundland, Canada/Pacific, Canada/Yukon,
    --    Chile/Continental, Chile/EasterIsland, Mexico/BajaNorte,
    --    Mexico/BajaSur, Mexico/General, Mideast/Riyadh87, Mideast/Riyadh88,
    --    Mideast/Riyadh89, US/Alaska, US/Aleutian, US/Arizona, US/Central,
    --    US/East-Indiana, US/Eastern, US/Hawaii, US/Michigan, US/Mountain,
    --    US/Pacific, US/Pacific-New, US/Samoa
    --
    ----------------------------------------------------------------------------

    TimeZone ::=
        OCTET STRING (SIZE (0..80))

    ----------------------------------------------------------------------------
    --
    --  TranslationType defines the SCCP GT Translation Type.
    --
    ----------------------------------------------------------------------------

    TranslationType ::=
        Gauge(0..255)

    ----------------------------------------------------------------------------
    --
    --  TransparentForwarding defines if MO messages should be forwarded
    --  transparently or not.
    --
    ----------------------------------------------------------------------------

    TransparentForwarding ::=
        INTEGER {
            useGlobalSetting(0), -- smsPropOptimisedMoRouting
            true(1),
            false(2)
        }

    ----------------------------------------------------------------------------
    --
    --  UcpRetErrCode defines the error range which can be returned in error
    --  message.
    --
    ----------------------------------------------------------------------------

    UcpRetErrCode ::=
        Gauge(0..99)

    ----------------------------------------------------------------------------
    --
    --  UserDataLength defines all legitimate values (0-160) for 7-bit encoded
    --  user data.
    --
    ----------------------------------------------------------------------------

    UserDataLength ::=
        Gauge(0..160)

    ----------------------------------------------------------------------------
    --
    --  UssdString defines a string that is used in a USSD request or response.
    --
    ----------------------------------------------------------------------------

    UssdString ::= 
        OCTET STRING (SIZE (0..93))

    ----------------------------------------------------------------------------
    --                              O B J E C T S                             --
    ----------------------------------------------------------------------------

    sms OBJECT IDENTIFIER ::= { textpass 31 }

    smsProperties OBJECT IDENTIFIER ::= { sms 1 }

    smsPropPreferredMtDestination OBJECT-TYPE
        SYNTAX  PreferredMtDestination
        ACCESS  read-write
        STATUS  mandatory
        DESCRIPTION
            "The preferred destination for MT/SM's. Only applicable for MAP
            phase 2+. Up until MAP phase 2, the only possible destination of
            an MT/SM is an MSC. In MAP phase 2+, an MT/SM can be sent to an
            SGSN as well. In case an (phase 2+) HLR returns both an MSC and
            an SGSN as possible destinations for an MT/SM, TextPass will try
            to deliver the SM through the preferred destination. When the
            attempt to the preferred destination fails, TextPass might retry
            to deliver the MT/SM through the non-preferred destination.
            Whether TextPass does the retry is not configurable, but
            dependent on the type of delivery failure that the preferred
            destination reports.
            Default is 'msc'."
        ::= { smsProperties 1 }

    smsPropOptimisedMoRouting OBJECT-TYPE
        SYNTAX  Boolean
        ACCESS  read-write
        STATUS  mandatory
        DESCRIPTION
            "When routing an MO/SM toward an SMSC, TextPass can route in the
            conventional way, which implies setting up a new TCAP dialogue
            towards the SMSC, or it can route in an optimal way, which
            comprises relaying the TCAP dialogue from the MSC to the SMSC.

            When routing the convential way, the flow of TCAP messages is as
            following:

            MSC                         TextPass                         SMSC
                ------ TC-BEGIN ------>
                                                 ------ TC-BEGIN ------>
                                                 <------  TC-END  ------
                <------  TC-END  ------

            When routing the optimal way, the flow of TCAP messages is as
            following:

            MSC                         TextPass                         SMSC
                ------ TC-BEGIN ------>
                                                 ------ TC-BEGIN ------>
                <----------------------  TC-END  -----------------------


            By default, TextPass routes in the convential way. This OID
            should be set to true to encorce optimal routing.

            Note that, as an option, optimised MO routing can be disabled for
            MO/SM issed from abroad. For this purpose, the
            smsPropDisableOptimisedMoRoutingForForeignTraffic is available.
            "
        ::= { smsProperties 2 }

    smsPropOptimisedMtDelivery OBJECT-TYPE
        SYNTAX  Boolean
        ACCESS  read-write
        STATUS  mandatory
        DESCRIPTION
            "Flag indicating whether or not HLR indications (AbsentSubscriber
            / MemoryCapacityExceeded) should be considered when performing a
            MT delivery attempt as result of a rule with an action
            routeToMsFallbackToSmsc. Default is true."
        ::= { smsProperties 3 }

    smsPropEnableMapPhaseOptimisation OBJECT-TYPE
        SYNTAX  Boolean
        ACCESS  read-write
        STATUS  mandatory
        DESCRIPTION
            "Flag indicating whether TextPass should use MAP phase 1 when
            this possible. Goal of using MAP phase 1 transactions is to
            reduce the signalling capacity that is required for a MAP
            operation. By doing this, the number of possible MAP operations
            on a link per unit of time increases. Default is true."
        ::= { smsProperties 4 }


    smsPropEnableHlrUpdates OBJECT-TYPE
        SYNTAX  Boolean
        ACCESS  read-write
        STATUS  mandatory
        DESCRIPTION
            "Flag indicating whether TextPass should update the HLR flags.
            Default is true."
        ::= { smsProperties 5 }

    smsPropCommonAddress OBJECT-TYPE
        SYNTAX  E164Address
        ACCESS  read-write
        STATUS  mandatory
        DESCRIPTION
            "E164 address that the TextPass should use for the SMSC parameter
            in MAP operations pertaining to delivery of an MT/SM. When this
            address is not configured, TextPass uses the E164 address that is
            defined for its GT. Note that smsPropSmscAddressForHlrOperations
            may overrule for MAP operations to HLR."
        ::= { smsProperties 6 }

    smsPropMoResponseAfterHlrQuery OBJECT-TYPE
        SYNTAX  Boolean
        ACCESS  read-write
        STATUS  mandatory
        DESCRIPTION
            "Flag indicating whether TextPass should send a response to an
            MO/SM after it has completed the HLR query to obtain details of
            the recipient. The response depends on the HLR query result. If
            the HLR query resulted in an error of permanent nature, the
            response to the MO/SM is a NAK. When the HLR query is successful
            or the HLR query failed due to a temporary error, the MO/SM
            response is an ACK. A typical case in which this setting is
            activated is for operators requiring that MO/SM's to unknown
            recipients are rejected. Default of this setting is false."
        ::= { smsProperties 7 }

    smsPropDisableOptimisedMoRoutingForForeignTraffic OBJECT-TYPE
        SYNTAX  Boolean
        ACCESS  read-write
        STATUS  mandatory
        DESCRIPTION
            "When routing MO/SM to an SMSC is enabled, it can either be done
            for all MO/SM's or only for MO/SM's originated through MSC's of
            the own country. This flag determines this behaviour. When set to
            'false', all MO/SM's are passed to the SMSC with optimised
            routing. When set to 'true', optimised routing pertains to
            MO/SM's originated through MSC's of the own country only. MO/SM's
            originated through foreign MSC's are routed using the
            conventional way. Default of this flags is 'false'."
        ::= { smsProperties 8 }

    smsPropConsiderNationalNonHplmnTrafficAsForeign OBJECT-TYPE
        SYNTAX  Boolean
        ACCESS  read-write
        STATUS  mandatory
        DESCRIPTION
            "Indicator specifying how to interpret the term 'foreign'. When
            set to 'true' any PLMN other than the HPLMN is considered as
            foreign.  When set to 'false', foreign refers to the country. As
            such, foreign then exludes any PLMN of the home country. Default
            of this flag is 'false'."
        ::= { smsProperties 9 }

    smsPropEnableAlertScRelaying OBJECT-TYPE
        SYNTAX  Boolean
        ACCESS  read-write
        STATUS  mandatory
        DESCRIPTION
            "Indicator specifying whether the feature to relay an AlertSC
            should be enabled or disabled. When this flag is 'true', TextPass
            will relay any AlertSC that it receives back to the network. This
            feature requires that a GTT rule matches for the SMSC address as
            specified on the MAP layer of the AlertSC. If this is the case,
            the AlertSC will be relayed to address resulting from the GTT
            rule. TextPass will terminate the AlertSC if no GTT rule matches
            (or when this feature is disabled).
            Default of this this flag is 'true'."
        ::= { smsProperties 10 }

    -- OIDs 11 to 14 have moved to genProperties (GEN MIB)

    smsPropX121CountryCode OBJECT-TYPE
        SYNTAX  X121Address
        ACCESS  read-write
        STATUS  mandatory
        DESCRIPTION
            "X121 country code for country in which TextPass operates.
            Defailt is 204"
        ::= { smsProperties 15 }

    smsPropX121NationalPrefix OBJECT-TYPE
        SYNTAX  X121Address
        ACCESS  read-write
        STATUS  mandatory
        DESCRIPTION
            "X121 national (prefix as used in country in which TextPass
            operates.

            Typically equal to 0, which is also the default."
        ::= { smsProperties 16 }

    smsPropAreaCodeLength OBJECT-TYPE
        SYNTAX  AreaCodeLength
        ACCESS  read-write
        STATUS  mandatory
        DESCRIPTION
            "Number of digits for area code as used in country in which
            TextPass operates. In some countries, the area code has a
            variable length.  If this is the case, this object should be set
            to 0 and the area codes should be provisioned using the
            areaCodeTable.
             
            Note that this object cannot be set to a non-zero value when the
            areaCodeTable has been filled.
             
            Default is 0."
        ::= { smsProperties 17 }

    smsPropSmscAddressForHlrOperations OBJECT-TYPE
        SYNTAX  E164Address
        ACCESS  read-write
        STATUS  mandatory
        DESCRIPTION
            "E164 address that the TextPass should use for the SMSC parameter
            in MAP operations to HLR. When this address is not configured, 
            TextPass uses the E164 address that is defined for 
            smsPropCommonAddress. When smsPropCommonAddress has not been 
            configured either, TextPass uses its GT. Both may be superceded
            by the mtModifierSmscAddressForSrism and 
            mtModifierSmscAddressForReportStatus MT modifiers."
        ::= { smsProperties 18 }
        
    smsPropMatchMoRoutingRulesForDestinationApplication OBJECT-TYPE
        SYNTAX  Boolean
        ACCESS  read-write
        STATUS  mandatory
        DESCRIPTION
            "When enabled, this parameter causes the router to match the MO
            routing rules before evaluating the MO external condition rules
            with the sole purpose of determining the destination application
            in case of MO-AT routing, and with the exception of the MO-MT-AT
            path. By default, this parameter is set to 'false'. Turning it on
            will consume extra processing power."
        ::= { smsProperties 19 }

    smsPropMobileCountryCode OBJECT-TYPE
        SYNTAX  MobileCountryCode
        ACCESS  read-write
        STATUS  mandatory
        DESCRIPTION
            "Mobile country code of mobile network in which TextPass operates.
             Default is 204."
        ::= { smsProperties 21 }

    smsPropMobileNetworkCode OBJECT-TYPE
        SYNTAX  MobileNetworkCode
        ACCESS  read-write
        STATUS  mandatory
        DESCRIPTION
            "Mobile network code of mobile network in which TextPass operates.
             Default is 12."
        ::= { smsProperties 22 }

    smsPropGsmMoDiscardError OBJECT-TYPE
        SYNTAX  GsmError
        ACCESS  read-write
        STATUS  mandatory
        DESCRIPTION
            "Error that TextPass uses to discard an MO/SM. TextPass discards
            an MO/SM if:
            1) an MO routing rule specifies discarding the SM as its action,
               or
            2) none of the MO routing rule matches an MO/SM, or
            3) none of the matching MO routing rules can be applied (due to,
               for instance, throughput regulation or blocking by an MT
               routing rule).
            Default is 'systemFailure'."
        ::= { smsProperties 31 }

    smsPropGsmMtPermDiscardErrorForMscOrSgsn OBJECT-TYPE
        SYNTAX  GsmError
        ACCESS  read-write
        STATUS  mandatory
        DESCRIPTION
            "Error that TextPass uses to discard an MT/SM permanently at the
            stage that the SMSC issues a MAP-MtForwardSm towards the MSC or
            the SGSN. TextPass uses this error when an MT routing rule
            applies that has an action specified which blocks an MT/SM with a
            permanent error. Note that this error is specific for the case
            that the MT/SM is issued by an SMSC.            
            Default is 'unknownSubscriber'."
        ::= { smsProperties 32 }

    smsPropGsmMtPermDiscardErrorForHlr OBJECT-TYPE
        SYNTAX  GsmError
        ACCESS  read-write
        STATUS  mandatory
        DESCRIPTION
            "Error that TextPass uses to discard an MT/SM permanently at the
            stage that the SMSC issues a MAP-SendRoutingInfoForSm towards the
            HLR. TextPass uses this error when an MT routing rule applies
            that has an action specified which blocks an MT/SM with a
            permanent error. Note that this error is specific for the case
            that the MT/SM is issued by an SMSC.            
            Default is 'unknownSubscriber'."
        ::= { smsProperties 33 }

    smsPropGsmMtTempDiscardErrorForMscOrSgsn OBJECT-TYPE
        SYNTAX  GsmError
        ACCESS  read-write
        STATUS  mandatory
        DESCRIPTION
            "Error that TextPass returns to discard an MT/SM temporarily at
            the stage that the SMSC issues a MAP-MtForwardSm towards the MSC
            or the SGSN. TextPass uses this error when an MT routing rule
            applies that has an action specified which blocks an MT/SM with a
            temporary error. Note that this error is specific for the case
            that the MT/SM is issued by an SMSC.            
            Default is 'absentSubscriber'."
        ::= { smsProperties 34 }

    smsPropGsmMtTempDiscardErrorForHlr OBJECT-TYPE
        SYNTAX  GsmError
        ACCESS  read-write
        STATUS  mandatory
        DESCRIPTION
            "Error that TextPass returns to discard an MT/SM temporarily at
            the stage that the SMSC issues a MAP-SendRoutingInfoForSm towards
            the HLR. TextPass uses this error when an MT routing rule applies
            that has an action specified which blocks an MT/SM with a
            temporary error. Note that this error is specific for the case
            that the MT/SM is issued by an SMSC.            
            Default is 'absentSubscriber'."
        ::= { smsProperties 35 }

    smsPropIgnorePermanentFailureOfHlrQueryForRecipient OBJECT-TYPE
        SYNTAX  Boolean
        ACCESS  read-write
        STATUS  mandatory
        DESCRIPTION
            "When this flag is set to 'true', TextPass ignores permanent
            errors for the HLR query of the recipient of a message, if
            the HLR query is executed before the process of matching the
            MO rules (smsPropHlrQueryForRecipientBeforeApproval).

            To prevent MT-delivery retries for messages with a permanent
            HLR query error, the MO rules should be configured such, that
            no message with a permanent HLR query error is routed to a
            fallback to MT. Typically, such messages should be routed to an
            application or be rejected.

            By default, this flag is set to 'false'."
        ::= { smsProperties 37 }

    smsPropIncludeMscAddrInMoFwdSmToSmsc OBJECT-TYPE
        SYNTAX  IncludeMscAddrIndicator
        ACCESS  read-write
        STATUS  mandatory
        DESCRIPTION
            "Indicator specifying when MSC address should be included in SCCP
            calling party address of MO Forward SM operation towards SMSC.
            The indicator specifies that the MSC address should
            (1) never be included (the default),
            (2) always be included, or
            (3) only be included in case the MSC is located in another
                country."
        ::= { smsProperties 41 }

    smsPropTtWhenIncludingMscAddrInMoFwdSmToSmsc OBJECT-TYPE
        SYNTAX  TranslationType
        ACCESS  read-write
        STATUS  mandatory
        DESCRIPTION
            "Value for Translation Type when MSC address is included in SCCP
            calling party address of MO Forward SM operation towards SMSC.
            The default for ITU-T is 0, whilst 10 is used as a default for 
            ANSI."
        ::= { smsProperties 42 }

    smsPropPcSsnRoutingWhenIncludingMscAddrInMoFwdSmToSmsc OBJECT-TYPE
        SYNTAX  Boolean
        ACCESS  read-write
        STATUS  mandatory
        DESCRIPTION
            "Indicator specifying whether the SCCP calling party address's 
            routing indicator should should be set to PC/SSN when the MSC 
            address is included in SCCP calling party address of MO Forward SM 
            operation towards SMSC.
            The default is 'false'."
        ::= { smsProperties 43 }

    smsPropSmscAoIcacheSupport OBJECT-TYPE
        SYNTAX  IcacheSupport
        ACCESS  read-write
        STATUS  mandatory
        DESCRIPTION
            "Support storing of billing data in an Icache store. Used where
            AO forwarding to an SMSC, to correlate SMSC delivery
            confirmations and generate CDRs. If this set to other than
            noIcacheSupport, then smsPropSmscAoAmsQueue must be configured.
            By default, this parameter is set to noIcacheSupport."
        ::= { smsProperties 44 }

    smsPropSmscMoIcacheSupport OBJECT-TYPE
        SYNTAX  IcacheSupport
        ACCESS  read-write
        STATUS  mandatory
        DESCRIPTION
            "Support storing of billing data in an Icache store. Used where
            MO forwarding to an SMSC, to correlate SMSC delivery
            confirmations and generate CDRs. If this set to other than
            noIcacheSupport, then smsPropSmscMoAmsQueue must be configured.
            By default, this parameter is set to noIcacheSupport."
        ::= { smsProperties 45 }

    smsPropSmscAoAmsQueue OBJECT-TYPE
        SYNTAX  AmsQueueIndex
        ACCESS  read-write
        STATUS  mandatory
        DESCRIPTION
            "Queue in AMS for AO messages for Icache store of billing data."
        ::= { smsProperties 46 }

    smsPropSmscMoAmsQueue OBJECT-TYPE
        SYNTAX  AmsQueueIndex
        ACCESS  read-write
        STATUS  mandatory
        DESCRIPTION
            "Queue in AMS for MO messages for Icache store of billing data."
        ::= { smsProperties 47 }

    smsPropUseMapAddressForMoCdpa OBJECT-TYPE
        SYNTAX  Boolean
        ACCESS  read-write
        STATUS  mandatory
        DESCRIPTION
            "When set to true, the SCCP called party address of MO Forward SM
            messages towards the SMSC is taken from the MAP layer SMSC address
            rather than from the configured SCCP address of the selected SMSC 
            table entry. By default, this object is set to FALSE."
        ::= { smsProperties 51 }

    smsPropMessageKeyWeightsForMsisdnDestination OBJECT-TYPE
        SYNTAX  MessageKeyWeights
        ACCESS  read-write
        STATUS  mandatory
        DESCRIPTION
            "Specifies the weights for computing a key for a message, the
            destination of which is an MSISDN. The key can be used for e.g.
            the load distribution algorithm. See the description of the
            MessageKeyWeights for more information on the format and meaning
            of the weights. By default, the weights are set to
            ':1000,100,10,1', which means that only the destination number
            is taken into account."
        ::= { smsProperties 52 }

    smsPropMessageKeyWeightsForShortNumberDestination OBJECT-TYPE
        SYNTAX  MessageKeyWeights
        ACCESS  read-write
        STATUS  mandatory
        DESCRIPTION
            "Specifies the weights for computing a key for a message, the
            destination of which is a short number. The key can be used for
            e.g. the load distribution algorithm. See the description of the
            MessageKeyWeights for more information on the format and meaning
            of the weights. By default, the weights are set to
            '1000,100,10,1:', which means that only the originator number
            is taken into account."
        ::= { smsProperties 53 }

    smsPropMscAddressInCamelTriggerForAoSm OBJECT-TYPE
        SYNTAX  E164Address
        ACCESS  read-write
        STATUS  mandatory
        DESCRIPTION
            "E164 address that the TextPass should use for the MSC parameter
            in CAMEL operations that are issued for AO/SM-s. When this
            address is not configured, TextPass uses the E164 address that is
            defined for its GT."
        ::= { smsProperties 54 }

    smsPropSmscAddressInCamelTriggerForAoSm OBJECT-TYPE
        SYNTAX  E164Address
        ACCESS  read-write
        STATUS  mandatory
        DESCRIPTION
            "E164 address that the TextPass should use for the SMSC parameter
            in CAMEL operations that are issued for AO/SM-s. When this
            address is not configured, TextPass uses the E164 address as set
            for smsPropCommonAddress."
        ::= { smsProperties 55 }

    smsPropServiceKeyInCamelTrigger OBJECT-TYPE
        SYNTAX  Gauge
        ACCESS  read-write
        STATUS  mandatory
        DESCRIPTION
            "Value that the TextPass should use for the Service Key parameter
            in CAMEL operations that are issued when an ECI application
            (e.g. PBC) does not provide a Service Key. When this 
            object is not configured, the value defaults to 0."
        ::= { smsProperties 56 }
        
    smsPropCapPhaseForCamelTrigger OBJECT-TYPE
        SYNTAX  CapPhase
        ACCESS  read-write
        STATUS  mandatory
        DESCRIPTION
            "Default for CAP phase that the TextPass is to use for CAMEL 
            trigger. This CAP phase is only used when an ECI application
            (e.g. PBC) does not specify a Charging Protocol. When this
            parameter is not configured, its value defaults to 'cap3'."
        ::= { smsProperties 57 }
        
    smsPropExpectChargingInfoForCamelTrigger OBJECT-TYPE
        SYNTAX  Boolean
        ACCESS  read-write
        STATUS  mandatory
        DESCRIPTION
            "Indicator specifying whether TextPass should expect a 
            FurnishChargingInformation operation from the SCF for CAMEL 
            trigger issued. This indicator is only used ECI 
            application (e.g. PBC) does not specify a Return Tariff Data 
            indicator. When this parameter is not configured, its value 
            defaults to 'false'."
        ::= { smsProperties 58 }
        
    smsPropBlockIfScfNotReachableForCamelTrigger OBJECT-TYPE
        SYNTAX  Boolean
        ACCESS  read-write
        STATUS  mandatory
        DESCRIPTION
            "Indicator specifying whether TextPass should consider a CAMEL 
            trigger as failed when a communications error with SCF occurs.
            This indicator is only used when ECI application (e.g. PBC)
            does not specify a Default SMS Handling indicator. When this 
            parameter is not configured, its value defaults to 'false'."
        ::= { smsProperties 59 }
        
    smsPropAllowMoFromFriendlySubscribersOnly OBJECT-TYPE
        SYNTAX  Boolean
        ACCESS  read-write
        STATUS  mandatory
        DESCRIPTION
            "Indicator specifying whether the TPR should only allow MO/SM's
            from 'friendly' subscribers (own and associated networks) and
            should reject MO/SM's from other operators' subscribers.
            Default is 'false'."
        ::= { smsProperties 61 }

    smsPropAlternativeScSelectionForAoSmWithDnEnabled OBJECT-TYPE
        SYNTAX  Boolean
        ACCESS  read-write
        STATUS  mandatory
        DESCRIPTION
            "Indicator specifying whether RTR should use an alternative 
            service centre selection scheme for an AO/SM with a request 
            for an notification that needs to be delivered on a dialout 
            session. Default is 'false'."
        ::= { smsProperties 60 }

    smsPropSmscHaveNumberPortabilityCheck OBJECT-TYPE
        SYNTAX  Boolean
        ACCESS  read-write
        STATUS  mandatory
        DESCRIPTION
            "Indicator specifying whether the SMSC's have a number
            portability check. If this is the case, the TPR never checks the
            originator when incoming MO/SM are routed to an SMSC. If the
            SMSC's do not have a number portability check, the TPR will do
            such a check (providing that
            smsPropAllowMoFromFriendlySubscribersOnly is set to 'true').
            Default is 'false'."
        ::= { smsProperties 62 }

    smsPropNationalRoamingEnabled OBJECT-TYPE
        SYNTAX  Boolean
        ACCESS  read-write
        STATUS  mandatory
        DESCRIPTION
            "Indicator specifying whether the operator's network is used by
            other other operators of the same network. If this is not the
            case, the TPR can optimise its checks to determine whether
            incoming MO/SM are from the operator's own subscriber. Default is
            'false'."
        ::= { smsProperties 63 }

    smsPropNumberPortabilityEnabled OBJECT-TYPE
        SYNTAX  Boolean
        ACCESS  read-write
        STATUS  mandatory
        DESCRIPTION
            "Indicator specifying whether number portability within the
            operator's country is implemented. Default is 'false'."
        ::= { smsProperties 64 }

    smsPropLowestMapPhaseToSupportImsiInMoFwdSm OBJECT-TYPE
        SYNTAX  MapPhase
        ACCESS  read-write
        STATUS  mandatory
        DESCRIPTION
            "Lowest MAP phase for which the SMSC's support passing on the
            IMSI in an MoForwardSm operation. Default is 'phase2plus'."
        ::= { smsProperties 65 }

    smsPropAlwaysRetrieveOriginatorImsi OBJECT-TYPE
        SYNTAX  Boolean
        ACCESS  read-write
        STATUS  mandatory
        DESCRIPTION
            "Indicator specifying whether originator IMSI should be retrieved
            in any case. This indicator should be set to 'true' when
            originator IMSI is used for matching of MO rules. It causes the
            rule to be determined after the IMSI has been retrieved.
            Default of this setting is  'false'."
        ::= { smsProperties 66 }

    smsPropTtUsedForOriginatorImsiRetrieval OBJECT-TYPE
        SYNTAX  TranslationType
        ACCESS  read-write
        STATUS  mandatory
        DESCRIPTION
            "Translation Type (TT) value to be used in SCCP Called Party
            Address of the SendRoutingInfoForSm operation that retrieves the
            originator IMSI. The default for ITU-T is 0, whilst 14 is used as
            a default for ANSI."        
        ::= { smsProperties 67 }

    smsPropActionForMnpCheckFailureDueToCallBarred OBJECT-TYPE
        SYNTAX  MnpErrorAction
        ACCESS  read-write
        STATUS  mandatory
        DESCRIPTION
            "Action to be executed when MNP check fails due to earlier call 
            barred error. Default action is 'treatAsIfMnpViolation'."
        ::= { smsProperties 68 }

    smsPropActionForMnpCheckFailureDueToTsvcNotProv OBJECT-TYPE
        SYNTAX  MnpErrorAction
        ACCESS  read-write
        STATUS  mandatory
        DESCRIPTION
            "Action to be executed when MNP check fails due to earlier 
            teleservice not provisioned error. Default action is 
            'treatAsIfMnpViolation'."
        ::= { smsProperties 69 }

	smsPropForceStatusReportForDroppedMoMessage OBJECT-TYPE
        SYNTAX  Boolean
        ACCESS  read-write
        STATUS  mandatory
        DESCRIPTION
            "Indicator specifying whether a status report will be sent when a
             message is dropped"
        ::= { smsProperties 70 }

    smsPropStatusReportEnabled OBJECT-TYPE
        SYNTAX  Boolean
        ACCESS  read-write
        STATUS  mandatory
        DESCRIPTION
            "Indicator specifying whether GSM status reports should be
            enabled.
            Default is 'false'."
        ::= { smsProperties 71 }

    smsPropPhase1StatusReportOverrules OBJECT-TYPE
        SYNTAX  Boolean
        ACCESS  read-write
        STATUS  mandatory
        DESCRIPTION
            "Indicator specifying which status report overrules when both a
            phase 1 status report and a phase 2/2+ status report is being
            requested for an MO/SM. A phase 1 status report is requested by
            preceding the text message with a specific tag, whilst a phase
            2/2+ status report is requested by means of the TP-SRR bit in the
            SMS-SUBMIT PDU. A phase 1 status report consists of a text
            message that is conveyed to the MS using a SMS-DELIVER PDU. A
            phase 2/2+ status report is implemented by the STATUS-REPORT PDU.
            When no value is provisioned for this setting, it defaults to
            'false'."
        ::= { smsProperties 72 }

    smsPropSctsTemplateForPhase1StatusReport OBJECT-TYPE
        SYNTAX  TemplateString
        ACCESS  read-write
        STATUS  mandatory
        DESCRIPTION
            "String specifying the format for the Service Centre Timestamp
            that is put in a phase 1 status report. The Service Centre
            Timestamp is assigned when a SM is submitted to the TextPass
            Router.
            The following format specifiers are supported:
            %y - year specified in two digits (e.g. 04)
            %m - month specified in two digits (e.g. 01 for Jan, 10 for Oct)
            %d - day specified in two digits (e.g 01 for 1st day of month,
                 31 for last day of month)
            %H - hour specified in two digits (e.g 00 for midnight, 12 for
                 noon)
            %M - minute specified in two digits
            %S - second specified in two digits
            Default is: %d.%m.%y %H:%M:%S"
        ::= { smsProperties 73 }


    smsPropDtTemplateForPhase1StatusReport OBJECT-TYPE
        SYNTAX  TemplateString
        ACCESS  read-write
        STATUS  mandatory
        DESCRIPTION
            "String specifying the format for the Discharge Time that is put
            in a phase 1 status report. The Discharge Time is the timestamp
            of delivery to the recipient of the SM.
            The following format specifiers are supported:
            %y - year specified in two digits (e.g. 04)
            %m - month specified in two digits (e.g. 01 for Jan, 10 for Oct)
            %d - day specified in two digits (e.g 01 for 1st day of month,
                 31 for last day of month)
            %H - hour specified in two digits (e.g 00 for midnight, 12 for
                 noon)
            %M - minute specified in two digits
            %S - second specified in two digits
            Default is: %d.%m.%y %H:%M:%S"
        ::= { smsProperties 74 }

    smsPropSucceededPhase1StatusReportTemplate OBJECT-TYPE
        SYNTAX  TemplateString
        ACCESS  read-write
        STATUS  mandatory
        DESCRIPTION
            "String specifying the format of a phase 1 status report that is
            sent to the originator of an SM that is successfully delivered to
            the recipient of the SM.
            The following format specifiers are supported:
            $(SCTS) - Service Centre Timestamp formatted as specified
            with smsPropSctsFormatOfPhase1StatusReport object
            $(DISCHARGE_TIME) - Discharge Time formatted as specified with
            smsPropDtFormatOfPhase1StatusReport object
            $(DESTINATION) - Address of recipient of SM.
            Default is: **STATUS** Delivered. Message to $(DESTINATION) sent
            at $(SCTS)"
        ::= { smsProperties 75 }

    smsPropFailedPhase1StatusReportTemplate OBJECT-TYPE
        SYNTAX  TemplateString
        ACCESS  read-write
        STATUS  mandatory
        DESCRIPTION
            "String specifying the format of a phase 1 status report that is
            sent to the originator of an SM that could not be delivered to
            the recipient of the SM.
            The following format specifiers are supported:
            $(SCTS) - Service Centre Timestamp formatted as specified
            with smsPropSctsFormatOfPhase1StatusReport object
            $(DISCHARGE_TIME) - Discharge Time formatted as specified with
            smsPropDtFormatOfPhase1StatusReport object
            $(DESTINATION) - Address of recipient of SM.
            $(ERROR) - Error string formatted as specified by one of the 
            smsPropXxxxxErrorStringOfPhase1StatusReport objects - which object
            is used is depending on the delivery error.
            Default is: **STATUS** Failed. Message to $(DESTINATION) sent
            at $(SCTS)"
        ::= { smsProperties 76 }

    smsPropDiscardedPhase1StatusReportTemplate OBJECT-TYPE
        SYNTAX  TemplateString
        ACCESS  read-write
        STATUS  mandatory
        DESCRIPTION
            "String specifying the format of a phase 1 status report that is
            sent to the originator of an SM that has been discarded before it
            could be delivered to the recipient of the SM.
            The following format specifiers are supported:
            $(SCTS) - Service Centre Timestamp formatted as specified
            with smsPropSctsFormatOfPhase1StatusReport object
            $(DISCHARGE_TIME) - Discharge Time formatted as specified with
            smsPropDtFormatOfPhase1StatusReport object
            $(DESTINATION) - Address of recipient of SM.
            $(ERROR) - Error string formatted as specified by one of the 
            smsPropXxxxxErrorStringOfPhase1StatusReport objects - which object
            is used is depending on the delivery error.
            Default is: **STATUS** Discarded. Message to $(DESTINATION) sent
            at $(SCTS)"
        ::= { smsProperties 77 }

    smsPropExpiredPhase1StatusReportTemplate OBJECT-TYPE
        SYNTAX  TemplateString
        ACCESS  read-write
        STATUS  mandatory
        DESCRIPTION
            "String specifying the format of a phase 1 status report that is
            sent to the originator of an SM that has expired before it could
            be delivered to the recipient of the SM.
            The following format specifiers are supported:
            $(SCTS) - Service Centre Timestamp formatted as specified
            with smsPropSctsFormatOfPhase1StatusReport object
            $(DISCHARGE_TIME) - Discharge Time formatted as specified with
            smsPropDtFormatOfPhase1StatusReport object
            $(DESTINATION) - Address of recipient of SM.
            Default is: **STATUS** Expired. Message to $(DESTINATION) sent
            at $(SCTS)"
        ::= { smsProperties 78 }

    smsPropDeletedPhase1StatusReportTemplate OBJECT-TYPE
        SYNTAX  TemplateString
        ACCESS  read-write
        STATUS  mandatory
        DESCRIPTION
            "String specifying the format of a phase 1 status report that is
            sent to the originator of an SM that has been deleted before it
            could be delivered to the recipient of the SM.
            The following format specifiers are supported:
            $(SCTS) - Service Centre Timestamp formatted as specified
            with smsPropSctsFormatOfPhase1StatusReport object
            $(DISCHARGE_TIME) - Discharge Time formatted as specified with
            smsPropDtFormatOfPhase1StatusReport object
            $(DESTINATION) - Address of recipient of SM.
            Default is: **STATUS** Deleted. Message to $(DESTINATION) sent
            at $(SCTS)"
        ::= { smsProperties 79 }

    smsPropBufferedPhase1StatusReportTemplate OBJECT-TYPE
        SYNTAX  TemplateString
        ACCESS  read-write
        STATUS  mandatory
        DESCRIPTION
            "String specifying the format of a phase 1 status report 
            that is sent to the originator of an SM that has been 
            buffered for delivery at a later point in time.
            The following format specifiers are supported:
            $(SCTS) - Service Centre Timestamp formatted as specified
            with smsPropSctsFormatOfPhase1StatusReport object
            $(DISCHARGE_TIME) - Discharge Time formatted as specified with
            smsPropDtFormatOfPhase1StatusReport object
            $(DESTINATION) - Address of recipient of SM.
            Default is: **STATUS** Buffered. Message to $(DESTINATION) sent
            at $(SCTS)"
        ::= { smsProperties 80 }

    smsPropFormatAtOriginator OBJECT-TYPE
        SYNTAX  AddressFormat
        ACCESS  read-write
        STATUS  mandatory
        DESCRIPTION
            "Indicator specifying how the originator should be specified in an
            AT/SM. Default is that originator is taken from the MO/SM without
            any modification. Note that this attribute might be overruled by
            the application-specific attribute applicationFormatOriginator."
        ::= { smsProperties 81 }

    smsPropFormatAtRecipient OBJECT-TYPE
        SYNTAX  AddressFormat
        ACCESS  read-write
        STATUS  mandatory
        DESCRIPTION
            "Indicator specifying how the recipient should be specified in an
            AT/SM. Default is that recipient is taken from the MO/SM without
            any modification. Note that this attribute might be overruled by
            the application-specific attribute applicationFormatRecipient."
        ::= { smsProperties 82 }

    smsPropFormatAtMsc OBJECT-TYPE
        SYNTAX  AddressFormat
        ACCESS  read-write
        STATUS  mandatory
        DESCRIPTION
            "Indicator specifying how the MSC should be specified in an AT/SM. 
            Default is that MSC is taken from the MO/SM without any 
            modification. Note that this attribute might be overruled by
            the application-specific attribute applicationFormatMsc."
        ::= { smsProperties 83 }

    smsPropFormatAtSmsc OBJECT-TYPE
        SYNTAX  AddressFormat
        ACCESS  read-write
        STATUS  mandatory
        DESCRIPTION
            "Indicator specifying how the SMSC should be specified in an
            AT/SM. Default is that SMSC is taken from the MO/SM without
            any modification. Note that this attribute might be overruled by
            the application-specific attribute applicationFormatSmsc."
        ::= { smsProperties 84 }

    smsPropFormatEciOriginator OBJECT-TYPE
        SYNTAX  AddressFormat
        ACCESS  read-write
        STATUS  mandatory
        DESCRIPTION
            "Indicator specifying how the originator should be specified in
            an ECI request. Default is  'international'. Note that this
            attribute might be overruled by the ECI application-specific
            attribute externalConditionFormatOriginator."
        ::= { smsProperties 85 }

    smsPropFormatEciRecipient OBJECT-TYPE
        SYNTAX  AddressFormat
        ACCESS  read-write
        STATUS  mandatory
        DESCRIPTION
            "Indicator specifying how the recipient should be specified in an
            ECI request. Default is  'international'. Note that this
            attribute might be overruled by the ECI application-specific
            attribute externalConditionFormatRecipient."
        ::= { smsProperties 86 }

    smsPropFormatEciMsc OBJECT-TYPE
        SYNTAX  AddressFormat
        ACCESS  read-write
        STATUS  mandatory
        DESCRIPTION
            "Indicator specifying how the MSC should be specified in an ECI
            request. Default is  'international'. Note that this attribute
            might be overruled by the ECI application-specific attribute
            externalConditionFormatMsc."
        ::= { smsProperties 87 }

    smsPropFormatEciSmsc OBJECT-TYPE
        SYNTAX  AddressFormat
        ACCESS  read-write
        STATUS  mandatory
        DESCRIPTION
            "Indicator specifying how the SMSC should be specified in an ECI
            request. Default is 'international'. Note that this attribute
            might be overruled by the ECI application-specific attribute
            externalConditionFormatSmsc."
        ::= { smsProperties 88 }

    smsPropFormatMtOriginatorForDomesticTraffic OBJECT-TYPE
        SYNTAX  AddressFormat
        ACCESS  read-write
        STATUS  mandatory
        DESCRIPTION
            "Indicator specifying how the originator should be specified in
            an MT/SM that is sent to a recipient of the same country as the
            one in which TextPass has been installed. Default is that
            recipient is taken from the MO/SM or AO/SM without any
            modification."
        ::= { smsProperties 90 }

    smsPropMoTagCaseSensitive OBJECT-TYPE
        SYNTAX  Boolean
        ACCESS  read-write
        STATUS  mandatory
        DESCRIPTION
            "Indicator specifying whether the MO tags that trigger specific
            functions (e.g. phase 1 status report) are case sensitive. Default
            is 'true'."
        ::= { smsProperties 101 }

    smsPropEnableAdvancedMoTagMode OBJECT-TYPE
        SYNTAX  Boolean
        ACCESS  read-write
        STATUS  mandatory
        DESCRIPTION
            "Indicator specifying whether advanced MO tag mode or simple MO
            tag mode is activated. When set to 'true', advanced MO tag mode
            is enabled. When set to 'false', simple MO tag mode is enabled.
            Default is 'false'.
            Advanced MO tag mode brings some features that are not available
            in simple MO tag mode. These features are:
            1. Support for multiple CMG-like scan tags in a single message.
            2. Support for scan tag functions with arguments.
            
            In simple MO tag mode, any delimiters to indicate start or end of
            an MO tag should be part of the MO tag string. In advanced MO tag
            mode, delimiters should not be part of the MO tag string. The
            delimiters are fixed: The asterix character (*) is used to start
            a sequence of tags and to seperate two consecutive tags in a
            sequence of tags. The hash (#) is used to terminate a sequence of
            tags."
        ::= { smsProperties 102 }

    smsPropAlwaysAcceptUnrecognisedMoTag OBJECT-TYPE
        SYNTAX  Boolean
        ACCESS  read-write
        STATUS  mandatory
        DESCRIPTION
            "Indicator specifying how to handle unrecognised MO tags in
            advanced MO tag mode. When set to 'true', SM's containing an
            unrecognised MO tag are always accepted. When set to 'false',
            SM's containing an unrecognised MO tag can only match an MO
            routing rule that relays the
            SM to the SMSC. Default is 'false'."
        ::= { smsProperties 103 }

    smsPropActionForMtStatusReports OBJECT-TYPE
        SYNTAX  StatusReportAction   
        ACCESS  read-write
        STATUS  mandatory
        DESCRIPTION
            "Action pertaining to the routing of status reports that terminate
            in mobiles. Default is routeFallbackToStorage."
        ::= { smsProperties 121 }
     
    smsPropActionForAtStatusReports OBJECT-TYPE
        SYNTAX  StatusReportAction   
        ACCESS  read-write
        STATUS  mandatory
        DESCRIPTION
            "Action pertaining to the routing of status reports that terminate
            in applications. Default is routeFallbackToStorage."
        ::= { smsProperties 122 }
     
    smsPropActionForExternalConditionMessages OBJECT-TYPE
        SYNTAX  StatusReportAction   
        ACCESS  read-write
        STATUS  mandatory
        DESCRIPTION
            "Action pertaining to the routing of messages that terminate
            in mobiles and that are sent as result of an external condition
            that did not satisfy. Default is routeFallbackToStorage."
        ::= { smsProperties 123 }
     
    smsPropExternalConditionMessagesSentAsFlashSMS OBJECT-TYPE
        SYNTAX  Boolean   
        ACCESS  read-write
        STATUS  mandatory
        DESCRIPTION
            "Pertaining to the encoding of messages that terminate
            in mobiles and that are sent as a result of an external condition
            that was not satisfied. Default is false."
        ::= { smsProperties 124 }
        
    smsPropEnableDialoutNotificationAsAmsMessageType OBJECT-TYPE
        SYNTAX  Boolean   
        ACCESS  read-write
        STATUS  mandatory
        DESCRIPTION
            "Indicator specifying whether the RTR generates AMS store 
            requests with message type 'dialoutNotification'. Default is 
            'false'.
            Initially, the AMS supported two message types: 'normalMessage' 
            and 'statusReport'. To better support notifications for AO 
            messages that need to be delivered using dialout, the message 
            type 'dialoutNotification' has been introduced. 
            This object has been added for compatibility reasons. It enables 
            the RTR to interface with a set of AMS-s that do not support the 
            'dialoutNotification' message type as  well as with an AMS set 
            that does support the 'dialoutNotification' message type."
        ::= { smsProperties 126 }

    smsPropAmsQueueForMtStatusReports OBJECT-TYPE
        SYNTAX  AmsQueueIndex
        ACCESS  read-write
        STATUS  mandatory
        DESCRIPTION
            "Specifies the AMS queue to store MT Status Reports. Default is 
            1."
        ::= { smsProperties 127 }

    smsPropAmsQueueForExternalConditionMessages OBJECT-TYPE
        SYNTAX  AmsQueueIndex
        ACCESS  read-write
        STATUS  mandatory
        DESCRIPTION
            "Specifies the AMS queue to store messages that terminate
            in mobiles and that are sent as result of an external condition
            that did not satisfy. Default is 1."
        ::= { smsProperties 128 }

    smsPropAmsQueueForRegularAtStatusReports OBJECT-TYPE
        SYNTAX  AmsQueueIndex
        ACCESS  read-write
        STATUS  mandatory
        DESCRIPTION
            "Specifies the AMS queue to store AT Status Reports that may be 
            delivered on sessions established by the application. Default 
            is 2."
        ::= { smsProperties 129 }

    smsPropAmsQueueForDialoutAtStatusReports OBJECT-TYPE
        SYNTAX  AmsQueueIndex
        ACCESS  read-write
        STATUS  mandatory
        DESCRIPTION
            "Specifies the AMS queue to store AT Status Reports that may only 
            be delivered on dialout sessions. Default is 2. 
            Notes: 
            1) If many AT Status Reports need to be delivered using dialout, 
               it is strongly recommended to setup a specific AMS queue
               for this type of status reports. The AMS is then able to 
               deliver these status reports faster.
            2) To enable this queue, set the following object to 'true':
               smsPropEnableDialoutNotificationAsAmsMessageType."
        ::= { smsProperties 130 }

    smsPropMaxStatusReportRetries OBJECT-TYPE
        SYNTAX  MaxStatusReportRetries
        ACCESS  read-write
        STATUS  mandatory
        DESCRIPTION
            "Maximum number of times that TextPass retries delivery for MT 
            status reports and external condition failure messages. 
            Default is 0."
        ::= { smsProperties 131 }

    smsPropStatusReportRetryInterval OBJECT-TYPE
        SYNTAX  StatusReportRetryInterval
        ACCESS  read-write
        STATUS  mandatory
        DESCRIPTION
            "Interval between two consecutive retries for an MT status report 
            or external condition failure messages. 
            The interval is expressed in number of seconds. Default is 60."
        ::= { smsProperties 132 }

    smsPropPhase1BufferedStatusReportEnabled OBJECT-TYPE
        SYNTAX  Boolean
        ACCESS  read-write
        STATUS  mandatory
        DESCRIPTION
            "Indicator specifying whether the generation of phase 1 status
            reports with status 'buffered' are generated or not. Default is 
            'false'."
        ::= { smsProperties 133 }

    smsPropOverrideNotificationTypeForMoAoMessages OBJECT-TYPE
        SYNTAX  NotificationType
        ACCESS  read-write
        STATUS  mandatory
        DESCRIPTION
            "Indicator specifying which notification types should be
            requested when an MO message is forwarded to an SMSC as AO.
            If any notification type is specified, the value received in the
            MO message is ignored. Otherwise, if the MO message requests
            a status report, both delivery and non-delivery notifications
            are requested. By default, delivery and non-delivery
            notifications are requested."
        ::= { smsProperties 134 }

    smsPropPhase2BufferedStatusReportEnabled OBJECT-TYPE
        SYNTAX  Boolean
        ACCESS  read-write
        STATUS  mandatory
        DESCRIPTION
            "Indicator specifying whether the generation of phase 2 status
            reports with status 'pending' are generated or not. Default is 
            'false'."
        ::= { smsProperties 135 }

    smsPropOverrideDeliveryNotificationRequestForAoAoMessages OBJECT-TYPE
        SYNTAX  BitValueModifier
        ACCESS  read-write
        STATUS  mandatory
        DESCRIPTION
            "Indicator specifying if and how to modify the request for a
            delivery notification of an AO-AO routed SM. By default, this
            object is set to -1 (no modification)."
        ::= { smsProperties 136 }

    smsPropOverrideNonDeliveryNotificationRequestForAoAoMessages OBJECT-TYPE
        SYNTAX  BitValueModifier
        ACCESS  read-write
        STATUS  mandatory
        DESCRIPTION
            "Indicator specifying if and how to modify the request for a
            non-delivery notification of an AO-AO routed SM. By default,
            this object is set to -1 (no modification)."
        ::= { smsProperties 137 }

    smsPropOverrideBufferedNotificationRequestForAoAoMessages OBJECT-TYPE
        SYNTAX  BitValueModifier
        ACCESS  read-write
        STATUS  mandatory
        DESCRIPTION
            "Indicator specifying if and how to modify the request for a
            buffered notification of an AO-AO routed SM. By default,
            this object is set to -1 (no modification)."
        ::= { smsProperties 138 }

    smsPropMaxRetriesForExternalConditionMessages OBJECT-TYPE
        SYNTAX  INTEGER(1..20)
        ACCESS  read-write
        STATUS  mandatory
        DESCRIPTION
            "Maximum number of times that TextPass retries delivery for MT 
            external condition messages. Default is 0."
    ::= { smsProperties 139 }

    smsPropRetryIntervalForExternalConditionMessages OBJECT-TYPE
        SYNTAX  INTEGER(1..900)
        ACCESS  read-write
        STATUS  mandatory
        DESCRIPTION
            "Interval between two consecutive retries for an MT external
            condition message. The interval is expressed in number of
            seconds. Default is 60."
    ::= { smsProperties 140 }

    smsPropHubMaxResponseTime OBJECT-TYPE
        SYNTAX  ApplicationTimer
        ACCESS  read-write
        STATUS  mandatory
        DESCRIPTION
            "Maximum time span, expressed in seconds, that TextPass ROUTER
            waits for a response from the TextPass HUB before it considers
            the relating message as timed out. The default is 15 seconds."
        ::= { smsProperties 141 }

    smsPropAmsMaxResponseTime OBJECT-TYPE
        SYNTAX  ApplicationTimer
        ACCESS  read-write
        STATUS  mandatory
        DESCRIPTION
            "Maximum time span, expressed in seconds, that TextPass ROUTER
            waits for a response from the TextPass AMS before it considers
            the relating message as timed out. The default is 5 seconds."
        ::= { smsProperties 142 }

    smsPropThroughputControlMaxDelay OBJECT-TYPE
        SYNTAX  ApplicationTimer
        ACCESS  read-write
        STATUS  mandatory
        DESCRIPTION
            "Maximum delay between receiving an AO/SM from an application and 
            returning the ACK to the application. This threshold is taken into
            account by the throughput control mechanism. When this mechanism
            detects that the delay as result of throughput control exceeds the
            threshold, the message is NAK-ed. The default is 3 seconds."
        ::= { smsProperties 143 }
        
    smsPropAoRtgRuleMatchesWhenThroughputExceeded OBJECT-TYPE
        SYNTAX  Boolean
        ACCESS  read-write
        STATUS  mandatory
        DESCRIPTION
            "Indicator specifying whether an AO routing rule should match
            when maximum throughput threshold is exceeded. If the indicator
            is equal to 'true' and maximum throughput threshold is exceeded,
            the message is always rejected.
            Default is 'true'."
        ::= { smsProperties 144 }
        
    smsPropSs7ConnectivityRequired OBJECT-TYPE
        SYNTAX  Boolean
        ACCESS  read-write
        STATUS  mandatory
        DESCRIPTION
            "Indicator specifying that the TextPass ROUTER may only transit to
            'operating' state after connectivity to SS.7 network has been 
            established. Default of this setting is 'true'. If there are 
            neither ss7 nor sctp connections defined in your configuration 
            then this setting has no effect."
        ::= { smsProperties 152 }        

    smsPropBlockedErrorStringOfPhase1StatusReport OBJECT-TYPE
        SYNTAX  TemplateString
        ACCESS  read-write
        STATUS  mandatory
        DESCRIPTION
            "Error string specifying that an SM has failed to be delivered
            due to a blocking by a rule. Default is 'Blocked'."
        ::= { smsProperties 161 }

    smsPropStorageFailureErrorStringOfPhase1StatusReport OBJECT-TYPE
        SYNTAX  TemplateString
        ACCESS  read-write
        STATUS  mandatory
        DESCRIPTION
            "Error string specifying that an SM has failed to be delivered
            due to a storage failure. Default is 'Storage failure'."
        ::= { smsProperties 162 }

    smsPropApplicationFailureErrorStringOfPhase1StatusReport OBJECT-TYPE
        SYNTAX  TemplateString
        ACCESS  read-write
        STATUS  mandatory
        DESCRIPTION
            "Error string specifying that an SM has failed to be delivered
            due to an application failure. Default is 'Application failure'."
        ::= { smsProperties 163 }

    smsPropTimeoutErrorStringOfPhase1StatusReport OBJECT-TYPE
        SYNTAX  TemplateString
        ACCESS  read-write
        STATUS  mandatory
        DESCRIPTION
            "Error string specifying that an SM has failed to be delivered
            due to a timeout. Default is 'Timeout'.  Setting this error
            string only makes sense when errClsMtTimeout or
            errClsSriSmTimeout is set to 'permanentForRecipient' or
            'permanentForMessage'"
        ::= { smsProperties 164 }

    smsPropAbsSubErrorStringOfPhase1StatusReport OBJECT-TYPE
        SYNTAX  TemplateString
        ACCESS  read-write
        STATUS  mandatory
        DESCRIPTION
            "Error string specifying that an SM has failed to be delivered
            due to absent subscriber error. Default is 'Absent subscriber
            (code 27)'.  Setting this error string only makes sense when
            errClsMtAbsSubError or errClsSriSmAbsSubError is set to
            'permanentForRecipient' or 'permanentForMessage'"
        ::= { smsProperties 165 }

    smsPropSysFailErrorStringOfPhase1StatusReport OBJECT-TYPE
        SYNTAX  TemplateString
        ACCESS  read-write
        STATUS  mandatory
        DESCRIPTION
            "Error string specifying that an SM has failed to be delivered
            due to a system failure error. Default is 'System failure (code
            34)'.
            Setting this error string only makes sense when
            errClsMtSysFailError or errClsSriSmSysFailError is set to
            'permanentForRecipient' or 'permanentForMessage'"
        ::= { smsProperties 166 }

    smsPropDataMisErrorStringOfPhase1StatusReport OBJECT-TYPE
        SYNTAX  TemplateString
        ACCESS  read-write
        STATUS  mandatory
        DESCRIPTION
            "Error string specifying that an SM has failed to be delivered
            due to a data missing error. Default is 'Data missing (code 35)'. 
            Setting this error string only makes sense when
            errClsMtDataMisError or errClsSriSmDataMisError is set to
            'permanentForRecipient' or 'permanentForMessage'"
        ::= { smsProperties 167 }

    smsPropUnexpDataValErrorStringOfPhase1StatusReport OBJECT-TYPE
        SYNTAX  TemplateString
        ACCESS  read-write
        STATUS  mandatory
        DESCRIPTION
            "Error string specifying that an SM has failed to be delivered
            due to a unexpected data value error. Default is 'Unexpected data
            value (code 36)'. 
            Setting this error string only makes sense when
            errClsMtUnexpDataValError or errClsSriSmUnexpDataValError is set
            to 'permanentForRecipient' or 'permanentForMessage'"
        ::= { smsProperties 168 }

    smsPropFacNotSuppErrorStringOfPhase1StatusReport OBJECT-TYPE
        SYNTAX  TemplateString
        ACCESS  read-write
        STATUS  mandatory
        DESCRIPTION
            "Error string specifying that an SM has failed to be delivered
            due to a facility not supported error. Default is 'Facility not
            supported (code 21)'. 
            Setting this error string only makes sense when
            errClsMtFacNotSuppError or errClsSriSmMtFacNotSuppError is set to
            'permanentForRecipient' or 'permanentForMessage'"
        ::= { smsProperties 169 }

    smsPropUnidenSubErrorStringOfPhase1StatusReport OBJECT-TYPE
        SYNTAX  TemplateString
        ACCESS  read-write
        STATUS  mandatory
        DESCRIPTION
            "Error string specifying that an SM has failed to be delivered
            due to a unidentified subscriber error. Default is 'Unidentified
            subscriber (code 5)'. 
            Setting this error string only makes sense when
            errClsMtUnidenSubError is set to 'permanentForRecipient' or
            'permanentForMessage'"
        ::= { smsProperties 170 }

    smsPropIllSubErrorStringOfPhase1StatusReport OBJECT-TYPE
        SYNTAX  TemplateString
        ACCESS  read-write
        STATUS  mandatory
        DESCRIPTION
            "Error string specifying that an SM has failed to be delivered
            due to a illegal subscriber error. Default is 'Illegal subscriber
            (code 9)'. 
            Setting this error string only makes sense when
            errClsMtIllSubError is set to 'permanentForRecipient' or
            'permanentForMessage'"
        ::= { smsProperties 171 }

    smsPropIllEquipErrorStringOfPhase1StatusReport OBJECT-TYPE
        SYNTAX  TemplateString
        ACCESS  read-write
        STATUS  mandatory
        DESCRIPTION
            "Error string specifying that an SM has failed to be delivered
            due to a illegal equipment error. Default is 'Illegal equipment
            (code 12)'. 
            Setting this error string only makes sense when 
            errClsMtIllEquipError is set to 'permanentForRecipient' or 
            'permanentForMessage'"
        ::= { smsProperties 172 }

    smsPropSubBusyForMtSmErrorStringOfPhase1StatusReport OBJECT-TYPE
        SYNTAX  TemplateString
        ACCESS  read-write
        STATUS  mandatory
        DESCRIPTION
            "Error string specifying that an SM has failed to be delivered
            due to a subscriber busy for MT/SM error. Default is 'Subscriber
            busy  for MT/SM (code 31)'. 
            Setting this error string only makes sense when 
            errClsMtIllEquipError or errClsSriSmIllEquipError is set to 
            'permanentForRecipient' or 'permanentForMessage'"
        ::= { smsProperties 173 }

    smsPropInvSmeAddrErrorStringOfPhase1StatusReport OBJECT-TYPE
        SYNTAX  TemplateString
        ACCESS  read-write
        STATUS  mandatory
        DESCRIPTION
            "Error string specifying that an SM has failed to be delivered
            due to a invalid SME address error. Default is 'Invalid SME
            address (code 32 diag 5)'. 
            Setting this error string only makes sense when 
            errClsMtInvSmeAddrError is set to 'permanentForRecipient' or 
            'permanentForMessage'"
        ::= { smsProperties 174 }

    smsPropEquipProtErrorStringOfPhase1StatusReport OBJECT-TYPE
        SYNTAX  TemplateString
        ACCESS  read-write
        STATUS  mandatory
        DESCRIPTION
            "Error string specifying that an SM has failed to be delivered
            due to a equipment protocol error. Default is 'Equipment protocol
            error (code 32 diag 1)'. 
            Setting this error string only makes sense when 
            errClsMtEquipProtError is set to 'permanentForRecipient' or 
            'permanentForMessage'"
        ::= { smsProperties 175 }

    smsPropEquipNotSmEquipErrorStringOfPhase1StatusReport OBJECT-TYPE
        SYNTAX  TemplateString
        ACCESS  read-write
        STATUS  mandatory
        DESCRIPTION
            "Error string specifying that an SM has failed to be delivered
            due to a equipment not SM equipped error. Default is 'Equipment
            not SM equipped (code 32 diag 2)'. 
            Setting this error string only makes sense when 
            errClsMtEquipNotSmEquipError is set to 'permanentForRecipient' or 
            'permanentForMessage'"
        ::= { smsProperties 176 }

    smsPropMemCapExcErrorStringOfPhase1StatusReport OBJECT-TYPE
        SYNTAX  TemplateString
        ACCESS  read-write
        STATUS  mandatory
        DESCRIPTION
            "Error string specifying that an SM has failed to be delivered
            due to a memory capacity error. Default is 'Memory capacity
            exceeded (code 32 diag 0)'. 
            Setting this error string only makes sense when 
            errClsMtMemCapExcError is set to 'permanentForRecipient' or 
            'permanentForMessage'"
        ::= { smsProperties 177 }

    smsPropUnkSubErrorStringOfPhase1StatusReport OBJECT-TYPE
        SYNTAX  TemplateString
        ACCESS  read-write
        STATUS  mandatory
        DESCRIPTION
            "Error string specifying that an SM has failed to be delivered
            due to a unknown subscriber error. Default is 'Unknown subscriber
            (code 1)'. 
            Setting this error string only makes sense when 
            errClsSriSmUnkSubError is set to 'permanentForRecipient' or 
            'permanentForMessage'"
        ::= { smsProperties 178 }

    smsPropCallBarredErrorStringOfPhase1StatusReport OBJECT-TYPE
        SYNTAX  TemplateString
        ACCESS  read-write
        STATUS  mandatory
        DESCRIPTION
            "Error string specifying that an SM has failed to be delivered
            due to a call barred error. Default is 'Call barred (code 13)'. 
            Setting this error string only makes sense when 
            errClsSriSmCallBarredError is set to 'permanentForRecipient' or 
            'permanentForMessage'"
        ::= { smsProperties 179 }

    smsPropTeleServNotProvErrorStringOfPhase1StatusReport OBJECT-TYPE
        SYNTAX  TemplateString
        ACCESS  read-write
        STATUS  mandatory
        DESCRIPTION
            "Error string specifying that an SM has failed to be delivered
            due to a teleservice not provisioned error. Default is
            'Teleservice not provisioned (code 11)'. 
            Setting this error string only makes sense when 
            errClsSriSmCallBarredError is set to 'permanentForRecipient' or 
            'permanentForMessage'"
        ::= { smsProperties 180 }

    smsPropTcapAbortedErrorStringOfPhase1StatusReport OBJECT-TYPE
        SYNTAX  TemplateString
        ACCESS  read-write
        STATUS  mandatory
        DESCRIPTION
            "Error string specifying that an SM has failed to be delivered
            due to a TCAP abort. Default is 'TCAP abort'. 
            Setting this error string only makes sense when 
            errClsMtTcapAbortedError or errClsSriSmTcapAbortedError is set to 
            'permanentForRecipient' or 'permanentForMessage'"
        ::= { smsProperties 181 }

    smsPropSccpAbortedErrorStringOfPhase1StatusReport OBJECT-TYPE
        SYNTAX  TemplateString
        ACCESS  read-write
        STATUS  mandatory
        DESCRIPTION
            "Error string specifying that an SM has failed to be delivered
            due to a SCCP abort. Default is 'SCCP abort'. 
            Setting this error string only makes sense when 
            errClsMtSccpAbortedError or errClsSriSmSccpAbortedError is set to 
            'permanentForRecipient' or 'permanentForMessage'"
        ::= { smsProperties 182 }

    smsPropMapPhaseForImsMessage OBJECT-TYPE
        SYNTAX  MapPhase
        ACCESS  read-write
        STATUS  mandatory
        DESCRIPTION
            "Map Phase to be used when an message from an IMS network is 
            forwarded to a GSM network. By default, MAP phase 2 is used."
        ::= { smsProperties 191 }

    smsPropRoutingDataProxyTimeout OBJECT-TYPE
        SYNTAX  RdpTimeout
        ACCESS  read-write
        STATUS  mandatory
        DESCRIPTION
            "Timeout for the Routing Data Proxy in units of seconds. The
            defaut value is 10 seconds."
        ::= { smsProperties 192 }

    smsPropIssueRsiForSrismAbsentSubscriber OBJECT-TYPE
        SYNTAX  Boolean
        ACCESS  read-write
        STATUS  mandatory
        DESCRIPTION
            "Flag specifying whether the Router should issue a Recipient
            Status Indication when it receives an AbsentSubscriber(SM)
            error to an SRI-SM request. By default, this object is set
            to 'true'."
        ::= { smsProperties 193 }
    
    smsPropIssueRsiForSrismMobileNotReachable OBJECT-TYPE
        SYNTAX  Boolean
        ACCESS  read-write
        STATUS  mandatory
        DESCRIPTION
            "Flag specifying whether the Router should issue a Recipient
            Status Indication when it receives an SRI-SM response having
            the Mobile Not Reachable Flag (MNRF) set. By default, this
            object is set to 'true'."
        ::= { smsProperties 194 }
    
    smsPropIssueRsiForNegativeRepStat OBJECT-TYPE
        SYNTAX  Boolean
        ACCESS  read-write
        STATUS  mandatory
        DESCRIPTION
            "Flag specifying whether the Router should issue a Recipient
            Status Indication when it receives a Report SM Delivery Status
            (RepStat) message specifying a negative delivery outcome (absent
            subscriber or memory capacity exceeded). By default, this object 
            is set to 'true'."
        ::= { smsProperties 195 }
    
    smsPropIssueRsiForPositiveRepStat OBJECT-TYPE
        SYNTAX  Boolean
        ACCESS  read-write
        STATUS  mandatory
        DESCRIPTION
            "Flag specifying whether the Router should issue a Recipient
            Status Indication when it receives a Report SM Delivery Status
            (RepStat) message specifying a positive delivery outcome.By
            default, this object is set to 'true'."
        ::= { smsProperties 196 }
    
    smsPropMaxStoreRequestsPerSecond OBJECT-TYPE
        SYNTAX  INTEGER
        ACCESS  read-write
        STATUS  mandatory
        DESCRIPTION
            "The maximum number of Store Request messages that a (set of)
            Router(s) may send per second to a (set of) AMS(s). Setting this
            threshold helps preventing the router(s) from flooding AMSs with
            messages to be stored. The default value is 350 Store Request 
            messages per second. This only works reliably if all routers have
            this object set to the same value.
            Example: assume that there are 2 Routers and 2 AMSs, and that this
            object is set to 500. Then, each of the two routers is entitled to
            distribute 250 SMs per second over the two AMSs. If one AMS goes 
            down, each router will send all 250 SMs to the remaining AMS."
        ::= { smsProperties 201 }

    -- OIDs 206 - 208 used to be used for the preliminary AT-AT big pipe impl.

    smsPropHlrQueryForRecipientBeforeApproval OBJECT-TYPE
        SYNTAX  Boolean
        ACCESS  read-write
        STATUS  mandatory
        DESCRIPTION
            "Indicator specifying that HLR query for recipient is done before
            or after the evaluation of the MO External Condition (MOX) rules.
            When set to 'false', the HLR query for recipient is done after
            the evaluation of MOX rules. When set to 'true', the HLR query
            for recipient precedes the evaluation of MOX rules.
            Default is 'false'."
        ::= { smsProperties 211 }

    smsPropHlrQueryForRecipientOfAoBeforeApproval OBJECT-TYPE
        SYNTAX  Boolean
        ACCESS  read-write
        STATUS  mandatory
        DESCRIPTION
            "Indicator specifying that an HLR query for recipient is done
            before the evaluation of the AO External Condition (AOX) rules.
            When set to 'false', the HLR query for the recipient is done
            depending on the routing path applied to the AO message.
            An HLR query is only attempted if the recipient number has
            been recognised as an MSISDN. Default is 'false'."
        ::= { smsProperties 212 }

    smsPropWhiteListOfMoRecipientForHlrQueryBeforeApproval OBJECT-TYPE
        SYNTAX  NameString
        ACCESS  read-write
        STATUS  mandatory
        DESCRIPTION
            "Name of a list with conditions that should be matched with
            the recipient MSISDN of an inbound MO message. If a name is
            specified, and the corresponding list is provisioned, the
            setting of smsPropHlrQueryForRecipientBeforeApproval is ignored.
            If there is a match, the router will issue an HLR query before
            evaluating the MO External Condition Rules.
            If the name is not specified (default) or does not match with
            a provisioned condition list, the
            smsPropHlrQueryForRecipientBeforeApproval object is used to
            control the behaviour of the router, independent of the MO
            message's recipient address."
        ::= { smsProperties 213 }

    smsPropWhiteListOfAoRecipientForHlrQueryBeforeApproval OBJECT-TYPE
        SYNTAX  NameString
        ACCESS  read-write
        STATUS  mandatory
        DESCRIPTION
            "Name of a list with conditions that should be matched with
            the recipient MSISDN of an inbound AO message. If a name is
            specified, and the corresponding list is provisioned, the
            setting of smsPropHlrQueryForRecipientOfAoBeforeApproval is
            ignored. If there is a match, the router will issue an HLR
            query before evaluating the MO External Condition Rules.
            If the name is not specified (default) or does not match with
            a provisioned condition list, the
            smsPropHlrQueryForRecipientOfAoBeforeApproval object is used to
            control the behaviour of the router, independent of the AO
            message's recipient address."
        ::= { smsProperties 214 }

    smsPropEnableBasicThroughputLimitHitLogging OBJECT-TYPE
        SYNTAX  Boolean
        ACCESS  read-write
        STATUS  mandatory
        DESCRIPTION
            "Indicator specifying whether a message should be written to 
            syslog whenever a throughput limit of one of the following 
            entities is being hit:
            - AO Routing Rule
            - Application
            - Application Group
            - Service Class
            - Service Centre
            - SC Node
            - SC Termination Point
            Note that:
            - A filter is applied to the log requests for generic events like 
              the 'throughput limit hit' events. The filter can be tuned 
              using the following parameters: genPropGenLogEventInterval, 
              genPropGenLogEventCount and genPropGenLogLevel.
              genPropGenLogEventInterval and genPropGenLogEventCount prevent
              flooding of the log file by multiple occurences of the same 
              event within a short time frame.
              The genPropGenLogLevel parameter should be set to 'warning' or 
              'error'. Any other value will result in the filter blocking the
              'throughput limit exceeded' events.
            - Besides the basic logging of 'throughput limit hit' events, a 
              more enhanced type of logging is available. The enhanced type of
              logging reveals the application causing the 'throughput limit 
              hit' event. It can be enabled on a per application basis by
              setting applicationLogLevel equal to 'warning' or 'error'.
            - Default value for this object is 'false'."
        ::= { smsProperties 221 }
        
    smsPropWhiteListOfMoMscForSpoofCheckSuppression OBJECT-TYPE
        SYNTAX  NameString
        ACCESS  read-write
        STATUS  mandatory
        DESCRIPTION
            "Name of a list of MSC GTs.  If an MO message originates
            from an MSC on the list, the MO spoof check is suppressed."
        ::= { smsProperties 222 }

    ----------------------------------------------------------------------------
    smsCounters OBJECT IDENTIFIER ::= { sms 2 }

    smsCntMoTotalCounter OBJECT-TYPE
        SYNTAX  Counter
        ACCESS  read-write
        STATUS  mandatory
        DESCRIPTION
            "Counter specifying the total number of times an MO/SM was
            received."
        ::= { smsCounters 1 }

    smsCntMoSuccessfulCounter OBJECT-TYPE
        SYNTAX  Counter
        ACCESS  read-write
        STATUS  mandatory
        DESCRIPTION
            "Counter specifying the number of times an MO/SM was successfully
             routed to its destination. The following events result in
             incrementing of this counter:
             - receiving a MO/SM matching a rule with action equal to
               discardWithAck
             - receiving an ACK from an application as result of an MO/SM
               being routed to the application
             - receiving an ACK from an SMSC as result of an MO/SM being
               routed to the SMSC."
        ::= { smsCounters 2 }

    smsCntMoTimeoutCounter OBJECT-TYPE
        SYNTAX  Counter
        ACCESS  read-write
        STATUS  mandatory
        DESCRIPTION
            "Counter specifying the number of times that routing an MO/SM to
            its destination resulted in a timeout. The following events
            result in incrementing of this counter:
             - not receiving a response from an application on an MO/SM
               being routed to the application within the maximum response
               time
             - not receiving an ACK from an SMSC as result of an MO/SM being
               routed to an SMSC within the maximum response time."
        ::= { smsCounters 3 }

    smsCntMoDroppedCounter OBJECT-TYPE
        SYNTAX  Counter
        ACCESS  read-write
        STATUS  mandatory
        DESCRIPTION
            "Counter specifying the number of times that an MO/SM has not
            been routed to its destination due to decimation (this is only
            applicable when routing to an application)."
        ::= { smsCounters 4 }

    smsCntMoDiscardWithNakCounter OBJECT-TYPE
        SYNTAX  Counter
        ACCESS  read-write
        STATUS  mandatory
        DESCRIPTION
            "Counter specifying the number of times that TPR has rejected an
            MO/SM as result of a routing rule with action equal to
            discardWithNak or because none of the routing rules match."
        ::= { smsCounters 5 }

    smsCntMoRejectedByTprCounter OBJECT-TYPE
        SYNTAX  Counter
        ACCESS  read-write
        STATUS  mandatory
        DESCRIPTION
            "Counter specifying the number of times that TPR has rejected an
            MO/SM as result of incorrect syntax of the MO/SM."
        ::= { smsCounters 6 }

    smsCntMoRejectedByAppCounter OBJECT-TYPE
        SYNTAX  Counter
        ACCESS  read-write
        STATUS  mandatory
        DESCRIPTION
            "Counter specifying the number of times that routing to an
            application resulted in the application rejecting the MO/SM by
            sending a NAK."
        ::= { smsCounters 7 }

    smsCntMoUnknownResultCounter OBJECT-TYPE
        SYNTAX  Counter
        ACCESS  read-write
        STATUS  mandatory
        DESCRIPTION
            "Counter specifying the number of times that the result of routing
            an MO/SM to its destination could not be retrieved (this is only
            applicable when using optimal routing towards an SMSC)."
        ::= { smsCounters 8 }

    smsCntMoSysFailErrorCounter OBJECT-TYPE
        SYNTAX  Counter
        ACCESS  read-write
        STATUS  mandatory
        DESCRIPTION
            "Counter specifying the number of times that routing to an SMSC
            resulted in the SMSC rejecting the MO/SM with a System-Failure
            error on MAP level."
        ::= { smsCounters 9 }

    smsCntMoDataMisErrorCounter OBJECT-TYPE
        SYNTAX  Counter
        ACCESS  read-write
        STATUS  mandatory
        DESCRIPTION
            "Counter specifying the number of times that routing to an SMSC
            resulted in the SMSC rejecting the MO/SM with a Data-Missing
            error on MAP level."
        ::= { smsCounters 10 }

    smsCntMoUnexpDataValErrorCounter OBJECT-TYPE
        SYNTAX  Counter
        ACCESS  read-write
        STATUS  mandatory
        DESCRIPTION
            "Counter specifying the number of times that routing to an SMSC
            resulted in the SMSC rejecting the MO/SM with a Unexpected-Data-
            Value error on MAP level."
        ::= { smsCounters 11 }

    smsCntMoFacNotSuppErrorCounter OBJECT-TYPE
        SYNTAX  Counter
        ACCESS  read-write
        STATUS  mandatory
        DESCRIPTION
            "Counter specifying the number of times that routing to an SMSC
            resulted in the SMSC rejecting the MO/SM with a Facility-Not-
            Supported error on MAP level."
        ::= { smsCounters 12 }

    smsCntMoUnkScErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Unknown-
            Service-Centre."
        ::= { smsCounters 13 }

    smsCntMoScCongErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to SC-
            Congestion."
        ::= { smsCounters 14 }

    smsCntMoInvSmeAddrErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Invalid-
            SME-Address."
        ::= { smsCounters 15 }

    smsCntMoSubNotScSubErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to
            Subscriber-Not-SC-Subscriber."
        ::= { smsCounters 16 }

    smsCntMoOtherErrorsCounter OBJECT-TYPE
        SYNTAX  Counter
        ACCESS  read-write
        STATUS  mandatory
        DESCRIPTION
            "Counter specifying the number of times that routing to an SMSC
            resulted in the SMSC rejecting the MO/SM with another MAP error
            (or possibly a failure cause) than specified for the
            other MO counters."
        ::= { smsCounters 17 }

    smsCntMoTcapAbortedCounter OBJECT-TYPE
        SYNTAX  Counter
        ACCESS  read-write
        STATUS  mandatory
        DESCRIPTION
            "Counter specifying the number of times that routing to an SMSC
            resulted in the SMSC rejecting the MO/SM by sending a TC-ABORT
            on TCAP level."
        ::= { smsCounters 18 }

    smsCntMoSccpAbortedCounter OBJECT-TYPE
        SYNTAX  Counter
        ACCESS  read-write
        STATUS  mandatory
        DESCRIPTION
            "Counter specifying the number of times that routing to an SMSC
            resulted in the SMSC rejecting the MO/SM by sending a UDTS on
            SCCP level."
        ::= { smsCounters 19 }

    smsCntMtTotalCounter OBJECT-TYPE
        SYNTAX  Counter
        ACCESS  read-write
        STATUS  mandatory
        DESCRIPTION
            "Counter specifying the total number of times an MT/SM was issued
            by the TPR. This counter is incremented whenever:
            - the TPR issues a MT/SM on behalf of an application that is
              directly connected to the TPR
            - the TPR receives all MT/SM's from an SMSC and directs the MT/SM
              to its destination."
        ::= { smsCounters 20 }

    smsCntMtSuccessfulCounter OBJECT-TYPE
        SYNTAX  Counter
        ACCESS  read-write
        STATUS  mandatory
        DESCRIPTION
            "Counter specifying the number of times an MT/SM was successfully
            delivered."
        ::= { smsCounters 21 }

    smsCntMtTimeoutCounter OBJECT-TYPE
        SYNTAX  Counter
        ACCESS  read-write
        STATUS  mandatory
        DESCRIPTION
            "Counter specifying the number of times that delivering an MT/SM
            resulted in a timeout."
        ::= { smsCounters 22 }

    smsCntMtAbsSubErrorCounter OBJECT-TYPE
        SYNTAX  Counter
        ACCESS  read-write
        STATUS  mandatory
        DESCRIPTION
            "Counter specifying the number of times that delivering an MT/SM
            resulted in an Absent-Subscriber error."
        ::= { smsCounters 23 }

    smsCntMtSysFailErrorCounter OBJECT-TYPE
        SYNTAX  Counter
        ACCESS  read-write
        STATUS  mandatory
        DESCRIPTION
            "Counter specifying the number of times that delivering an MT/SM
            resulted in an System-Failure error."
        ::= { smsCounters 24 }

    smsCntMtDataMisErrorCounter OBJECT-TYPE
        SYNTAX  Counter
        ACCESS  read-write
        STATUS  mandatory
        DESCRIPTION
            "Counter specifying the number of times that delivering an MT/SM
            resulted in an Data-Missing error."
        ::= { smsCounters 25 }

    smsCntMtUnexpDataValErrorCounter OBJECT-TYPE
        SYNTAX  Counter
        ACCESS  read-write
        STATUS  mandatory
        DESCRIPTION
            "Counter specifying the number of times that delivering an MT/SM
            resulted in an Unexpected-Data-Value error."
        ::= { smsCounters 26 }

   smsCntMtFacNotSuppErrorCounter OBJECT-TYPE
        SYNTAX  Counter
        ACCESS  read-write
        STATUS  mandatory
        DESCRIPTION
            "Counter specifying the number of times that delivering an MT/SM
            resulted in an Facility-Not-Supported error."
        ::= { smsCounters 27 }

    smsCntMtUnidenSubErrorCounter OBJECT-TYPE
        SYNTAX  Counter
        ACCESS  read-write
        STATUS  mandatory
        DESCRIPTION
            "Counter specifying the number of times that delivering an MT/SM
            resulted in an Unidentified-Subscriber error."
        ::= { smsCounters 28 }

    smsCntMtIllSubErrorCounter OBJECT-TYPE
        SYNTAX  Counter
        ACCESS  read-write
        STATUS  mandatory
        DESCRIPTION
            "Counter specifying the number of times that delivering an MT/SM
            resulted in an Illegal-Subscriber error."
        ::= { smsCounters 29 }

    smsCntMtIllEquipErrorCounter OBJECT-TYPE
        SYNTAX  Counter
        ACCESS  read-write
        STATUS  mandatory
        DESCRIPTION
            "Counter specifying the number of times that delivering an MT/SM
            resulted in an Illegal-Equipment error."
        ::= { smsCounters 30 }

    smsCntMtSubBusyForMtSmErrorCounter OBJECT-TYPE
        SYNTAX  Counter
        ACCESS  read-write
        STATUS  mandatory
        DESCRIPTION
            "Counter specifying the number of times that delivering an MT/SM
            resulted in an Subscriber-Busy-For-MT-SMS error."
        ::= { smsCounters 31 }

    smsCntMtInvSmeAddrErrorCounter OBJECT-TYPE
        SYNTAX  Counter
        ACCESS  read-write
        STATUS  mandatory
        DESCRIPTION
            "Counter specifying the number of times that delivering an MT/SM
            resulted in a SM-Delivery-Failure error with failure cause equal
            to Invalid-SME-Address."
        ::= { smsCounters 32 }

    smsCntMtEquipProtErrorCounter OBJECT-TYPE
        SYNTAX  Counter
        ACCESS  read-write
        STATUS  mandatory
        DESCRIPTION
            "Counter specifying the number of times that delivering an MT/SM
            resulted in a SM-Delivery-Failure error with failure cause equal
            to Equipment-Protocol-Error."
        ::= { smsCounters 33 }

    smsCntMtEquipNotSmEquipErrorCounter OBJECT-TYPE
        SYNTAX  Counter
        ACCESS  read-write
        STATUS  mandatory
        DESCRIPTION
            "Counter specifying the number of times that delivering an MT/SM
            resulted in a SM-Delivery-Failure error with failure cause equal
            to Equipment-Not-SM-equipped."
        ::= { smsCounters 34 }

    smsCntMtMemCapExcErrorCounter OBJECT-TYPE
        SYNTAX  Counter
        ACCESS  read-write
        STATUS  mandatory
        DESCRIPTION
            "Counter specifying the number of times that delivering an MT/SM
            resulted in a SM-Delivery-Failure error with failure cause equal
            to Memory-Capacity-Exceeded."
        ::= { smsCounters 35 }

    smsCntMtOtherErrorsCounter OBJECT-TYPE
        SYNTAX  Counter
        ACCESS  read-write
        STATUS  mandatory
        DESCRIPTION
            "Counter specifying the number of times that delivering an MT/SM
            resulted in another MAP error (or possibly a failure cause) than
            specified for the other MT counters."
        ::= { smsCounters 36 }

    smsCntMtTcapAbortedCounter OBJECT-TYPE
        SYNTAX  Counter
        ACCESS  read-write
        STATUS  mandatory
        DESCRIPTION
            "Counter specifying the number of times that delivering an MT/SM
            resulted in the MSC/SGSN rejecting the MT/SM by sending a TC-ABORT
            on TCAP level."
        ::= { smsCounters 37 }

    smsCntMtSccpAbortedCounter OBJECT-TYPE
        SYNTAX  Counter
        ACCESS  read-write
        STATUS  mandatory
        DESCRIPTION
            "Counter specifying the number of times that delivering an MT/SM
            resulted in the MSC/SGSN rejecting the MT/SM by sending a UDTS on
            SCCP level."
        ::= { smsCounters 38 }

    smsCntMtFallbackToVersion2Counter OBJECT-TYPE
        SYNTAX  Counter
        ACCESS  read-write
        STATUS  mandatory
        DESCRIPTION
            "Counter specifying the number of times that delivering an MT/SM
            resulted in the MSC/SGSN requesting to fallback to MAP version 2."
        ::= { smsCounters 39 }

    smsCntMtFallbackToVersion1Counter OBJECT-TYPE
        SYNTAX  Counter
        ACCESS  read-write
        STATUS  mandatory
        DESCRIPTION
            "Counter specifying the number of times that delivering an MT/SM
            resulted in the MSC/SGSN requesting to fallback to MAP version 1."
        ::= { smsCounters 40 }

    smsCntMtAlternatePathUsedCounter OBJECT-TYPE
        SYNTAX  Counter
        ACCESS  read-write
        STATUS  mandatory
        DESCRIPTION
            "Counter specifying the number of times that for delivering an
            MT/SM both paths (through MSC and through SGSN) were available
            and that delivery on the primary path failed (and the alternate
            path was thus used)."
        ::= { smsCounters 41 }

    smsCntMtAlternatePathNotUsedCounter OBJECT-TYPE
        SYNTAX  Counter
        ACCESS  read-write
        STATUS  mandatory
        DESCRIPTION
            "Counter specifying the number of times that for delivering an
            MT/SM both paths (through MSC and through SGSN) were available
            and that delivery on the primary path succeeded (and the
            alternate path was thus not used)."
        ::= { smsCounters 42 }

    smsCntSriSmTotalCounter OBJECT-TYPE
        SYNTAX  Counter
        ACCESS  read-write
        STATUS  mandatory
        DESCRIPTION
            "Counter specifying the total number of times a Send-Routing-Info-
            For-SM operation was issued
            by the TPR. This counter is incremented whenever:
            - the TPR issues a Send-Routing-Info-For-SM operation as part of
              the delivery of a MT/SM that was sent by an application that is
              directly connected to the TPR
            - the TPR receives all Send-Routing-Info-For-SM operations from
              an SMSC and directs the opeation to its destination."
        ::= { smsCounters 43 }

    smsCntSriSmSuccessCounter OBJECT-TYPE
        SYNTAX  Counter
        ACCESS  read-write
        STATUS  mandatory
        DESCRIPTION
            "Counter specifying the number of times a Send-Routing-Info-For-
            SM operation was successfully issued."
        ::= { smsCounters 44 }

    smsCntSriSmTimeoutCounter OBJECT-TYPE
        SYNTAX  Counter
        ACCESS  read-write
        STATUS  mandatory
        DESCRIPTION
            "Counter specifying the number of times that issueing a
            Send-Routing- Info-For-SM operation resulted in a timeout."
        ::= { smsCounters 45 }

    smsCntSriSmSysFailErrorCounter OBJECT-TYPE
        SYNTAX  Counter
        ACCESS  read-write
        STATUS  mandatory
        DESCRIPTION
            "Counter specifying the number of times that issueing a
            Send-Routing- Info-For-SM operation resulted in a System-Failure
            error."
        ::= { smsCounters 46 }

    smsCntSriSmDataMisErrorCounter OBJECT-TYPE
        SYNTAX  Counter
        ACCESS  read-write
        STATUS  mandatory
        DESCRIPTION
            "Counter specifying the number of times that issueing a
            Send-Routing- Info-For-SM operation resulted in a Data-Missing
            error."
        ::= { smsCounters 47 }

    smsCntSriSmUnexpDataValErrorCounter OBJECT-TYPE
        SYNTAX  Counter
        ACCESS  read-write
        STATUS  mandatory
        DESCRIPTION
            "Counter specifying the number of times that issueing a
            Send-Routing- Info-For-SM operation resulted in a
            Unexpected-Data-Value error."
        ::= { smsCounters 48 }

    smsCntSriSmFacNotSuppErrorCounter OBJECT-TYPE
        SYNTAX  Counter
        ACCESS  read-write
        STATUS  mandatory
        DESCRIPTION
            "Counter specifying the number of times that issueing a
            Send-Routing- Info-For-SM operation resulted in a
            Facility-Not-Supported error."
        ::= { smsCounters 49 }

    smsCntSriSmUnkSubErrorCounter OBJECT-TYPE
        SYNTAX  Counter
        ACCESS  read-write
        STATUS  mandatory
        DESCRIPTION
            "Counter specifying the number of times that issueing a
            Send-Routing- Info-For-SM operation resulted in a
            Unknown-Subscriber error."
        ::= { smsCounters 50 }

    smsCntSriSmAbsSubErrorCounter OBJECT-TYPE
        SYNTAX  Counter
        ACCESS  read-write
        STATUS  mandatory
        DESCRIPTION
            "Counter specifying the number of times that issueing a
            Send-Routing- Info-For-SM operation resulted in a
            Absent-Subscriber error."
        ::= { smsCounters 51 }

    smsCntSriSmCallBarredErrorCounter OBJECT-TYPE
        SYNTAX  Counter
        ACCESS  read-write
        STATUS  mandatory
        DESCRIPTION
            "Counter specifying the number of times that issueing a
            Send-Routing- Info-For-SM operation resulted in a Call-Barred
            error."
        ::= { smsCounters 52 }

    smsCntSriSmTeleServNotProvErrorCounter OBJECT-TYPE
        SYNTAX  Counter
        ACCESS  read-write
        STATUS  mandatory
        DESCRIPTION
            "Counter specifying the number of times that issueing a
            Send-Routing- Info-For-SM operation resulted in a
            Teleservice-Not-Provisioned error."
        ::= { smsCounters 53 }

    smsCntSriSmOtherErrorsCounter OBJECT-TYPE
        SYNTAX  Counter
        ACCESS  read-write
        STATUS  mandatory
        DESCRIPTION
            "Counter specifying the number of times that issueing a
            Send-Routing-Info-For-SM operation resulted in another error than
            specified for the other Send-Routing-Info-For-SM counters."
        ::= { smsCounters 54 }

    smsCntSriSmTcapAbortedCounter OBJECT-TYPE
        SYNTAX  Counter
        ACCESS  read-write
        STATUS  mandatory
        DESCRIPTION
            "Counter specifying the number of times that issueing a
            Send-Routing- Info-For-SM operation resulted in the HLR rejecting
            the operation by sending a TC-ABORT on TCAP level."
        ::= { smsCounters 55 }

    smsCntSriSmSccpAbortedCounter OBJECT-TYPE
        SYNTAX  Counter
        ACCESS  read-write
        STATUS  mandatory
        DESCRIPTION
            "Counter specifying the number of times that issueing a
            Send-Routing- Info-For-SM operation resulted in the HLR rejecting
            the operation by sending a UDTS on SCCP level."
        ::= { smsCounters 56 }

    smsCntSriSmFallbackToVersion2Counter OBJECT-TYPE
        SYNTAX  Counter
        ACCESS  read-write
        STATUS  mandatory
        DESCRIPTION
            "Counter specifying the number of times that issueing a
            Send-Routing- Info-For-SM operation resulted in the HLR
            requesting to fallback to MAP version 2."
        ::= { smsCounters 57 }

    smsCntSriSmFallbackToVersion1Counter OBJECT-TYPE
        SYNTAX  Counter
        ACCESS  read-write
        STATUS  mandatory
        DESCRIPTION
            "Counter specifying the number of times that issueing a
            Send-Routing- Info-For-SM operation resulted in the HLR
            requesting to fallback to MAP version 1."
        ::= { smsCounters 58 }

    smsCntRepStsTotalCounter OBJECT-TYPE
        SYNTAX  Counter
        ACCESS  read-write
        STATUS  mandatory
        DESCRIPTION
            "Counter specifying the total number of times a Report-SM-
            Delivery-Status operation was issued
            by the TPR. This counter is incremented whenever:
            - the TPR issues a Report-SM-Delivery-Status operation as part of
              the delivery of a MT/SM that was sent by an application that is
              directly connected to the TPR
            - the TPR receives all Report-SM-Delivery-Status operations from
              an SMSC and directs the opeation to its destination."
        ::= { smsCounters 59 }

    smsCntRepStsSuccessCounter OBJECT-TYPE
        SYNTAX  Counter
        ACCESS  read-write
        STATUS  mandatory
        DESCRIPTION
            "Counter specifying the number of times a Report-SM-Delivery-
            Status operation was successfully issued."
        ::= { smsCounters 60 }

    smsCntRepStsTimeoutCounter OBJECT-TYPE
        SYNTAX  Counter
        ACCESS  read-write
        STATUS  mandatory
        DESCRIPTION
            "Counter specifying the number of times that issueing a Report-SM-
            Delivery-Status operation resulted in a timeout."
        ::= { smsCounters 61 }

    smsCntRepStsSysFailErrorCounter OBJECT-TYPE
        SYNTAX  Counter
        ACCESS  read-write
        STATUS  mandatory
        DESCRIPTION
            "Counter specifying the number of times that issueing a Report-SM-
            Delivery-Status operation resulted in a System-Failure error."
        ::= { smsCounters 62 }

    smsCntRepStsDataMisErrorCounter OBJECT-TYPE
        SYNTAX  Counter
        ACCESS  read-write
        STATUS  mandatory
        DESCRIPTION
            "Counter specifying the number of times that issueing a Report-SM-
            Delivery-Status operation resulted in a Data-Missing error."
        ::= { smsCounters 63 }

    smsCntRepStsUnexpDataValErrorCounter OBJECT-TYPE
        SYNTAX  Counter
        ACCESS  read-write
        STATUS  mandatory
        DESCRIPTION
            "Counter specifying the number of times that issueing a Report-SM-
            Delivery-Status operation resulted in a Unexpected-Data-Value
            error."
        ::= { smsCounters 64 }

    smsCntRepStsUnkSubErrorCounter OBJECT-TYPE
        SYNTAX  Counter
        ACCESS  read-write
        STATUS  mandatory
        DESCRIPTION
           "Counter specifying the number of times that issueing a Report-SM-
            Delivery-Status operation resulted in a Unknown-Subscriber
            error."
        ::= { smsCounters 65 }

    smsCntRepStsMsgWaitListFullErrorCounter OBJECT-TYPE
        SYNTAX  Counter
        ACCESS  read-write
        STATUS  mandatory
        DESCRIPTION
           "Counter specifying the number of times that issueing a Report-SM-
            Delivery-Status operation resulted in a Message-Waiting-List-Full
            error."
        ::= { smsCounters 66 }

    smsCntRepStsOtherErrorsCounter OBJECT-TYPE
        SYNTAX  Counter
        ACCESS  read-write
        STATUS  mandatory
        DESCRIPTION
            "Counter specifying the number of times that issueing a
            Report-SM- Delivery-Status operation resulted in in another error
            than specified for the other Report-SM-Delivery-Status counters."
        ::= { smsCounters 67 }

    smsCntRepStsTcapAbortedCounter OBJECT-TYPE
        SYNTAX  Counter
        ACCESS  read-write
        STATUS  mandatory
        DESCRIPTION
            "Counter specifying the number of times that issueing a Report-SM-
            Delivery-Status operation resulted in the HLR rejecting the
            operation by sending a TC-ABORT on TCAP level."
        ::= { smsCounters 68 }

    smsCntRepStsSccpAbortedCounter OBJECT-TYPE
        SYNTAX  Counter
        ACCESS  read-write
        STATUS  mandatory
        DESCRIPTION
            "Counter specifying the number of times that issueing a Report-SM-
            Delivery-Status operation resulted in the HLR rejecting the
            operation by sending a UDTS on SCCP level."
        ::= { smsCounters 69 }

    smsCntRepStsFallbackToVersion2Counter OBJECT-TYPE
        SYNTAX  Counter
        ACCESS  read-write
        STATUS  mandatory
        DESCRIPTION
            "Counter specifying the number of times that issueing a Report-SM-
            Delivery-Status operation resulted in the HLR requesting to
            fallback to MAP version 2."
        ::= { smsCounters 70 }

    smsCntRepStsFallbackToVersion1Counter OBJECT-TYPE
        SYNTAX  Counter
        ACCESS  read-write
        STATUS  mandatory
        DESCRIPTION
            "Counter specifying the number of times that issueing a Report-SM-
            Delivery-Status operation resulted in the HLR requesting to
            fallback to MAP version 1."
        ::= { smsCounters 71 }

    smsCntAltScTotalCounter OBJECT-TYPE
        SYNTAX  Counter
        ACCESS  read-write
        STATUS  mandatory
        DESCRIPTION
            "Counter specifying the total number of times a Alert-Service-
            Centre operation was issued by the TPR. This counter is
            incremented whenever the TPR issues a Alert-Service-Centre
            operation towards an SMSC."
        ::= { smsCounters 72 }

    smsCntAltScSuccessCounter OBJECT-TYPE
        SYNTAX  Counter
        ACCESS  read-write
        STATUS  mandatory
        DESCRIPTION
            "Counter specifying the number of times a Alert-Service-Centre
            operation was successfully issued."
        ::= { smsCounters 73 }

    smsCntAltScTimeoutCounter OBJECT-TYPE
        SYNTAX  Counter
        ACCESS  read-write
        STATUS  mandatory
        DESCRIPTION
            "Counter specifying the number of times that issueing a Alert-
            Service-Centre operation resulted in a timeout."
        ::= { smsCounters 74 }

    smsCntAltScSysFailErrorCounter OBJECT-TYPE
        SYNTAX  Counter
        ACCESS  read-write
        STATUS  mandatory
        DESCRIPTION
            "Counter specifying the number of times that issueing a Alert-
            Service-Centre operation resulted in a System-Failure error."
        ::= { smsCounters 75 }

    smsCntAltScDataMisErrorCounter OBJECT-TYPE
        SYNTAX  Counter
        ACCESS  read-write
        STATUS  mandatory
        DESCRIPTION
            "Counter specifying the number of times that issueing a Alert
            Service-Centre operation resulted in a Data-Missing error."
        ::= { smsCounters 76 }

    smsCntAltScUnexpDataValErrorCounter OBJECT-TYPE
        SYNTAX  Counter
        ACCESS  read-write
        STATUS  mandatory
        DESCRIPTION
            "Counter specifying the number of times that issueing a Alert-
            Service-Centre operation resulted in a Unexpected-Data-Value
            error."
        ::= { smsCounters 77 }

    smsCntAltScOtherErrorsCounter OBJECT-TYPE
        SYNTAX  Counter
        ACCESS  read-write
        STATUS  mandatory
        DESCRIPTION
            "Counter specifying the number of times that issueing a Alert-
            Service-Centre operation resulted in another error than specified
            for the other Alert-Service-Centre counters."
        ::= { smsCounters 78 }

    smsCntAltScTcapAbortedCounter OBJECT-TYPE
        SYNTAX  Counter
        ACCESS  read-write
        STATUS  mandatory
        DESCRIPTION
            "Counter specifying the number of times that issueing a Alert-
            Service-Centre operation resulted in the HLR rejecting the
            operation by sending a TC-ABORT on TCAP level."
        ::= { smsCounters 79 }

    smsCntAltScSccpAbortedCounter OBJECT-TYPE
        SYNTAX  Counter
        ACCESS  read-write
        STATUS  mandatory
        DESCRIPTION
            "Counter specifying the number of times that issueing a Alert-
            Service-Centre operation resulted in the HLR rejecting the
            operation by sending a UDTS on SCCP level."
        ::= { smsCounters 80 }

    smsCntMoDiscardWithNoResponseCounter OBJECT-TYPE
        SYNTAX  Counter
        ACCESS  read-write
        STATUS  mandatory
        DESCRIPTION
            "Counter specifying the number of times that TPR has rejected an
            MO/SM as result of a routing rule with action equal to
            discardWithNoResponse."
        ::= { smsCounters 81 }

    smsCntRecvSriSmRespPassedCounter OBJECT-TYPE
        SYNTAX  Counter
        ACCESS  read-write
        STATUS  mandatory
        DESCRIPTION
            "Counter specifying the number of times that TextPass received an
             response for an inbound Send-Routing-Info-For-SM operation and 
             relayed it to the invoking SMSC."
        ::= { smsCounters 91 }

    smsCntRecvSriSmRespBlockedWithPermanentErrorCounter OBJECT-TYPE
        SYNTAX  Counter
        ACCESS  read-write
        STATUS  mandatory
        DESCRIPTION
            "Counter specifying the number of times that TextPass rejected a
             response to an inbound Send-Routing-Info-For-SM operation and 
             returned a permanent error to the invoking SMSC."
        ::= { smsCounters 92 }

    smsCntRecvSriSmRespBlockedWithTemporaryErrorCounter OBJECT-TYPE
        SYNTAX  Counter
        ACCESS  read-write
        STATUS  mandatory
        DESCRIPTION
            "Counter specifying the number of times that TextPass rejected a 
             response to an inbound Send-Routing-Info-For-SM operation and 
             returned a temporary error to the invoking SMSC."
        ::= { smsCounters 93 }

    smsCntRecvSriSmRespBlockedWithNoResponseCounter OBJECT-TYPE
        SYNTAX  Counter
        ACCESS  read-write
        STATUS  mandatory
        DESCRIPTION
            "Counter specifying the number of times that TextPass rejected a
             response to an inbound Send-Routing-Info-For-SM operation and 
             did not return anything to the invoking SMSC."
        ::= { smsCounters 94 }

    smsCntRecvSriSmRespReleasedCounter OBJECT-TYPE
        SYNTAX  Counter
        ACCESS  read-write
        STATUS  mandatory
        DESCRIPTION
            "Counter specifying the number of times that TextPass released a
             response to an inbound Send-Routing-Info-For-SM operation."
        ::= { smsCounters 96 }

    smsCntRecvSriSmPassedCounter OBJECT-TYPE
        SYNTAX  Counter
        ACCESS  read-write
        STATUS  mandatory
        DESCRIPTION
            "Counter specifying the number of times that TextPass accepted an
             inbound Send-Routing-Info-For-SM operation and relayed it to an
             HLR on behalf of the invoking SMSC."
        ::= { smsCounters 101 }

    smsCntRecvSriSmBlockedWithPermanentErrorCounter OBJECT-TYPE
        SYNTAX  Counter
        ACCESS  read-write
        STATUS  mandatory
        DESCRIPTION
            "Counter specifying the number of times that TextPass rejected an
            inbound Send-Routing-Info-For-SM operation and returned a
            permanent error to the invoking SMSC."
        ::= { smsCounters 102 }

    smsCntRecvSriSmBlockedWithTemporaryErrorCounter OBJECT-TYPE
        SYNTAX  Counter
        ACCESS  read-write
        STATUS  mandatory
        DESCRIPTION
            "Counter specifying the number of times that TextPass rejected an
            inbound Send-Routing-Info-For-SM operation and returned a
            temporary error to the invoking SMSC."
        ::= { smsCounters 103 }

    smsCntRecvSriSmBlockedWithNoResponseCounter OBJECT-TYPE
        SYNTAX  Counter
        ACCESS  read-write
        STATUS  mandatory
        DESCRIPTION
            "Counter specifying the number of times that TextPass rejected an
             inbound Send-Routing-Info-For-SM operation and did not return
             anything to the invoking SMSC."
        ::= { smsCounters 104 }

    smsCntRecvSriSmReleasedCounter OBJECT-TYPE
        SYNTAX  Counter
        ACCESS  read-write
        STATUS  mandatory
        DESCRIPTION
            "Counter specifying the number of times that TextPass released an 
            inbound Send-Routing-Info-For-SM operation."
        ::= { smsCounters 106 }

    smsCntRecvMtPassedCounter OBJECT-TYPE
        SYNTAX  Counter
        ACCESS  read-write
        STATUS  mandatory
        DESCRIPTION
            "Counter specifying the number of times that TextPass accepted an
             inbound MT-Forward-SM operation and relayed it to an MSC/SGSN on
             behalf of the invoking SMSC."
        ::= { smsCounters 111 }

    smsCntRecvMtBlockedWithPermanentErrorCounter OBJECT-TYPE
        SYNTAX  Counter
        ACCESS  read-write
        STATUS  mandatory
        DESCRIPTION
            "Counter specifying the number of times that TextPass rejected an
             inbound MT-Forward-SM operation and returned a permanent error to
             the invoking SMSC."
        ::= { smsCounters 112 }

    smsCntRecvMtBlockedWithTemporaryErrorCounter OBJECT-TYPE
        SYNTAX  Counter
        ACCESS  read-write
        STATUS  mandatory
        DESCRIPTION
            "Counter specifying the number of times that TextPass rejected an
             inbound MT-Forward-SM operation and returned a temporary error to
             the invoking SMSC."
        ::= { smsCounters 113 }

    smsCntRecvMtBlockedWithNoResponseCounter OBJECT-TYPE
        SYNTAX  Counter
        ACCESS  read-write
        STATUS  mandatory
        DESCRIPTION
            "Counter specifying the number of times that TextPass rejected an
            inbound MT-Forward-SM operation and did not return anything to
            the invoking SMSC."
        ::= { smsCounters 114 }

    smsCntRecvMtBlockedWithAckCounter OBJECT-TYPE
        SYNTAX  Counter
        ACCESS  read-write
        STATUS  mandatory
        DESCRIPTION
            "Counter specifying the number of times that TextPass rejected an
             inbound MT-Forward-SM operation, but did a positive response to
             the invoking SMSC."
        ::= { smsCounters 115 }

    smsCntRecvMtReleasedCounter OBJECT-TYPE
        SYNTAX  Counter
        ACCESS  read-write
        STATUS  mandatory
        DESCRIPTION
            "Counter specifying the number of times that TextPass released an
             inbound MT-Forward-SM operation."
        ::= { smsCounters 116 }

    smsCntRecvSriSmInvalidSccpSmscAddressCounter OBJECT-TYPE
        SYNTAX  Counter
        ACCESS  read-write
        STATUS  mandatory
        DESCRIPTION
            "Counter specifying the number of times that TextPass received an
             inbound Send-Routing-Info-For-SM operation with an invalid SMSC
             address at SCCP layer."
        ::= { smsCounters 121 }

    smsCntRecvSriSmInvalidMapSmscAddressCounter OBJECT-TYPE
        SYNTAX  Counter
        ACCESS  read-write
        STATUS  mandatory
        DESCRIPTION
            "Counter specifying the number of times that TextPass received an
             inbound Send-Routing-Info-For-SM operation with an invalid SMSC
             address at MAP layer."
        ::= { smsCounters 122 }

    smsCntRecvSriSmInvalidRecipientAddressCounter OBJECT-TYPE
        SYNTAX  Counter
        ACCESS  read-write
        STATUS  mandatory
        DESCRIPTION
            "Counter specifying the number of times that TextPass received an
             inbound Send-Routing-Info-For-SM operation with an invalid
             recipient address."
        ::= { smsCounters 123 }

    smsCntRecvSriSmInvalidOriginatorAddressCounter OBJECT-TYPE
        SYNTAX  Counter
        ACCESS  read-write
        STATUS  mandatory
        DESCRIPTION
            "Counter specifying the number of times that TextPass received an
             inbound Send-Routing-Info-For-SM operation with an invalid
             originator address."
        ::= { smsCounters 124 }

    smsCntRecvSriSmUnknownSccpSmscAddressCounter OBJECT-TYPE
        SYNTAX  Counter
        ACCESS  read-write
        STATUS  mandatory
        DESCRIPTION
            "Counter specifying the number of times that TextPass received an
            inbound Send-Routing-Info-For-SM operation with an SMSC address
            at SCCP layer that could not be associated with any of the
            defined mobile network entities."
        ::= { smsCounters 125 }

    smsCntRecvSriSmUnknownMapSmscAddressCounter OBJECT-TYPE
        SYNTAX  Counter
        ACCESS  read-write
        STATUS  mandatory
        DESCRIPTION
            "Counter specifying the number of times that TextPass received an
             inbound Send-Routing-Info-For-SM operation with an SMSC address
             at MAP layer that could not be associated with any of the defined
             mobile network entities."
        ::= { smsCounters 126 }

    smsCntRecvSriSmConflictingSmscAddressCounter OBJECT-TYPE
        SYNTAX  Counter
        ACCESS  read-write
        STATUS  mandatory
        DESCRIPTION
            "Counter specifying the number of times that TextPass received an
             inbound Send-Routing-Info-For-SM operation with conflicting SMSC
             addresses at SCCP layer and MAP layer. These addresses conflict
             when they are from:
             - different countries (determined on the basis of the country
               code)
             - different mobile networks (determined by associating the
               addresses with a mobile network)."
        ::= { smsCounters 127 }

    smsCntRecvSriSmMatchingMtRoutingRuleCounter OBJECT-TYPE
        SYNTAX  Counter
        ACCESS  read-write
        STATUS  mandatory
        DESCRIPTION
            "Counter specifying the number of times that TextPass received an
             inbound Send-Routing-Info-For-SM operation that matches an MT
             routing rule."
        ::= { smsCounters 128 }

    smsCntRecvSriSmMatchingMtExtConditionRuleCounter OBJECT-TYPE
        SYNTAX  Counter
        ACCESS  read-write
        STATUS  mandatory
        DESCRIPTION
            "Counter specifying the number of times that TextPass received an
             inbound Send-Routing-Info-For-SM operation that matches an MT
             external condition rule."
        ::= { smsCounters 129 }

    smsCntRecvSriSmRespMatchingMtRoutingRuleCounter OBJECT-TYPE
        SYNTAX  Counter
        ACCESS  read-write
        STATUS  mandatory
        DESCRIPTION
            "Counter specifying the number of times that TextPass received a
             response to an inbound Send-Routing-Info-For-SM operation that 
             matches an MT routing rule."
        ::= { smsCounters 130 }

    smsCntRecvSriSmRespMatchingMtExtConditionRuleCounter OBJECT-TYPE
        SYNTAX  Counter
        ACCESS  read-write
        STATUS  mandatory
        DESCRIPTION
            "Counter specifying the number of times that TextPass received a
            response to an inbound Send-Routing-Info-For-SM operation that 
            matches an MT external condition rule."
        ::= { smsCounters 131 }

    smsCntRecvMtInvalidSccpSmscAddressCounter OBJECT-TYPE
        SYNTAX  Counter
        ACCESS  read-write
        STATUS  mandatory
        DESCRIPTION
            "Counter specifying the number of times that TextPass received an
             inbound MT-Forward-SM operation with an invalid SMSC address at
             SCCP layer."
        ::= { smsCounters 141 }

    smsCntRecvMtInvalidMapSmscAddressCounter OBJECT-TYPE
        SYNTAX  Counter
        ACCESS  read-write
        STATUS  mandatory
        DESCRIPTION
            "Counter specifying the number of times that TextPass received an
             inbound MT-Forward-SM operation with an invalid SMSC address at
             MAP layer."
        ::= { smsCounters 142 }

    smsCntRecvMtInvalidOriginatorAddressCounter OBJECT-TYPE
        SYNTAX  Counter
        ACCESS  read-write
        STATUS  mandatory
        DESCRIPTION
            "Counter specifying the number of times that TextPass received an
             inbound MT-Forward-SM operation with an invalid originator
             address."
        ::= { smsCounters 143 }

    smsCntRecvMtInvalidImsiCounter OBJECT-TYPE
        SYNTAX  Counter
        ACCESS  read-write
        STATUS  mandatory
        DESCRIPTION
            "Counter specifying the number of times that TextPass received an
             inbound MT-Forward-SM operation with an invalid IMSI."
        ::= { smsCounters 144 }

    smsCntRecvMtInvalidMscOrSgsnAddressCounter OBJECT-TYPE
        SYNTAX  Counter
        ACCESS  read-write
        STATUS  mandatory
        DESCRIPTION
            "Counter specifying the number of times that TextPass received an
             inbound MT-Forward-SM operation with an invalid MSC address or
             SGSN address."
        ::= { smsCounters 145 }

    smsCntRecvMtUnknownSccpSmscAddressCounter OBJECT-TYPE
        SYNTAX  Counter
        ACCESS  read-write
        STATUS  mandatory
        DESCRIPTION
            "Counter specifying the number of times that TextPass received an
             inbound MT-Forward-SM operation with an SMSC address at SCCP
             layer that could not be associated with any of the defined mobile
             network entities."
        ::= { smsCounters 146 }

    smsCntRecvMtUnknownMapSmscAddressCounter OBJECT-TYPE
        SYNTAX  Counter
        ACCESS  read-write
        STATUS  mandatory
        DESCRIPTION
            "Counter specifying the number of times that TextPass received an
             inbound MT-Forward-SM operation with an SMSC address at MAP
             layer that could not be associated with any of the defined mobile
             network entities."
        ::= { smsCounters 147 }

    smsCntRecvMtConflictingSmscAddressCounter OBJECT-TYPE
        SYNTAX  Counter
        ACCESS  read-write
        STATUS  mandatory
        DESCRIPTION
            "Counter specifying the number of times that TextPass received an
             inbound MT-Forward-SM operation with:
             - conflicting SMSC addresses at SCCP layer and MAP layer
             - different SMSC addresses at SCCP layer used amongst the various
               TCAP messages of a segmented TCAP dialogue
             SMSC addresses at SCCP layer and MAP layer conflict when they are
             from:
               - different countries (determined on the basis of the country
                 code), or
               - different mobile networks (determined by associating the
                 addresses with a mobile network)."
        ::= { smsCounters 148 }

    smsCntRecvMtSpoofedSccpSmscAddressCounter OBJECT-TYPE
        SYNTAX  Counter
        ACCESS  read-write
        STATUS  mandatory
        DESCRIPTION
            "Counter specifying the number of times that TextPass received an
            inbound MT-Forward-SM operation with spoofing of the SMSC address
            at SCCP level, i.e. using an SMSC address at SCCP level for
            MT-Forward-SM that conflicts with address used in relating Send-
            Routing-Info-For-SM operation. A conflict exist when the
            addresses are from:
               - different countries (determined on the basis of the country
                 code), or
               - different mobile networks (determined by associating the
                 addresses with a mobile network)."
        ::= { smsCounters 149 }

    smsCntRecvMtSpoofedMapSmscAddressCounter OBJECT-TYPE
        SYNTAX  Counter
        ACCESS  read-write
        STATUS  mandatory
        DESCRIPTION
            "Counter specifying the number of times that TextPass received an
            inbound MT-Forward-SM operation with spoofing of the SMSC address
            at MAP level, i.e. using an SMSC address at MAP level for
            MT-Forward-SM that conflicts with address used in relating Send-
            Routing-Info-For-SM operation. A conflict exist when the
            addresses are from:
               - different countries (determined on the basis of the country
                 code), or
               - different mobile networks (determined by associating the
                 addresses with a mobile network)."
        ::= { smsCounters 150 }

    smsCntRecvMtWithoutPrecedingSriSmCounter OBJECT-TYPE
        SYNTAX  Counter
        ACCESS  read-write
        STATUS  mandatory
        DESCRIPTION
            "Counter specifying the number of times that TextPass received an
             inbound MT-Forward-SM operation pertaining to a subscriber of the
             operator's network that could not be related with a previously
             received Send-Routing-Info-For-SM operation."
        ::= { smsCounters 151 }

    smsCntRecvMtForgedMscOrSgsnAddressCounter OBJECT-TYPE
        SYNTAX  Counter
        ACCESS  read-write
        STATUS  mandatory
        DESCRIPTION

            "Counter specifying the number of times that TextPass received an
             inbound MT-Forward-SM operation with a forged MSC address or
             SGSN address."
        ::= { smsCounters 152 }

    smsCntRecvMtForgedImsiCounter OBJECT-TYPE
        SYNTAX  Counter
        ACCESS  read-write
        STATUS  mandatory
        DESCRIPTION
            "Counter specifying the number of times that TextPass received an
             inbound MT-Forward-SM operation with a forged IMSI."
        ::= { smsCounters 153 }

    smsCntRecvMtForgedLmsiCounter OBJECT-TYPE
        SYNTAX  Counter
        ACCESS  read-write
        STATUS  mandatory
        DESCRIPTION
            "Counter specifying the number of times that TextPass received an
             inbound MT-Forward-SM operation with a forged LMSI."
        ::= { smsCounters 154 }

    smsCntRecvMtMatchingMtRoutingRuleCounter OBJECT-TYPE
        SYNTAX  Counter
        ACCESS  read-write
        STATUS  mandatory
        DESCRIPTION
            "Counter specifying the number of times that TextPass received an
             inbound MT-Forward-SM operation that matches an MT routing rule."
        ::= { smsCounters 155 }

    smsCntRecvMtMatchingMtExtConditionRuleCounter OBJECT-TYPE
        SYNTAX  Counter
        ACCESS  read-write
        STATUS  mandatory
        DESCRIPTION
            "Counter specifying the number of times that TextPass received an
             inbound MT-Forward-SM  operation that matches an MT external
             condition rule."
        ::= { smsCounters 156 }

    smsCntRecvMtMatchingWhiteListedImsiCounter OBJECT-TYPE
        SYNTAX  Counter
        ACCESS  read-write
        STATUS  mandatory
        DESCRIPTION
            "Counter specifying the number of times that TextPass received an
             inbound MT-Forward-SM  operation that matches a whitelisted
             prefix from fwPropNoSpoofCheckWhiteListedRecipientImsi."
        ::= { smsCounters 157 }

    smsCntRecvMoSpoofedOriginatorAddressCounter OBJECT-TYPE
        SYNTAX  Counter
        ACCESS  read-write
        STATUS  mandatory
        DESCRIPTION
            "Counter specifying the number of times that TextPass received an
             inbound MO-Forward-SM operation with spoofing of the originator
             address."
        ::= { smsCounters 191 }

    smsCntRecvRogueTcapContinueCounter OBJECT-TYPE
        SYNTAX  Counter
        ACCESS  read-write
        STATUS  mandatory
        DESCRIPTION
            "Counter specifying the number of times that TextPass received an
             TCAP Continue message that had no corresponding previous dialog
             and contained components other than Invoke."
        ::= { smsCounters 192 }

    smsCntRecvRogueTcapEndCounter OBJECT-TYPE
        SYNTAX  Counter
        ACCESS  read-write
        STATUS  mandatory
        DESCRIPTION
            "Counter specifying the number of times that TextPass received an
             TCAP End message that had no corresponding previous dialog."
        ::= { smsCounters 193 }

    smsCntRecvRogueTcapContinueUnknownCountryCounter OBJECT-TYPE
        SYNTAX  Counter
        ACCESS  read-write
        STATUS  mandatory
        DESCRIPTION
            "Counter specifying the number of times that TextPass received an
             TCAP Continue message that had no corresponding previous dialog
             and contained components other than Invoke. Only counts from
             origins where the country could not be identified are included."
        ::= { smsCounters 194 }

    smsCntRecvRogueTcapEndUnknownCountryCounter OBJECT-TYPE
        SYNTAX  Counter
        ACCESS  read-write
        STATUS  mandatory
        DESCRIPTION
            "Counter specifying the number of times that TextPass received an
             TCAP End message that had no corresponding previous dialog.
             Only counts from origins where the country could not be
             identified are included."
        ::= { smsCounters 195 }

    smsCntRecvRogueTcapContinueUnknownNetworkCounter OBJECT-TYPE
        SYNTAX  Counter
        ACCESS  read-write
        STATUS  mandatory
        DESCRIPTION
            "Counter specifying the number of times that TextPass received an
             TCAP Continue message that had no corresponding previous dialog
             and contained components other than Invoke. Only counts from
             origins where the network could not be identified are included."
        ::= { smsCounters 196 }

    smsCntRecvRogueTcapEndUnknownNetworkCounter OBJECT-TYPE
        SYNTAX  Counter
        ACCESS  read-write
        STATUS  mandatory
        DESCRIPTION
            "Counter specifying the number of times that TextPass received an
             TCAP End message that had no corresponding previous dialog.
             Only counts from origins where the network could not be
             identified are included."
        ::= { smsCounters 197 }

    smsCntRecvMoFwdSmCounter OBJECT-TYPE
        SYNTAX  Counter
        ACCESS  read-write
        STATUS  mandatory
        DESCRIPTION
            "Counter specifying the number of MO-Forward-SM operations
            received."
        ::= { smsCounters 201 }

    smsCntSentMoFwdSmCounter OBJECT-TYPE
        SYNTAX  Counter
        ACCESS  read-write
        STATUS  mandatory
        DESCRIPTION
            "Counter specifying the number of MO-Forward-SM operations sent."
        ::= { smsCounters 202 }

    smsCntRecvMtFwdSmCounter OBJECT-TYPE
        SYNTAX  Counter
        ACCESS  read-write
        STATUS  mandatory
        DESCRIPTION
            "Counter specifying the number of MT-Forward-SM operations
            received."
        ::= { smsCounters 203 }

    smsCntSentMtFwdSmCounter OBJECT-TYPE
        SYNTAX  Counter
        ACCESS  read-write
        STATUS  mandatory
        DESCRIPTION
            "Counter specifying the number of MT-Forward-SM operations sent."
        ::= { smsCounters 204 }

    smsCntRecvSriSmCounter OBJECT-TYPE
        SYNTAX  Counter
        ACCESS  read-write
        STATUS  mandatory
        DESCRIPTION
            "Counter specifying the number of Send-Routing-Info-For-SM
            operations received."
        ::= { smsCounters 205 }

    smsCntSentSriSmCounter OBJECT-TYPE
        SYNTAX  Counter
        ACCESS  read-write
        STATUS  mandatory
        DESCRIPTION
            "Counter specifying the number of Send-Routing-Info-For-SM
            operations sent."
        ::= { smsCounters 206 }

    smsCntRecvInfScCounter OBJECT-TYPE
        SYNTAX  Counter
        ACCESS  read-write
        STATUS  mandatory
        DESCRIPTION
            "Counter specifying the number of Inform-Service-Centre
            operations received."
        ::= { smsCounters 207 }

    smsCntSentInfScCounter OBJECT-TYPE
        SYNTAX  Counter
        ACCESS  read-write
        STATUS  mandatory
        DESCRIPTION
            "Counter specifying the number of Inform-Service-Centre
            operations sent."
        ::= { smsCounters 208 }

    smsCntRecvRepStsCounter OBJECT-TYPE
        SYNTAX  Counter
        ACCESS  read-write
        STATUS  mandatory
        DESCRIPTION
            "Counter specifying the number of Report-SM-Delivery-Status
            operations received."
        ::= { smsCounters 209 }

    smsCntSentRepStsCounter OBJECT-TYPE
        SYNTAX  Counter
        ACCESS  read-write
        STATUS  mandatory
        DESCRIPTION
            "Counter specifying the number of Report-SM-Delivery-Status
            operations sent."
        ::= { smsCounters 210 }

    smsCntRecvAltScCounter OBJECT-TYPE
        SYNTAX  Counter
        ACCESS  read-write
        STATUS  mandatory
        DESCRIPTION
            "Counter specifying the number of Alert-Service-Centre operations
            received."
        ::= { smsCounters 211 }

    smsCntSentAltScCounter OBJECT-TYPE
        SYNTAX  Counter
        ACCESS  read-write
        STATUS  mandatory
        DESCRIPTION
            "Counter specifying the number of Alert-Service-Centre operations
            sent."
        ::= { smsCounters 212 }

    smsCntRecvMoFwdSmWithoutStatusReportRequestCounter OBJECT-TYPE
        SYNTAX  Counter
        ACCESS  read-write
        STATUS  mandatory
        DESCRIPTION
            "Counter specifying the number of MO-Forward-SM operations
            received that contained a SMS-SUBMIT or SMS-COMMAND that
            requested for a status report."
        ::= { smsCounters 301 }

    smsCntRecvMoFwdSmWithPhase1StatusReportRequestCounter OBJECT-TYPE
        SYNTAX  Counter
        ACCESS  read-write
        STATUS  mandatory
        DESCRIPTION
            "Counter specifying the number of MO-Forward-SM operations
            received that contained a SMS-SUBMIT that requested for a phase 1
            status report. Note that an SMS-COMMAND can not request for a
            phase 1 status report as the only means to specify it is by means
            of a tag in the TP -UD parameter of the SMS-SUBMIT."
        ::= { smsCounters 302 }

    smsCntRecvMoFwdSmWithPhase2StatusReportRequestCounter OBJECT-TYPE
        SYNTAX  Counter
        ACCESS  read-write
        STATUS  mandatory
        DESCRIPTION
            "Counter specifying the number of MO-Forward-SM operations
            received that contained a SMS-SUBMIT or SMS-COMMAND that
            requested for a phase 2/2+ status report. This is done by means
            of the TP-SRR parameter."
        ::= { smsCounters 303 }

    smsCntSentMtFwdSmWithOrdinaryMessageCounter OBJECT-TYPE
        SYNTAX  Counter
        ACCESS  read-write
        STATUS  mandatory
        DESCRIPTION
            "Counter specifying the number of MT-Forward-SM operations sent
            that contained an SMS-DELIVER that did contain an ordinary
            message (i.e.  not a phase 1 status report)."
        ::= { smsCounters 304 }

    smsCntSentMtFwdSmWithPhase1StatusReportCounter OBJECT-TYPE
        SYNTAX  Counter
        ACCESS  read-write
        STATUS  mandatory
        DESCRIPTION
            "Counter specifying the number of MT-Forward-SM operations sent
            that contained an SMS-DELIVER that did contain a phase 1 status
            report."
        ::= { smsCounters 305 }

    smsCntSentMtFwdSmWithPhase2StatusReportCounter OBJECT-TYPE
        SYNTAX  Counter
        ACCESS  read-write
        STATUS  mandatory
        DESCRIPTION
            "Counter specifying the number of MT-Forward-SM operations sent
            that contained an STATUS-REPORT (i.e. a phase 2/2+ status
            report)."
        ::= { smsCounters 306 }

    smsCntPendingStatusReportsForRetryCounter OBJECT-TYPE
        SYNTAX  Gauge
        ACCESS  read-write
        STATUS  mandatory
        DESCRIPTION
            "Counter specifying the number of status reports that are pending 
            for a retry."
        ::= { smsCounters 307 }

    smsCntSentExternalConditionFailureMessagesCounter OBJECT-TYPE
        SYNTAX  Counter
        ACCESS  read-write
        STATUS  mandatory
        DESCRIPTION
            "Counter specifying the number of External Condition failure
            messages generated. This counter is deprecated and will be
            removed in the future."
        ::= { smsCounters 308 }

    smsCntSentExternalConditionMessagesCounter OBJECT-TYPE
        SYNTAX  Counter
        ACCESS  read-write
        STATUS  mandatory
        DESCRIPTION
            "Counter specifying the number of External Condition
            messages generated."
        ::= { smsCounters 309 }

    smsCntMoRejectedDueToLengthChangeOnTransparentForwarding OBJECT-TYPE
        SYNTAX  Counter
        ACCESS  read-write
        STATUS  mandatory
        DESCRIPTION
            "Counter specifying the number of times an MO message that
            should be forwarded transparently could not be due to changes
            to the length of the message, requiring TCAP-segmentation."
        ::= { smsCounters 310 }

    smsCntTransparentForwardingOverriddenForSegmentedMo OBJECT-TYPE
        SYNTAX  Counter
        ACCESS  read-write
        STATUS  mandatory
        DESCRIPTION
            "Counter specifying the number of times an MO message that
            should be forwarded transparently was forwarded untransparently
            because it was TCAP-segmented and the incoming dialog has
            already been terminated on the Router."
        ::= { smsCounters 311 }

    smsCntTransparentForwardingAppliedToMoBeginWithoutComponent OBJECT-TYPE
        SYNTAX  Counter
        ACCESS  read-write
        STATUS  mandatory
        DESCRIPTION
            "Counter specifying the number of times an MO BEGIN without
            component was transparently forwarded due to matching the
            'fwPropMoFwdSmBeginWithoutComponentCdpaList'."
        ::= { smsCounters 312 }

    smsCntInsideAoTotal OBJECT-TYPE
        SYNTAX  Counter
        ACCESS  read-write
        STATUS  mandatory
        DESCRIPTION
            "Counter specifying the total number of times an AO/SM was
            sent towards a service centre."
        ::= { smsCounters 321 }

    smsCntInsideAoSuccess OBJECT-TYPE
        SYNTAX  Counter
        ACCESS  read-write
        STATUS  mandatory
        DESCRIPTION
            "Counter specifying the number of times an AO/SM was
            successfully routed to its destination."
        ::= { smsCounters 322 }

    smsCntInsideAoSourceError OBJECT-TYPE
        SYNTAX  Counter
        ACCESS  read-write
        STATUS  mandatory
        DESCRIPTION
            "Counter specifying the number of times an AO/SM towards
             a service centre resulted in a source error
             (like a syntax error). The error mapping
             table is used to identify a source error. With a correct
             error mapping table it is not possible that this counter
             increases."
        ::= { smsCounters 323 }

    smsCntInsideAoRoutingError OBJECT-TYPE
        SYNTAX  Counter
        ACCESS  read-write
        STATUS  mandatory
        DESCRIPTION
            "Counter specifying the number of times an AO/SM towards
            a service centre resulted in a routing error. The error
            mapping table is used to identify a routing error."
        ::= { smsCounters 324 }

    smsCntInsideAoDestinationTemporaryError OBJECT-TYPE
        SYNTAX  Counter
        ACCESS  read-write
        STATUS  mandatory
        DESCRIPTION
            "Counter specifying the number of times an AO/SM towards
            a service centre resulted in a temporary error. The error
            mapping table is used to identify a temporary error."
        ::= { smsCounters 325 }

    smsCntInsideAoDestinationPermanentRecipientError OBJECT-TYPE
        SYNTAX  Counter
        ACCESS  read-write
        STATUS  mandatory
        DESCRIPTION
            "Counter specifying the number of times an AO/SM towards
            a service centre resulted in a permanent recipient error. 
            The error mapping table is used to identify a permanent 
            recipient error."
        ::= { smsCounters 326 }

    smsCntInsideAoDestinationPermanentMessageError OBJECT-TYPE
        SYNTAX  Counter
        ACCESS  read-write
        STATUS  mandatory
        DESCRIPTION
            "Counter specifying the number of times an AO/SM towards
            a service centre resulted in a permanent message error. The 
            error mapping table is used to identify a permanent message 
            error."
        ::= { smsCounters 327 }

    smsCntInsideAtTotal OBJECT-TYPE
        SYNTAX  Counter
        ACCESS  read-write
        STATUS  mandatory
        DESCRIPTION
            "Counter specifying the total number of times an AT/SM was
            received from a service centre."
        ::= { smsCounters 328 }

    smsCntInsideAtSuccess OBJECT-TYPE
        SYNTAX  Counter
        ACCESS  read-write
        STATUS  mandatory
        DESCRIPTION
            "Counter specifying the number of times an AT/SM was
            successfully routed to its destination."
        ::= { smsCounters 329 }

    smsCntInsideAtSourceError OBJECT-TYPE
        SYNTAX  Counter
        ACCESS  read-write
        STATUS  mandatory
        DESCRIPTION
            "Counter specifying the number of times an AT/SM from
             a service centre resulted in a source error
             (like a syntax error). The error mapping
             table is used to identify a source error."
        ::= { smsCounters 330 }

    smsCntInsideAtRoutingError OBJECT-TYPE
        SYNTAX  Counter
        ACCESS  read-write
        STATUS  mandatory
        DESCRIPTION
            "Counter specifying the number of times an AT/SM from
            a service centre resulted in a routing error. The error
            mapping table is used to identify a routing error."
        ::= { smsCounters 331 }

    smsCntInsideAtDestinationTemporaryError OBJECT-TYPE
        SYNTAX  Counter
        ACCESS  read-write
        STATUS  mandatory
        DESCRIPTION
            "Counter specifying the number of times an AT/SM from
            a service centre resulted in a temporary error. The error
            mapping table is used to identify a temporary error."
        ::= { smsCounters 332 }

    smsCntInsideAtDestinationPermanentRecipientError OBJECT-TYPE
        SYNTAX  Counter
        ACCESS  read-write
        STATUS  mandatory
        DESCRIPTION
            "Counter specifying the number of times an AT/SM from
            a service centre resulted in a permanent recipient error. 
            The error mapping table is used to identify a permanent 
            recipient error."
        ::= { smsCounters 333 }

    smsCntInsideAtDestinationPermanentMessageError OBJECT-TYPE
        SYNTAX  Counter
        ACCESS  read-write
        STATUS  mandatory
        DESCRIPTION
            "Counter specifying the number of times an AT/SM from
            a service centre resulted in a permanent message error. The 
            error mapping table is used to identify a permanent message 
            error."
        ::= { smsCounters 334 }

    smsCntOutsideAoTotal OBJECT-TYPE
        SYNTAX  Counter
        ACCESS  read-write
        STATUS  mandatory
        DESCRIPTION
            "Counter specifying the total number of times an AO/SM was
            received from an application."
        ::= { smsCounters 335 }

    smsCntOutsideAoSuccess OBJECT-TYPE
        SYNTAX  Counter
        ACCESS  read-write
        STATUS  mandatory
        DESCRIPTION
            "Counter specifying the number of times an AO/SM resulted
            in a successful response to the application."
        ::= { smsCounters 336 }

    smsCntOutsideAoSourceError OBJECT-TYPE
        SYNTAX  Counter
        ACCESS  read-write
        STATUS  mandatory
        DESCRIPTION
            "Counter specifying the number of times an AO/SM from
             an application resulted in a source error
             (like a syntax error). The error mapping
             table is used to identify a source error."
        ::= { smsCounters 337 }

    smsCntOutsideAoRoutingError OBJECT-TYPE
        SYNTAX  Counter
        ACCESS  read-write
        STATUS  mandatory
        DESCRIPTION
            "Counter specifying the number of times an AO/SM from
            an application resulted in a routing error. The error
            mapping table is used to identify a routing error."
        ::= { smsCounters 338 }

    smsCntOutsideAoDestinationTemporaryError OBJECT-TYPE
        SYNTAX  Counter
        ACCESS  read-write
        STATUS  mandatory
        DESCRIPTION
            "Counter specifying the number of times an AO/SM from
            an application resulted in a temporary error. The error
            mapping table is used to identify a temporary error."
        ::= { smsCounters 339 }
        
    smsCntOutsideAoDestinationPermanentRecipientError OBJECT-TYPE
        SYNTAX  Counter
        ACCESS  read-write
        STATUS  mandatory
        DESCRIPTION
            "Counter specifying the number of times an AO/SM from
            an application resulted in a permanent recipient error. 
            The error mapping table is used to identify a permanent 
            recipient error."
        ::= { smsCounters 340 }
        
    smsCntOutsideAoDestinationPermanentMessageError OBJECT-TYPE
        SYNTAX  Counter
        ACCESS  read-write
        STATUS  mandatory
        DESCRIPTION
            "Counter specifying the number of times an AO/SM from
            an application resulted in a permanent message error. 
            The error mapping table is used to identify a permanent 
            message error."
        ::= { smsCounters 341 }        

    smsCntOutsideAtTotal OBJECT-TYPE
        SYNTAX  Counter
        ACCESS  read-write
        STATUS  mandatory
        DESCRIPTION
            "Counter specifying the total number of times an AT/SM was
            sent towards an application."
        ::= { smsCounters 342 }

    smsCntOutsideAtSuccess OBJECT-TYPE
        SYNTAX  Counter
        ACCESS  read-write
        STATUS  mandatory
        DESCRIPTION
            "Counter specifying the number of times an AT/SM was
            successfully routed to its destination."
        ::= { smsCounters 343 }

    smsCntOutsideAtSourceError OBJECT-TYPE
        SYNTAX  Counter
        ACCESS  read-write
        STATUS  mandatory
        DESCRIPTION
            "Counter specifying the number of times an AT/SM towards
             an application resulted in a source error
             (like a syntax error). The error mapping
             table is used to identify a source error. With a correct
             error mapping table it is not possible that this counter
             increases."
        ::= { smsCounters 344 }

    smsCntOutsideAtRoutingError OBJECT-TYPE
        SYNTAX  Counter
        ACCESS  read-write
        STATUS  mandatory
        DESCRIPTION
            "Counter specifying the number of times an AT/SM towards
            an application resulted in a routing error. The error
            mapping table is used to identify a routing error."
        ::= { smsCounters 345 }

    smsCntOutsideAtDestinationTemporaryError OBJECT-TYPE
        SYNTAX  Counter
        ACCESS  read-write
        STATUS  mandatory
        DESCRIPTION
            "Counter specifying the number of times an AT/SM towards
            an application resulted in a temporary error. The error
            mapping table is used to identify a temporary error."
        ::= { smsCounters 346 }

    smsCntOutsideAtDestinationPermanentRecipientError OBJECT-TYPE
        SYNTAX  Counter
        ACCESS  read-write
        STATUS  mandatory
        DESCRIPTION
            "Counter specifying the number of times an AT/SM towards
            an application resulted in a permanent recipient error. 
            The error mapping table is used to identify a permanent 
            recipient error."
        ::= { smsCounters 347 }

    smsCntOutsideAtDestinationPermanentMessageError OBJECT-TYPE
        SYNTAX  Counter
        ACCESS  read-write
        STATUS  mandatory
        DESCRIPTION
            "Counter specifying the number of times an AT/SM towards
            an application resulted in a permanent message error. The 
            error mapping table is used to identify a permanent message 
            error."
        ::= { smsCounters 348 }


    smsCntAoMtSuccess OBJECT-TYPE
        SYNTAX  Counter
        ACCESS  read-write
        STATUS  mandatory
        DESCRIPTION
            "Counter specifying the number of times an AO->MT routed
            message was succesfully delivered as MT/SM."
        ::= { smsCounters 400 }

    smsCntAoMtFailure OBJECT-TYPE
        SYNTAX  Counter
        ACCESS  read-write
        STATUS  mandatory
        DESCRIPTION
            "Counter specifying the number of times an AO->MT routed
            message failed to be delivered as MT/SM."
        ::= { smsCounters 401 }

    smsCntAoAoSuccess OBJECT-TYPE
        SYNTAX  Counter
        ACCESS  read-write
        STATUS  mandatory
        DESCRIPTION
            "Counter specifying the number of times an AO->AO routed message
            was succesfully submitted as AO/SM."
        ::= { smsCounters 402 }

    smsCntAoAoFailure OBJECT-TYPE
        SYNTAX  Counter
        ACCESS  read-write
        STATUS  mandatory
        DESCRIPTION
            "Counter specifying the number of times an AO->AO routed message
            failed to be submitted as AO/SM."
        ::= { smsCounters 403 }

    smsCntAtAtSuccess OBJECT-TYPE
        SYNTAX  Counter
        ACCESS  read-write
        STATUS  mandatory
        DESCRIPTION
            "Counter specifying the number of times an AT->AT routed message
            was succesfully delivered as AT/SM."
        ::= { smsCounters 404 }

    smsCntAtAtFailure OBJECT-TYPE
        SYNTAX  Counter
        ACCESS  read-write
        STATUS  mandatory
        DESCRIPTION
            "Counter specifying the number of times an AT->AT routed message
            failed to be delivered as AT/SM."
        ::= { smsCounters 405 }

    smsCntMoMoSuccess OBJECT-TYPE
        SYNTAX  Counter
        ACCESS  read-write
        STATUS  mandatory
        DESCRIPTION
            "Counter specifying the number of times an MO->MO routed message
            was succesfully submitted as MO/SM."
        ::= { smsCounters 406 }

    smsCntMoMoFailure OBJECT-TYPE
        SYNTAX  Counter
        ACCESS  read-write
        STATUS  mandatory
        DESCRIPTION
            "Counter specifying the number of times an MO->MO routed message
            failed to be submitted as MO/SM."
        ::= { smsCounters 407 }

    smsCntMoAoSuccess OBJECT-TYPE
        SYNTAX  Counter
        ACCESS  read-write
        STATUS  mandatory
        DESCRIPTION
            "Counter specifying the number of times an MO->AO routed message
            was succesfully submitted as AO/SM."
        ::= { smsCounters 408 }

    smsCntMoAoFailure OBJECT-TYPE
        SYNTAX  Counter
        ACCESS  read-write
        STATUS  mandatory
        DESCRIPTION
            "Counter specifying the number of times an MO->AO routed message
            failed to be submitted as AO/SM."
        ::= { smsCounters 409 }

    smsCntMoAtSuccess OBJECT-TYPE
        SYNTAX  Counter
        ACCESS  read-write
        STATUS  mandatory
        DESCRIPTION
            "Counter specifying the number of times an MO->AT routed message
            was succesfully delivered as AT/SM."
        ::= { smsCounters 410 }

    smsCntMoAtFailure OBJECT-TYPE
        SYNTAX  Counter
        ACCESS  read-write
        STATUS  mandatory
        DESCRIPTION
            "Counter specifying the number of times an MO->AT routed message
            failed to be delivered as AT/SM."
        ::= { smsCounters 411 }

    smsCntMtMtSuccess OBJECT-TYPE
        SYNTAX  Counter
        ACCESS  read-write
        STATUS  mandatory
        DESCRIPTION
            "Counter specifying the number of times an MT->MT routed message
            was succesfully delivered as MT/SM."
        ::= { smsCounters 412 }

    smsCntMtMtFailure OBJECT-TYPE
        SYNTAX  Counter
        ACCESS  read-write
        STATUS  mandatory
        DESCRIPTION
            "Counter specifying the number of times an MT->MT  routed message
            failed to be delivered as MT/SM."
        ::= { smsCounters 413 }

    smsCntAoDiscard OBJECT-TYPE
        SYNTAX  Counter
        ACCESS  read-write
        STATUS  mandatory
        DESCRIPTION
            "Counter specifying the number of times an AO/SM
            was discarded because of a rule."
        ::= { smsCounters 414 }

    smsCntAtDiscard OBJECT-TYPE
        SYNTAX  Counter
        ACCESS  read-write
        STATUS  mandatory
        DESCRIPTION
            "Counter specifying the number of times an AT/SM
            was discarded because of a rule."
        ::= { smsCounters 415 }

    smsCntMoDiscard OBJECT-TYPE
        SYNTAX  Counter
        ACCESS  read-write
        STATUS  mandatory
        DESCRIPTION
            "Counter specifying the number of times an MO/SM
            was discarded because of a rule."
        ::= { smsCounters 416 }

    smsCntMtDiscard OBJECT-TYPE
        SYNTAX  Counter
        ACCESS  read-write
        STATUS  mandatory
        DESCRIPTION
            "Counter specifying the number of times an MT/SM
            was discarded because of a rule."
        ::= { smsCounters 417 }

    smsCntAoMtAoPrimarySuccess OBJECT-TYPE
        SYNTAX  Counter
        ACCESS  read-write
        STATUS  mandatory
        DESCRIPTION
            "Counter specifying the number of times an AO->MT->AO routed
            message was succesfully delivered as MT/SM."
        ::= { smsCounters 418 }

    smsCntAoMtAoFallbackSuccess OBJECT-TYPE
        SYNTAX  Counter
        ACCESS  read-write
        STATUS  mandatory
        DESCRIPTION
            "Counter specifying the number of times an AO->MT->AO routed
            message was succesfully submitted as AO/SM after a failed first
            delivery attempt as MT/SM."
        ::= { smsCounters 419 }

    smsCntAoMtAoFallbackFailure OBJECT-TYPE
        SYNTAX  Counter
        ACCESS  read-write
        STATUS  mandatory
        DESCRIPTION
            "Counter specifying the number of times an AO->MT->AO routed
            message failed to be submitted as AO/SM after a failed first
            delivery attempt as MT/SM."
        ::= { smsCounters 420 }

    smsCntAoMtAoPrimaryFailure OBJECT-TYPE
        SYNTAX  Counter
        ACCESS  read-write
        STATUS  mandatory
        DESCRIPTION
            "Counter specifying the number of times an AO->MT->AO routed
            message failed to be delivered as MT/SM."
        ::= { smsCounters 421 }
    
    smsCntAoMtAoFallbackNotAppliedDueToPermErrorOnPrimary OBJECT-TYPE
        SYNTAX  Counter
        ACCESS  read-write
        STATUS  mandatory
        DESCRIPTION
            "Counter specifying the number of times an AO->MT->AO routed
            message was not attempted to be submitted as AO/SM because
            the first delivery attempt as MT/SM resulted in an error
            classified as 'permanent'."
        ::= { smsCounters 422 }
    
    smsCntAoMtAoFallbackNotAppliedDueToUnavailability OBJECT-TYPE
        SYNTAX  Counter
        ACCESS  read-write
        STATUS  mandatory
        DESCRIPTION
            "Counter specifying the number of times an AO->MT->AO routed
            message was not attempted to be submitted as AO/SM after a
            failed first delivery attempt as MT/SM, because the service
            centre was unavailable."
        ::= { smsCounters 423 }
    
    smsCntAoMtToAmsSuccess OBJECT-TYPE
        SYNTAX  Counter
        ACCESS  read-write
        STATUS  mandatory
        DESCRIPTION
            "Counter specifying the number of times an AO->AMS(as MT) routed
            message was successfully stored in the AMS."
        ::= { smsCounters 424 }
    
    smsCntAoMtToAmsFailure OBJECT-TYPE
        SYNTAX  Counter
        ACCESS  read-write
        STATUS  mandatory
        DESCRIPTION
            "Counter specifying the number of times an AO->AMS(as MT) routed
            message failed to be stored in the AMS."
        ::= { smsCounters 425 }
    
    smsCntAoMtAmsSuccess OBJECT-TYPE
        SYNTAX  Counter
        ACCESS  read-write
        STATUS  mandatory
        DESCRIPTION
            "Counter specifying the number of times an AO->MT->AMS routed
            message was accepted by the AMS for direct delivery as MT/SM."
        ::= { smsCounters 426 }
    
    smsCntAoMtAmsFailure OBJECT-TYPE
        SYNTAX  Counter
        ACCESS  read-write
        STATUS  mandatory
        DESCRIPTION
            "Counter specifying the number of times an AO->MT->AMS routed
            message failed to be submitted to the AMS for direct delivery
            as MT/SM."
        ::= { smsCounters 427 }

    -- [obsolete AO->MT->AMS counters]
    
    smsCntMoMtToAmsSuccess OBJECT-TYPE
        SYNTAX  Counter
        ACCESS  read-write
        STATUS  mandatory
        DESCRIPTION
            "Counter specifying the number of times an MO->AMS(as MT)
            routed message was successfully stored in the AMS."
        ::= { smsCounters 432 }
    
    smsCntMoMtToAmsFailure OBJECT-TYPE
        SYNTAX  Counter
        ACCESS  read-write
        STATUS  mandatory
        DESCRIPTION
            "Counter specifying the number of times an MO->AMS(as MT)
            routed message failed to be stored in AMS."
        ::= { smsCounters 433 }
    
    smsCntMoMtAmsPrimarySuccess OBJECT-TYPE
        SYNTAX  Counter
        ACCESS  read-write
        STATUS  mandatory
        DESCRIPTION
            "Counter specifying the number of times an MO->MT->AMS(as MT)
            routed message was successfully delivered as MT/SM."
        ::= { smsCounters 434 }
    
    smsCntMoMtAmsPrimaryFailure OBJECT-TYPE
        SYNTAX  Counter
        ACCESS  read-write
        STATUS  mandatory
        DESCRIPTION
            "Counter specifying the number of times an MO->MT->AMS(as MT)
            routed message failed to be delivered as MT/SM."
        ::= { smsCounters 435 }
    
    smsCntMoMtAmsFallbackSuccess OBJECT-TYPE
        SYNTAX  Counter
        ACCESS  read-write
        STATUS  mandatory
        DESCRIPTION
            "Counter specifying the number of times an MO->MT->AMS
            routed message was successfully stored in the AMS after a first
            delivery attempt failed."
        ::= { smsCounters 436 }
    
    smsCntMoMtAmsFallbackFailure OBJECT-TYPE
        SYNTAX  Counter
        ACCESS  read-write
        STATUS  mandatory
        DESCRIPTION
            "Counter specifying the number of times an MO->MT->AMS
            routed message could not be stored in the AMS after a first
            delivery attempt failed."
        ::= { smsCounters 437 }
    
    smsCntMoMtAmsFallbackNotAppliedDueToPermErrorOnPrimary OBJECT-TYPE
        SYNTAX  Counter
        ACCESS  read-write
        STATUS  mandatory
        DESCRIPTION
            "Counter specifying the number of times an MO->MT->AMS
            routed message was not attempted to be stored in the AMS because
            the first delivery attempt as MT/SM resulted in an error
            classified as 'permanent'."
        ::= { smsCounters 438 }
    
    smsCntMoMtAmsFallbackNotAppliedDueToUnavailability OBJECT-TYPE
        SYNTAX  Counter
        ACCESS  read-write
        STATUS  mandatory
        DESCRIPTION
            "Counter specifying the number of times an MO->MT->AMS
            routed message was not attempted to be stored in the AMS after
            a failed first delivery attempt as MT/SM, because the AMS was
            not available."
        ::= { smsCounters 439 }
    
    smsCntMoAtToAmsSuccess OBJECT-TYPE
        SYNTAX  Counter
        ACCESS  read-write
        STATUS  mandatory
        DESCRIPTION
            "Counter specifying the number of times an MO->AMS(as AT)
            routed message was successfully stored in the AMS."
        ::= { smsCounters 440 }
    
    smsCntMoAtToAmsFailure OBJECT-TYPE
        SYNTAX  Counter
        ACCESS  read-write
        STATUS  mandatory
        DESCRIPTION
            "Counter specifying the number of times an MO->AMS(as AT)
            routed message failed to be stored in the AMS."
        ::= { smsCounters 441 }
    
    smsCntMoAtAmsPrimarySuccess OBJECT-TYPE
        SYNTAX  Counter
        ACCESS  read-write
        STATUS  mandatory
        DESCRIPTION
            "Counter specifying the number of times an MO->AT->AMS
            routed message was successfully delivered as AT/SM."
        ::= { smsCounters 442 }
    
    smsCntMoAtAmsPrimaryFailure OBJECT-TYPE
        SYNTAX  Counter
        ACCESS  read-write
        STATUS  mandatory
        DESCRIPTION
            "Counter specifying the number of times an MO->AT->AMS
            routed message failed to be delivered as AT/SM."
        ::= { smsCounters 443 }
    
    smsCntMoAtAmsFallbackSuccess OBJECT-TYPE
        SYNTAX  Counter
        ACCESS  read-write
        STATUS  mandatory
        DESCRIPTION
            "Counter specifying the number of times an MO->AT->AMS
            routed message was successfully stored in the AMS after the
            first delivery attempt as AT/SM failed."
        ::= { smsCounters 444 }
    
    smsCntMoAtAmsFallbackFailure OBJECT-TYPE
        SYNTAX  Counter
        ACCESS  read-write
        STATUS  mandatory
        DESCRIPTION
            "Counter specifying the number of times an MO->AT->AMS routed
            message failed to be stored in the AMS after the first delivery
            attempt as AT/SM failed."
        ::= { smsCounters 445 }
    
    smsCntMoAtAmsFallbackNotAppliedDueToPermErrorOnPrimary OBJECT-TYPE
        SYNTAX  Counter
        ACCESS  read-write
        STATUS  mandatory
        DESCRIPTION
            "Counter specifying the number of times an MO->AT->AMS routed
            message was not attempted to be stored in the AMS because the
            first delivery attempt as AT/SM resulted in an error
            classified as 'permanent'."
        ::= { smsCounters 446 }
    
    smsCntMoAtAmsFallbackNotAppliedDueToUnavailability OBJECT-TYPE
        SYNTAX  Counter
        ACCESS  read-write
        STATUS  mandatory
        DESCRIPTION
            "Counter specifying the number of times an MO->AT->AMS routed
            message was not stored in the AMS after a failed first delivery
            attempt as AT/SM, because the AMS was unavailable."
        ::= { smsCounters 447 }
    
    smsCntMoMtMoPrimarySuccess OBJECT-TYPE
        SYNTAX  Counter
        ACCESS  read-write
        STATUS  mandatory
        DESCRIPTION
            "Counter specifying the number of times an MO->MT->MO routed
            message was succesfully delivered as MT/SM."
        ::= { smsCounters 448 }
    
    smsCntMoMtMoPrimaryFailure OBJECT-TYPE
        SYNTAX  Counter
        ACCESS  read-write
        STATUS  mandatory
        DESCRIPTION
            "Counter specifying the number of times an MO->MT->MO routed
            message failed to be delivered as MT/SM."
        ::= { smsCounters 449 }
    
    smsCntMoMtMoFallbackSuccess OBJECT-TYPE
        SYNTAX  Counter
        ACCESS  read-write
        STATUS  mandatory
        DESCRIPTION
            "Counter specifying the number of times an MO->MT->MO routed
            message was succesfully submitted as MO/SM after a failed
            first delivery attempt."
        ::= { smsCounters 450 }
    
    smsCntMoMtMoFallbackFailure OBJECT-TYPE
        SYNTAX  Counter
        ACCESS  read-write
        STATUS  mandatory
        DESCRIPTION
            "Counter specifying the number of times an MO->MT->MO routed
            message failed to be submitted as MO/SM after a failed first
            delivery attempt as MT/SM."
        ::= { smsCounters 451 }
    
    smsCntMoMtMoFallbackNotAppliedDueToPermErrorOnPrimary OBJECT-TYPE
        SYNTAX  Counter
        ACCESS  read-write
        STATUS  mandatory
        DESCRIPTION
            "Counter specifying the number of times an MO->MT->MO routed
            message was not attempted to be submitted as MO/SM because the
            first delivery attempt as MT/SM failed with an error classified
            as 'permanent'."
        ::= { smsCounters 452 }
    
    smsCntMoMtMoFallbackNotAppliedDueToUnavailability OBJECT-TYPE
        SYNTAX  Counter
        ACCESS  read-write
        STATUS  mandatory
        DESCRIPTION
            "Counter specifying the number of times an MO->MT->MO routed
            message was not attempted to be subbmitted as MO/SM after a
            failed first delivery attempt as MT/SM, because the SMSC was
            unavailable."
        ::= { smsCounters 453 }
    
    smsCntMoMtAtPrimarySuccess OBJECT-TYPE
        SYNTAX  Counter
        ACCESS  read-write
        STATUS  mandatory
        DESCRIPTION
            "Counter specifying the number of times an MO->MT->AT routed
            message was succesfully delivered as MT/SM."
        ::= { smsCounters 454 }
    
    smsCntMoMtAtPrimaryFailure OBJECT-TYPE
        SYNTAX  Counter
        ACCESS  read-write
        STATUS  mandatory
        DESCRIPTION
            "Counter specifying the number of times an MO->MT->AT routed
            message failed to be delivered as MT/SM."
        ::= { smsCounters 455 }
    
    smsCntMoMtAtFallbackSuccess OBJECT-TYPE
        SYNTAX  Counter
        ACCESS  read-write
        STATUS  mandatory
        DESCRIPTION
            "Counter specifying the number of times an MO->MT->AT routed
            message was succesfully delivered as AT/SM after a failed
            first delivery attempt as MT/SM."
        ::= { smsCounters 456 }
    
    smsCntMoMtAtFallbackFailure OBJECT-TYPE
        SYNTAX  Counter
        ACCESS  read-write
        STATUS  mandatory
        DESCRIPTION
            "Counter specifying the number of times an MO->MT->AT routed
            message failed to be delivered as AT/SM after a failed
            first delivery attempt as MT/SM."
        ::= { smsCounters 457 }
    
    smsCntMoMtAtFallbackNotAppliedDueToPermErrorOnPrimary OBJECT-TYPE
        SYNTAX  Counter
        ACCESS  read-write
        STATUS  mandatory
        DESCRIPTION
            "Counter specifying the number of times an MO->MT->AT routed
            message was not attempted to be delivered as AT/SM because
            the first delivery attempt as MT/SM failed with an error
            classified as 'permanent'."
        ::= { smsCounters 458 }
    
    smsCntMoMtAtFallbackNotAppliedDueToUnavailability OBJECT-TYPE
        SYNTAX  Counter
        ACCESS  read-write
        STATUS  mandatory
        DESCRIPTION
            "Counter specifying the number of times an MO->MT->AT routed
            message was not attempted to be delivered as AT/SM after a
            failed first delivery attempt as MT/SM, because the target
            application was unavailable."
        ::= { smsCounters 459 }
    
    smsCntMoMtAoPrimarySuccess OBJECT-TYPE
        SYNTAX  Counter
        ACCESS  read-write
        STATUS  mandatory
        DESCRIPTION
            "Counter specifying the number of times an MO->MT->AO routed
            message was succesfully delivered as MT/SM."
        ::= { smsCounters 460 }
    
    smsCntMoMtAoPrimaryFailure OBJECT-TYPE
        SYNTAX  Counter
        ACCESS  read-write
        STATUS  mandatory
        DESCRIPTION
            "Counter specifying the number of times an MO->MT->AO routed
            message failed to be delivered as MT/SM."
        ::= { smsCounters 461 }
    
    smsCntMoMtAoFallbackSuccess OBJECT-TYPE
        SYNTAX  Counter
        ACCESS  read-write
        STATUS  mandatory
        DESCRIPTION
            "Counter specifying the number of times an MO->MT->AO routed
            message was succesfully submitted as AO/SM after a failed first
            delivery attempt as MT/SM."
        ::= { smsCounters 462 }
    
    smsCntMoMtAoFallbackFailure OBJECT-TYPE
        SYNTAX  Counter
        ACCESS  read-write
        STATUS  mandatory
        DESCRIPTION
            "Counter specifying the number of times an MO->MT->AO routed
            message failed to be submitted as AO/SM after a failed first
            delivery attempt as MT/SM."
        ::= { smsCounters 463 }
    
    smsCntMoMtAoFallbackNotAppliedDueToPermErrorOnPrimary OBJECT-TYPE
        SYNTAX  Counter
        ACCESS  read-write
        STATUS  mandatory
        DESCRIPTION
            "Counter specifying the number of times an MO->MT->AO routed
            message was not attemptd to be submitted as AO/SM because the
            first delivery attempt an MT/SM failed with an error classified
            as 'permanent'."
        ::= { smsCounters 464 }
    
    smsCntMoMtAoFallbackNotAppliedDueToUnavailability OBJECT-TYPE
        SYNTAX  Counter
        ACCESS  read-write
        STATUS  mandatory
        DESCRIPTION
            "Counter specifying the number of times an MO->MT->AO routed
            message was not attempted to be submitted as AO/SM after a
            failed first delivery attempt as MT/SM, because the service
            centre was unavailable."
        ::= { smsCounters 465 }
    
    smsCntMoMtSuccess OBJECT-TYPE
        SYNTAX  Counter
        ACCESS  read-write
        STATUS  mandatory
        DESCRIPTION
            "Counter specifying the number of times an MO->MT routed message
            was succesfully delivered as MT/SM."
        ::= { smsCounters 466 }
    
    smsCntMoMtFailure OBJECT-TYPE
        SYNTAX  Counter
        ACCESS  read-write
        STATUS  mandatory
        DESCRIPTION
            "Counter specifying the number of times an MO->MT routed message
            failed to be delivered as MT/SM."
        ::= { smsCounters 467 }
    
    smsCntAoAtSuccess OBJECT-TYPE
        SYNTAX  Counter
        ACCESS  read-write
        STATUS  mandatory
        DESCRIPTION
            "Counter specifying the number of times an AO->AT routed message
            was succesfully delivered as AT/SM."
        ::= { smsCounters 468 }
    
    smsCntAoAtFailure OBJECT-TYPE
        SYNTAX  Counter
        ACCESS  read-write
        STATUS  mandatory
        DESCRIPTION
            "Counter specifying the number of times an AO->AT routed message
            failed to be delivered as AT/SM."
        ::= { smsCounters 469 }
    
    smsCntAoAtToAmsSuccess OBJECT-TYPE
        SYNTAX  Counter
        ACCESS  read-write
        STATUS  mandatory
        DESCRIPTION
            "Counter specifying the number of times an AO->AMS(as AT) routed
            message was successfully stored in the AMS."
        ::= { smsCounters 470 }
    
    smsCntAoAtToAmsFailure OBJECT-TYPE
        SYNTAX  Counter
        ACCESS  read-write
        STATUS  mandatory
        DESCRIPTION
            "Counter specifying the number of times an AO->AMS(as AT) routed
            message failed to be stored in the AMS."
        ::= { smsCounters 471 }
    
    smsCntAoAtAmsSuccess OBJECT-TYPE
        SYNTAX  Counter
        ACCESS  read-write
        STATUS  mandatory
        DESCRIPTION
            "Counter specifying the number of times an AO->AT->AMS
            routed message was accepted by the AMS for immediate delivery 
            as AT/SM."
        ::= { smsCounters 472 }
    
    smsCntAoAtAmsFailure OBJECT-TYPE
        SYNTAX  Counter
        ACCESS  read-write
        STATUS  mandatory
        DESCRIPTION
            "Counter specifying the number of times an AO->AT->AMS
            routed message failed to be submitted to the AMS for direct
            delivery as AT/SM."
        ::= { smsCounters 473 }

    -- AO - Store - AO

    smsCntAoAoToAmsSuccess OBJECT-TYPE
        SYNTAX  Counter
        ACCESS  read-write
        STATUS  mandatory
        DESCRIPTION
            "Counter specifying the number of times an AO->AMS(as AO) routed
            message was successfully stored in the AMS."
        ::= { smsCounters 474 }

    smsCntAoAoToAmsFailure OBJECT-TYPE
        SYNTAX  Counter
        ACCESS  read-write
        STATUS  mandatory
        DESCRIPTION
            "Counter specifying the number of times an AO->AMS(as AO) routed
            message failed to be stored in the AMS."
        ::= { smsCounters 475 }

    -- AO - AO - Store

    smsCntAoAoAmsPrimarySuccess OBJECT-TYPE
        SYNTAX  Counter
        ACCESS  read-write
        STATUS  mandatory
        DESCRIPTION
            "Counter specifying the number of times an AO->AO->AMS
            routed message was successfully forwarded as AO/SM."
        ::= { smsCounters 476 }

    smsCntAoAoAmsPrimaryFailure OBJECT-TYPE
        SYNTAX  Counter
        ACCESS  read-write
        STATUS  mandatory
        DESCRIPTION
            "Counter specifying the number of times an AO->AO->AMS
            routed message failed to be forwarded as AO/SM."
        ::= { smsCounters 477 }

    smsCntAoAoAmsFallbackSuccess OBJECT-TYPE
        SYNTAX  Counter
        ACCESS  read-write
        STATUS  mandatory
        DESCRIPTION
            "Counter specifying the number of times an AO->AO->AMS
            routed message was succesfully stored in the AMS after a
            first attempt to forward it as AO/SM."
        ::= { smsCounters 478 }

    smsCntAoAoAmsFallbackFailure OBJECT-TYPE
        SYNTAX  Counter
        ACCESS  read-write
        STATUS  mandatory
        DESCRIPTION
            "Counter specifying the number of times an AO->AO->AMS
            routed message failed to be stored in the AMS after a
            first attempt to forward it as AO/SM."
        ::= { smsCounters 479 }

    smsCntAoAoAmsFallbackNotAppliedDueToPermErrorOnPrimary OBJECT-TYPE
        SYNTAX  Counter
        ACCESS  read-write
        STATUS  mandatory
        DESCRIPTION
            "Counter specifying the number of times an AO->AO->AMS routed
            message was not attemptd to be stored in the AMS because the
            first attempt to forward it as AO/SM failed with an error
            classified as 'permanent'."
        ::= { smsCounters 480 }

    smsCntAoAoAmsFallbackNotAppliedDueToUnavailability OBJECT-TYPE
        SYNTAX  Counter
        ACCESS  read-write
        STATUS  mandatory
        DESCRIPTION
            "Counter specifying the number of times an AO->AO->AMS routed
            message was not attempted to be stored in the AMS after a
            failed first attempt to forward it as AO/SM, because the AMS
            was unavailable."
        ::= { smsCounters 481 }

    -- AT - Store - AT

    smsCntAtAtToAmsSuccess OBJECT-TYPE
        SYNTAX  Counter
        ACCESS  read-write
        STATUS  mandatory
        DESCRIPTION
            "Counter specifying the number of times an AT->AMS(as AT) routed
            message was successfully stored in the AMS."
        ::= { smsCounters 482 }

    smsCntAtAtToAmsFailure OBJECT-TYPE
        SYNTAX  Counter
        ACCESS  read-write
        STATUS  mandatory
        DESCRIPTION
            "Counter specifying the number of times an AT->AMS(as AT) routed
            message failed to be stored in the AMS."
        ::= { smsCounters 483 }

    -- AT - AT - Store

    smsCntAtAtAmsPrimarySuccess OBJECT-TYPE
        SYNTAX  Counter
        ACCESS  read-write
        STATUS  mandatory
        DESCRIPTION
            "Counter specifying the number of times an AT->AT->AMS
            routed message was successfully forwarded as AT/SM."
        ::= { smsCounters 484 }

    smsCntAtAtAmsPrimaryFailure OBJECT-TYPE
        SYNTAX  Counter
        ACCESS  read-write
        STATUS  mandatory
        DESCRIPTION
            "Counter specifying the number of times an AT->AT->AMS
            routed message failed to be forwarded as AT/SM."
        ::= { smsCounters 485 }

    smsCntAtAtAmsFallbackSuccess OBJECT-TYPE
        SYNTAX  Counter
        ACCESS  read-write
        STATUS  mandatory
        DESCRIPTION
            "Counter specifying the number of times an AT->AT->AMS
            routed message was succesfully stored in the AMS after a
            first attempt to forward it as AT/SM."
        ::= { smsCounters 486 }

    smsCntAtAtAmsFallbackFailure OBJECT-TYPE
        SYNTAX  Counter
        ACCESS  read-write
        STATUS  mandatory
        DESCRIPTION
            "Counter specifying the number of times an AT->AT->AMS
            routed message failed to be stored in the AMS after a
            first attempt to forward it as AT/SM."
        ::= { smsCounters 487 }

    smsCntAtAtAmsFallbackNotAppliedDueToPermErrorOnPrimary OBJECT-TYPE
        SYNTAX  Counter
        ACCESS  read-write
        STATUS  mandatory
        DESCRIPTION
            "Counter specifying the number of times an AT->AT->AMS routed
            message was not attemptd to be stored in the AMS because the
            first attempt to forward it as AT/SM failed with an error
            classified as 'permanent'."
        ::= { smsCounters 488 }

    smsCntAtAtAmsFallbackNotAppliedDueToUnavailability OBJECT-TYPE
        SYNTAX  Counter
        ACCESS  read-write
        STATUS  mandatory
        DESCRIPTION
            "Counter specifying the number of times an AT->AT->AMS routed
            message was not attempted to be stored in the AMS after a
            failed first attempt to forward it as AT/SM, because the AMS
            was unavailable."
        ::= { smsCounters 489 }

    -- AT - AO

    smsCntAtAoSuccess OBJECT-TYPE
        SYNTAX  Counter
        ACCESS  read-write
        STATUS  mandatory
        DESCRIPTION
            "Counter specifying the number of times an AT->AO routed message
            was succesfully submitted as AO/SM."
        ::= { smsCounters 490 }

    smsCntAtAoFailure OBJECT-TYPE
        SYNTAX  Counter
        ACCESS  read-write
        STATUS  mandatory
        DESCRIPTION
            "Counter specifying the number of times an AT->AO routed message
            failed to be submitted as AO/SM."
        ::= { smsCounters 491 }

    -- AT - Store - AO

    smsCntAtAoToAmsSuccess OBJECT-TYPE
        SYNTAX  Counter
        ACCESS  read-write
        STATUS  mandatory
        DESCRIPTION
            "Counter specifying the number of times an AT->AMS(as AO) routed
            message was successfully stored in the AMS."
        ::= { smsCounters 492 }

    smsCntAtAoToAmsFailure OBJECT-TYPE
        SYNTAX  Counter
        ACCESS  read-write
        STATUS  mandatory
        DESCRIPTION
            "Counter specifying the number of times an AT->AMS(as AO) routed
            message failed to be stored in the AMS."
        ::= { smsCounters 493 }

    -- AT - AO - Store

    smsCntAtAoAmsPrimarySuccess OBJECT-TYPE
        SYNTAX  Counter
        ACCESS  read-write
        STATUS  mandatory
        DESCRIPTION
            "Counter specifying the number of times an AT->AO->AMS
            routed message was successfully forwarded as AO/SM."
        ::= { smsCounters 494 }

    smsCntAtAoAmsPrimaryFailure OBJECT-TYPE
        SYNTAX  Counter
        ACCESS  read-write
        STATUS  mandatory
        DESCRIPTION
            "Counter specifying the number of times an AT->AO->AMS
            routed message failed to be forwarded as AO/SM."
        ::= { smsCounters 495 }

    smsCntAtAoAmsFallbackSuccess OBJECT-TYPE
        SYNTAX  Counter
        ACCESS  read-write
        STATUS  mandatory
        DESCRIPTION
            "Counter specifying the number of times an AT->AO->AMS
            routed message was succesfully stored in the AMS after a
            first attempt to forward it as AO/SM."
        ::= { smsCounters 496 }

    smsCntAtAoAmsFallbackFailure OBJECT-TYPE
        SYNTAX  Counter
        ACCESS  read-write
        STATUS  mandatory
        DESCRIPTION
            "Counter specifying the number of times an AT->AO->AMS
            routed message failed to be stored in the AMS after a
            first attempt to forward it as AO/SM."
        ::= { smsCounters 497 }

    smsCntAtAoAmsFallbackNotAppliedDueToPermErrorOnPrimary OBJECT-TYPE
        SYNTAX  Counter
        ACCESS  read-write
        STATUS  mandatory
        DESCRIPTION
            "Counter specifying the number of times an AT->AO->AMS routed
            message was not attemptd to be stored in the AMS because the
            first attempt to forward it as AO/SM failed with an error
            classified as 'permanent'."
        ::= { smsCounters 498 }

    smsCntAtAoAmsFallbackNotAppliedDueToUnavailability OBJECT-TYPE
        SYNTAX  Counter
        ACCESS  read-write
        STATUS  mandatory
        DESCRIPTION
            "Counter specifying the number of times an AT->AO->AMS routed
            message was not attempted to be stored in the AMS after a
            failed first attempt to forward it as AO/SM, because the AMS
            was unavailable."
        ::= { smsCounters 499 }

    -- AMS-initiated paths:
    
    smsCntAoMtFromAmsSuccess OBJECT-TYPE
        SYNTAX  Counter
        ACCESS  read-write
        STATUS  mandatory
        DESCRIPTION
            "Counter specifying the number of times that a delivery attempt 
            triggered by the AMS for an AO->MT routed message succeeded."
        ::= { smsCounters 531 }

    smsCntAoMtFromAmsTemporaryError OBJECT-TYPE 
        SYNTAX  Counter
        ACCESS  read-write
        STATUS  mandatory
        DESCRIPTION
            "Counter specifying the number of times that a delivery attempt 
            triggered by the AMS for an AO->MT routed message failed with a 
            temporary error."
        ::= { smsCounters 532 }

    smsCntAoMtFromAmsPermanentRecipientError OBJECT-TYPE
        SYNTAX  Counter
        ACCESS  read-write
        STATUS  mandatory
        DESCRIPTION
            "Counter specifying the number of times that a delivery attempt 
            triggered by the AMS for an AO->MT routed message failed with a 
            permanent recipient error."
        ::= { smsCounters 533 }

    smsCntAoMtFromAmsPermanentMessageError OBJECT-TYPE
        SYNTAX  Counter
        ACCESS  read-write
        STATUS  mandatory
        DESCRIPTION
            "Counter specifying the number of times that a delivery attempt 
            triggered by the AMS for an AO->MT routed message failed with a 
            permanent message error."
        ::= { smsCounters 534 }

    smsCntAoMtFromAmsExpired OBJECT-TYPE
        SYNTAX  Counter
        ACCESS  read-write
        STATUS  mandatory
        DESCRIPTION
            "Counter specifying the number of times that an AO->MT routed
            message has expired in the AMS."
        ::= { smsCounters 535 }

    smsCntAoMtFromAmsDeleted OBJECT-TYPE
        SYNTAX  Counter
        ACCESS  read-write
        STATUS  mandatory
        DESCRIPTION
            "Counter specifying the number of times that an AO->MT routed
            message has been deleted from the AMS."
        ::= { smsCounters 536 }

    smsCntAoMtFromAmsReplaced OBJECT-TYPE
        SYNTAX  Counter
        ACCESS  read-write
        STATUS  mandatory
        DESCRIPTION
            "Counter specifying the number of times that an AO->MT routed
            message has been replaced in the AMS."
        ::= { smsCounters 537 }
    
    smsCntMoMtFromAmsSuccess OBJECT-TYPE
        SYNTAX  Counter
        ACCESS  read-write
        STATUS  mandatory
        DESCRIPTION
            "Counter specifying the number of times that a delivery attempt 
            triggered by the AMS for an MO->MT routed message succeeded."
        ::= { smsCounters 541 }

    smsCntMoMtFromAmsTemporaryError OBJECT-TYPE 
        SYNTAX  Counter
        ACCESS  read-write
        STATUS  mandatory
        DESCRIPTION
            "Counter specifying the number of times that a delivery attempt 
            triggered by the AMS for an MO->MT routed message failed with a 
            temporary error."
        ::= { smsCounters 542 }

    smsCntMoMtFromAmsPermanentRecipientError OBJECT-TYPE
        SYNTAX  Counter
        ACCESS  read-write
        STATUS  mandatory
        DESCRIPTION
            "Counter specifying the number of times that a delivery attempt 
            triggered by the AMS for an MO->MT routed message failed with a 
            permanent recipient error."
        ::= { smsCounters 543 }

    smsCntMoMtFromAmsPermanentMessageError OBJECT-TYPE
        SYNTAX  Counter
        ACCESS  read-write
        STATUS  mandatory
        DESCRIPTION
            "Counter specifying the number of times that a delivery attempt 
            triggered by the AMS for an MO->MT routed message failed with a 
            permanent message error."
        ::= { smsCounters 544 }

    smsCntMoMtFromAmsExpired OBJECT-TYPE
        SYNTAX  Counter
        ACCESS  read-write
        STATUS  mandatory
        DESCRIPTION
            "Counter specifying the number of times that an MO->MT routed
            message has expired in the AMS."
        ::= { smsCounters 545 }

    smsCntMoMtFromAmsDeleted OBJECT-TYPE
        SYNTAX  Counter
        ACCESS  read-write
        STATUS  mandatory
        DESCRIPTION
            "Counter specifying the number of times that an MO->MT routed
            message has been deleted from the AMS."
        ::= { smsCounters 546 }

    smsCntMoMtFromAmsReplaced OBJECT-TYPE
        SYNTAX  Counter
        ACCESS  read-write
        STATUS  mandatory
        DESCRIPTION
            "Counter specifying the number of times that an MO->MT routed
            message has been replaced in the AMS."
        ::= { smsCounters 547 }

    smsCntAoAtFromAmsSuccess OBJECT-TYPE
        SYNTAX  Counter
        ACCESS  read-write
        STATUS  mandatory
        DESCRIPTION
            "Counter specifying the number of times that a delivery attempt 
            triggered by the AMS for an AO->AT or AT->AT routed message
            succeeded."
        ::= { smsCounters 551 }

    smsCntAoAtFromAmsTemporaryError OBJECT-TYPE 
        SYNTAX  Counter
        ACCESS  read-write
        STATUS  mandatory
        DESCRIPTION
            "Counter specifying the number of times that a delivery attempt 
            triggered by the AMS for an AO->AT or AT->AT routed message
            failed with a temporary error."
        ::= { smsCounters 552 }

    smsCntAoAtFromAmsPermanentRecipientError OBJECT-TYPE
        SYNTAX  Counter
        ACCESS  read-write
        STATUS  mandatory
        DESCRIPTION
            "Counter specifying the number of times that a delivery attempt 
            triggered by the AMS for an AO->AT or AT->AT routed message
            failed with a permanent recipient error."
        ::= { smsCounters 553 }

    smsCntAoAtFromAmsPermanentMessageError OBJECT-TYPE
        SYNTAX  Counter
        ACCESS  read-write
        STATUS  mandatory
        DESCRIPTION
            "Counter specifying the number of times that a delivery attempt 
            triggered by the AMS for an AO->AT or AT->AT routed message
            failed with a permanent message error."
        ::= { smsCounters 554 }

    smsCntAoAtFromAmsExpired OBJECT-TYPE
        SYNTAX  Counter
        ACCESS  read-write
        STATUS  mandatory
        DESCRIPTION
            "Counter specifying the number of times that an AO->AT or
            AT->AT routed message has expired in the AMS."
        ::= { smsCounters 555 }

    smsCntAoAtFromAmsDeleted OBJECT-TYPE
        SYNTAX  Counter
        ACCESS  read-write
        STATUS  mandatory
        DESCRIPTION
            "Counter specifying the number of times that an AO->AT or
            AT->AT routed message has been deleted from the AMS."
        ::= { smsCounters 556 }

    smsCntAoAtFromAmsReplaced OBJECT-TYPE
        SYNTAX  Counter
        ACCESS  read-write
        STATUS  mandatory
        DESCRIPTION
            "Counter specifying the number of times that an AO->AT or
            AT->AT routed message has been replaced in the AMS."
        ::= { smsCounters 557 }

    -- AO - Store - AO

    smsCntAoAoFromAmsSuccess OBJECT-TYPE
        SYNTAX  Counter
        ACCESS  read-write
        STATUS  mandatory
        DESCRIPTION
            "Counter specifying the number of times that a forward attempt 
            triggered by the AMS for an AO->AO routed message succeeded."
        ::= { smsCounters 561 }

    smsCntAoAoFromAmsTemporaryError OBJECT-TYPE 
        SYNTAX  Counter
        ACCESS  read-write
        STATUS  mandatory
        DESCRIPTION
            "Counter specifying the number of times that a forward attempt 
            triggered by the AMS for an AO->AO routed message failed with a 
            temporary error."
        ::= { smsCounters 562 }

    smsCntAoAoFromAmsPermanentRecipientError OBJECT-TYPE
        SYNTAX  Counter
        ACCESS  read-write
        STATUS  mandatory
        DESCRIPTION
            "Counter specifying the number of times that a forward attempt 
            triggered by the AMS for an AO->AO routed message failed with a 
            permanent recipient error."
        ::= { smsCounters 563 }

    smsCntAoAoFromAmsPermanentMessageError OBJECT-TYPE
        SYNTAX  Counter
        ACCESS  read-write
        STATUS  mandatory
        DESCRIPTION
            "Counter specifying the number of times that a forward attempt 
            triggered by the AMS for an AO->AO routed message failed with a 
            permanent message error."
        ::= { smsCounters 564 }

    smsCntAoAoFromAmsExpired OBJECT-TYPE
        SYNTAX  Counter
        ACCESS  read-write
        STATUS  mandatory
        DESCRIPTION
            "Counter specifying the number of times that an AO->AO routed
            message has expired in the AMS."
        ::= { smsCounters 565 }

    smsCntAoAoFromAmsDeleted OBJECT-TYPE
        SYNTAX  Counter
        ACCESS  read-write
        STATUS  mandatory
        DESCRIPTION
            "Counter specifying the number of times that an AO->AT routed
            message has been deleted from the AMS."
        ::= { smsCounters 566 }

    smsCntAoAoFromAmsReplaced OBJECT-TYPE
        SYNTAX  Counter
        ACCESS  read-write
        STATUS  mandatory
        DESCRIPTION
            "Counter specifying the number of times that an AO->AO routed
            message has been replaced in the AMS."
        ::= { smsCounters 567 }
    
    -- MO - Store - AT

    smsCntMoAtFromAmsSuccess OBJECT-TYPE
        SYNTAX  Counter
        ACCESS  read-write
        STATUS  mandatory
        DESCRIPTION
            "Counter specifying the number of times that a delivery attempt 
            triggered by the AMS for an MO->AT/SM succeeded."
        ::= { smsCounters 571 }

    smsCntMoAtFromAmsTemporaryError OBJECT-TYPE 
        SYNTAX  Counter
        ACCESS  read-write
        STATUS  mandatory
        DESCRIPTION
            "Counter specifying the number of times that a delivery attempt 
            triggered by the AMS for an MO->AT routed message failed with a 
            temporary error."
        ::= { smsCounters 572 }

    smsCntMoAtFromAmsPermanentRecipientError OBJECT-TYPE
        SYNTAX  Counter
        ACCESS  read-write
        STATUS  mandatory
        DESCRIPTION
            "Counter specifying the number of times that a delivery attempt 
            triggered by the AMS for an MO->AT routed message failed with a 
            permanent recipient error."
        ::= { smsCounters 573 }

    smsCntMoAtFromAmsPermanentMessageError OBJECT-TYPE
        SYNTAX  Counter
        ACCESS  read-write
        STATUS  mandatory
        DESCRIPTION
            "Counter specifying the number of times that a delivery attempt 
            triggered by the AMS for an MO->AT routed message failed with a 
            permanent message error."
        ::= { smsCounters 574 }

    smsCntMoAtFromAmsExpired OBJECT-TYPE
        SYNTAX  Counter
        ACCESS  read-write
        STATUS  mandatory
        DESCRIPTION
            "Counter specifying the number of times that an MO->AT routed
            message has expired in the AMS."
        ::= { smsCounters 575 }

    smsCntMoAtFromAmsDeleted OBJECT-TYPE
        SYNTAX  Counter
        ACCESS  read-write
        STATUS  mandatory
        DESCRIPTION
            "Counter specifying the number of times that an MO->AT routed
            message has been deleted from the AMS."
        ::= { smsCounters 576 }

    smsCntMoAtFromAmsReplaced OBJECT-TYPE
        SYNTAX  Counter
        ACCESS  read-write
        STATUS  mandatory
        DESCRIPTION
            "Counter specifying the number of times that an MO->AT routed
            message has been replaced in the AMS."
        ::= { smsCounters 577 }

    -- AT - Store - AO

    smsCntAtAoFromAmsSuccess OBJECT-TYPE
        SYNTAX  Counter
        ACCESS  read-write
        STATUS  mandatory
        DESCRIPTION
            "Counter specifying the number of times that a delivery attempt 
            triggered by the AMS for an AT->AO routed message succeeded."
        ::= { smsCounters 581 }

    smsCntAtAoFromAmsTemporaryError OBJECT-TYPE 
        SYNTAX  Counter
        ACCESS  read-write
        STATUS  mandatory
        DESCRIPTION
            "Counter specifying the number of times that a delivery attempt 
            triggered by the AMS for an AT->AO routed message failed with a 
            temporary error."
        ::= { smsCounters 582 }

    smsCntAtAoFromAmsPermanentRecipientError OBJECT-TYPE
        SYNTAX  Counter
        ACCESS  read-write
        STATUS  mandatory
        DESCRIPTION
            "Counter specifying the number of times that a delivery attempt 
            triggered by the AMS for an AT->AO routed message failed with a 
            permanent recipient error."
        ::= { smsCounters 583 }

    smsCntAtAoFromAmsPermanentMessageError OBJECT-TYPE
        SYNTAX  Counter
        ACCESS  read-write
        STATUS  mandatory
        DESCRIPTION
            "Counter specifying the number of times that a delivery attempt 
            triggered by the AMS for an AT->AO routed message failed with a 
            permanent message error."
        ::= { smsCounters 584 }

    smsCntAtAoFromAmsExpired OBJECT-TYPE
        SYNTAX  Counter
        ACCESS  read-write
        STATUS  mandatory
        DESCRIPTION
            "Counter specifying the number of times that an AT->AO routed
            message has expired in the AMS."
        ::= { smsCounters 585 }

    smsCntAtAoFromAmsDeleted OBJECT-TYPE
        SYNTAX  Counter
        ACCESS  read-write
        STATUS  mandatory
        DESCRIPTION
            "Counter specifying the number of times that an AT->AO routed
            message has been deleted from the AMS."
        ::= { smsCounters 586 }

    smsCntAtAoFromAmsReplaced OBJECT-TYPE
        SYNTAX  Counter
        ACCESS  read-write
        STATUS  mandatory
        DESCRIPTION
            "Counter specifying the number of times that an AT->AO routed
            message has been replaced in the AMS."
        ::= { smsCounters 587 }

    errorClassification OBJECT IDENTIFIER ::= { sms 3 }

    errClsMtTimeout OBJECT-TYPE
        SYNTAX  ErrorClassification
        ACCESS  read-write
        STATUS  mandatory
        DESCRIPTION
            "Classification of timeout on a MT-Forward-SM operation.
            Default is 'temporary'."
        ::= { errorClassification 22 }

    errClsMtAbsSubError OBJECT-TYPE
        SYNTAX  ErrorClassification
        ACCESS  read-write
        STATUS  mandatory
        DESCRIPTION
            "Classification of an Absent-Subscriber error on a MT-Forward-SM
            operation. Default is 'temporary'."
        ::= { errorClassification 23 }

    errClsMtSysFailError OBJECT-TYPE
        SYNTAX  ErrorClassification
        ACCESS  read-write
        STATUS  mandatory
        DESCRIPTION
            "Classification of a System Failure error on a MT-Forward-SM
            operation. Default is 'temporary'."
        ::= { errorClassification 24 }

    errClsMtDataMisError OBJECT-TYPE
        SYNTAX  ErrorClassification
        ACCESS  read-write
        STATUS  mandatory
        DESCRIPTION
            "Classification of a Data Missing error on a MT-Forward-SM
            operation. Default is 'temporary'."
        ::= { errorClassification 25 }

    errClsMtUnexpDataValError OBJECT-TYPE
        SYNTAX  ErrorClassification
        ACCESS  read-write
        STATUS  mandatory
        DESCRIPTION
            "Classification of an Unexpected=Data-Value error on a
            MT-Forward-SM operation. Default is 'temporary'."
        ::= { errorClassification 26 }

    errClsMtFacNotSuppError OBJECT-TYPE
        SYNTAX  ErrorClassification
        ACCESS  read-write
        STATUS  mandatory
        DESCRIPTION
            "Classification of a Facility-Not-Supported error on a
            MT-Forward-SM operation. Default is 'temporary'."
        ::= { errorClassification 27 }

    errClsMtUnidenSubError OBJECT-TYPE
        SYNTAX  ErrorClassification
        ACCESS  read-write
        STATUS  mandatory
        DESCRIPTION
            "Classification of an Unidentified-Subscriber error on a
            MT-Forward-SM operation. Default is 'temporary'."
        ::= { errorClassification 28 }

    errClsMtIllSubError OBJECT-TYPE
        SYNTAX  ErrorClassification
        ACCESS  read-write
        STATUS  mandatory
        DESCRIPTION
            "Classification of an Illegal-Subscriber error on a MT-Forward-SM
            operation. Default is 'permanentForRecipient'."
        ::= { errorClassification 29 }

    errClsMtIllEquipError OBJECT-TYPE
        SYNTAX  ErrorClassification
        ACCESS  read-write
        STATUS  mandatory
        DESCRIPTION
            "Classification of an Illegal-Equipment error on a MT-Forward-SM
            operation. Default is 'permanentForRecipient'."
        ::= { errorClassification 30 }

    errClsMtSubBusyForMtSmError OBJECT-TYPE
        SYNTAX  ErrorClassification
        ACCESS  read-write
        STATUS  mandatory
        DESCRIPTION
            "Classification of an MT-Subscriber-Busy-For-MT-SM error on a
             MT-Forward-SM operation. Default is 'temporary'."
        ::= { errorClassification 31 }

    errClsMtInvSmeAddrError OBJECT-TYPE

        SYNTAX  ErrorClassification
        ACCESS  read-write
        STATUS  mandatory
        DESCRIPTION
            "Classification of an SM-Delivery-Failure error with failure cause
            equal to Invalid-SME-Address on a MT-Forward-SM operation. Default
            is 'temporary'."
        ::= { errorClassification 32 }

    errClsMtEquipProtError OBJECT-TYPE
        SYNTAX  ErrorClassification
        ACCESS  read-write
        STATUS  mandatory
        DESCRIPTION
            "Classification of an SM-Delivery-Failure error with failure cause
            equal to Equipment-Protocol-Error on a MT-Forward-SM operation.
            Default is 'temporary'."
        ::= { errorClassification 33 }

    errClsMtEquipNotSmEquipError OBJECT-TYPE
        SYNTAX  ErrorClassification
        ACCESS  read-write
        STATUS  mandatory
        DESCRIPTION
            "Classification of an SM-Delivery-Failure error with failure cause
            equal to Equipment-Not-SM-Equipped on a MT-Forward-SM operation.
            Default is 'temporary'."
        ::= { errorClassification 34 }

    errClsMtMemCapExcError OBJECT-TYPE
        SYNTAX  ErrorClassification
        ACCESS  read-write
        STATUS  mandatory
        DESCRIPTION
            "Classification of an SM-Delivery-Failure error with failure cause
            equal to Memory-Capacity-Exceeded on a MT-Forward-SM operation.
            Default is 'temporary'."
        ::= { errorClassification 35 }

    errClsMtTcapAborted OBJECT-TYPE
        SYNTAX  ErrorClassification
        ACCESS  read-write
        STATUS  mandatory
        DESCRIPTION
            "Classification of a TCAP abort on a MT-Forward-SM operation.
            Default is 'temporary'."
        ::= { errorClassification 37 }

    errClsMtSccpAborted OBJECT-TYPE
        SYNTAX  ErrorClassification
        ACCESS  read-write
        STATUS  mandatory
        DESCRIPTION
            "Classification of an SCCP abort on a MT-Forward-SM operation.
             Default is 'temporary'."
        ::= { errorClassification 38 }

    errClsSriSmTimeout OBJECT-TYPE
        SYNTAX  ErrorClassification
        ACCESS  read-write
        STATUS  mandatory
        DESCRIPTION
            "Classification of a timeout on a Send-Routing-Info-For-SM
            operation.  Default is 'temporary'."
        ::= { errorClassification 45 }

    errClsSriSmSysFailError OBJECT-TYPE
        SYNTAX  ErrorClassification
        ACCESS  read-write
        STATUS  mandatory
        DESCRIPTION
            "Classification of a System-Failure error on a
            Send-Routing-Info-For-SM operation. Default is 'temporary'."
        ::= { errorClassification 46 }

    errClsSriSmDataMisError OBJECT-TYPE
        SYNTAX  ErrorClassification
        ACCESS  read-write
        STATUS  mandatory
        DESCRIPTION
            "Classification of a Data-Missing error on a
            Send-Routing-Info-For-SM operation. Default is 'temporary'."
        ::= { errorClassification 47 }

    errClsSriSmUnexpDataValError OBJECT-TYPE
        SYNTAX  ErrorClassification
        ACCESS  read-write
        STATUS  mandatory
        DESCRIPTION
            "Classification of an Unexpected-Data-Value error on a
             Send-Routing-Info-For-SM operation. Default is 'temporary'."
        ::= { errorClassification 48 }

    errClsSriSmFacNotSuppError OBJECT-TYPE
        SYNTAX  ErrorClassification
        ACCESS  read-write
        STATUS  mandatory
        DESCRIPTION
            "Classification of a Facility-Not-Supported error on a
             Send-Routing-Info-For-SM operation. Default is 'temporary'."
        ::= { errorClassification 49 }

    errClsSriSmUnkSubError OBJECT-TYPE
        SYNTAX  ErrorClassification
        ACCESS  read-write
        STATUS  mandatory
        DESCRIPTION
            "Classification of an Unknown-Subscriber error on a
             Send-Routing-Info-For-SM operation. Default is 
             'permanentForRecipient'."
        ::= { errorClassification 50 }

    errClsSriSmAbsSubError OBJECT-TYPE
        SYNTAX  ErrorClassification
        ACCESS  read-write
        STATUS  mandatory
        DESCRIPTION
            "Classification of a Absent-Subscriber error on a
             Send-Routing-Info-For-SM operation. Default is 'temporary'."
        ::= { errorClassification 51 }

    errClsSriSmCallBarredError OBJECT-TYPE
        SYNTAX  ErrorClassification
        ACCESS  read-write
        STATUS  mandatory
        DESCRIPTION
            "Classification of Call-Barred error on a
            Send-Routing-Info-For-SM operation. Default is 'temporary'."
        ::= { errorClassification 52 }

    errClsSriSmTeleServNotProvError OBJECT-TYPE
        SYNTAX  ErrorClassification
        ACCESS  read-write
        STATUS  mandatory
        DESCRIPTION
            "Classification of a Teleservice-Not-Provisioned error on a
             Send-Routing-Info-For-SM operation. Default is 
             'permanentForRecipient'."
        ::= { errorClassification 53 }

    errClsSriSmTcapAborted OBJECT-TYPE
        SYNTAX  ErrorClassification
        ACCESS  read-write
        STATUS  mandatory
        DESCRIPTION
            "Classification of a TCAP abort on a Send-Routing-Info-For-SM
            operation. Default is 'temporary'."
        ::= { errorClassification 55 }

    errClsSriSmSccpAborted OBJECT-TYPE
        SYNTAX  ErrorClassification
        ACCESS  read-write
        STATUS  mandatory
        DESCRIPTION
            "Classification of an SCCP abort on a Send-Routing-Info-For-SM
            operation. Default is 'temporary'."
        ::= { errorClassification 56 }


    extAttrTable OBJECT-TYPE
        SYNTAX  SEQUENCE OF ExtAttrEntry
        ACCESS  not-accessible
        STATUS  mandatory
        DESCRIPTION
            "A table containing properties and conditions of the attributes
            that can be set using the external approval interface and that
            are subject to conditions in the routing rules.            
            Each attribute is associated with an ID. This ID is equal to the
            bit number that is used in the bit strings that are used to
            convey the values of the external attributes in ECI (i.e. the
            interface between TextPass ROUTER and the external approval
            applications).
            The attribute ID has a range of 0-31, wheras the table index has
            a range of 1-32. So, the ID is always one off from the table
            index."
        ::= { sms 4 }

    extAttrEntry OBJECT-TYPE
        SYNTAX  ExtAttrEntry
        ACCESS  not-accessible
        STATUS  mandatory
        DESCRIPTION
            "Table entry specifying a single external attribute."
        INDEX   { extAttrIndex }
        ::= { extAttrTable 1 }

    ExtAttrEntry ::=
        SEQUENCE {
            extAttrIndex                          ExtAttrTableIndex,
            extAttrName                           NameString,
            extAttrTrueCounter                    Counter,                 
            extAttrFalseCounter                   Counter
        }
        
    extAttrIndex OBJECT-TYPE
        SYNTAX  ExtAttrTableIndex
        ACCESS  read-write
        STATUS  mandatory
        DESCRIPTION
            "Index of entry in external attribute table."
        ::= { extAttrEntry 1 }

    extAttrName OBJECT-TYPE
        SYNTAX  NameString
        ACCESS  read-write
        STATUS  mandatory
        DESCRIPTION
            "Name of the external attribute rule."
        ::= { extAttrEntry 3 }

    extAttrTrueCounter OBJECT-TYPE
        SYNTAX  Counter
        ACCESS  read-write
        STATUS  mandatory
        DESCRIPTION
            "Counter specifying the number of times that the external 
            applications have used the attribute and set it to TRUE."
        ::= { extAttrEntry 11 }

    extAttrFalseCounter OBJECT-TYPE
        SYNTAX  Counter
        ACCESS  read-write
        STATUS  mandatory
        DESCRIPTION
            "Counter specifying the number of times that the external 
            applications have used the attribute and set it to FALSE."
        ::= { extAttrEntry 12 }
                         
    areaCodeTable OBJECT-TYPE
        SYNTAX  SEQUENCE OF AreaCodeEntry
        ACCESS  not-accessible
        STATUS  mandatory
        DESCRIPTION
            "A table containing area codes as used in the mobile 
            numbering plan of the country in which the TextPass device has
            been installed. This table should be used when the length of
            area codes is variable. If the length is fixed, there is no 
            need to use this table. The length can then be set using the 
            smsPropAreaCodeLength object.
            Note that this table can only be filled when the 
            smsPropAreaCodeLength object."
        ::= { sms 5 }

    areaCodeEntry OBJECT-TYPE
        SYNTAX  AreaCodeEntry
        ACCESS  not-accessible
        STATUS  mandatory
        DESCRIPTION
            "Table entry specifying a single area code."
        INDEX   { areaCodeIndex }
        ::= { areaCodeTable 1 }

    AreaCodeEntry ::=
        SEQUENCE {
            areaCodeIndex                         AreaCodeIndex,
            areaCodeString                        AreaCodeString
        }

    areaCodeIndex OBJECT-TYPE
        SYNTAX  AreaCodeIndex
        ACCESS  read-write
        STATUS  mandatory
        DESCRIPTION
            "Index of entry in area code table."
        ::= { areaCodeEntry 1 }

    areaCodeString OBJECT-TYPE
        SYNTAX  AreaCodeString
        ACCESS  read-write
        STATUS  mandatory
        DESCRIPTION
            "Area code (e.g. 20). Supplying a zero-length string for this
            object, results in a removal of the concerning table row."
        ::= { areaCodeEntry 2 }

    gsmAcTable OBJECT-TYPE
        SYNTAX  SEQUENCE OF GsmAcEntry
        ACCESS  not-accessible
        STATUS  mandatory
        DESCRIPTION
            "A table containing rules for conversion of GSM addresses. The
            purpose of this table is converting addresses to international
            format. For addresses that do not need to be converted, no rule
            is required.
            The addresses that result from this conversion are used by the
            rule processor to match conditions in the routing and counting
            rules. Furthermore, the addresses are used when TextPass requires
            a conversion to international format for a specific purpose (e.g.
            doing an HLR query or HLR update).
            When no entries in this table are defined, TextPass uses a scheme
            for address conversion that is solely based on the NPI/TON
            supplied with the GSM address."
        ::= { sms 6 }

    gsmAcEntry OBJECT-TYPE
        SYNTAX  GsmAcEntry
        ACCESS  not-accessible
        STATUS  mandatory
        DESCRIPTION
            "Table entry specifying a single GSM address conversion rule."
        INDEX   { gsmAcIndex }
        ::= { gsmAcTable 1 }

    GsmAcEntry ::=
        SEQUENCE {
            gsmAcIndex                            GsmAcTableIndex,
            gsmAcAdminState                       AdminState,
            gsmAcInputTypeOfNumber                TypeOfNumber,
            gsmAcInputNumberingPlanIdentification NumberingPlanIdentification,
            gsmAcInputAddressPrefix               GsmAddress,
            gsmAcInputMinimumAddressLength        GsmAddressLength,
            gsmAcInputMaximumAddressLength        GsmAddressLength,
            gsmAcOutputAddressPrefix              GsmAddressPrefixWithAreaCodeSpecifier,
            gsmAcOutputType                       GsmAcOutputType
        }

    gsmAcIndex OBJECT-TYPE
        SYNTAX  GsmAcTableIndex
        ACCESS  read-write
        STATUS  mandatory
        DESCRIPTION
            "Index of entry in GSM address conversion table."
        ::= { gsmAcEntry 1 }

    gsmAcAdminState OBJECT-TYPE
        SYNTAX  AdminState
        ACCESS  read-write
        STATUS  mandatory
        DESCRIPTION
            "Administrative state of the GSM address conversion rule."
        ::= { gsmAcEntry 2 }

    gsmAcInputTypeOfNumber OBJECT-TYPE
        SYNTAX  TypeOfNumber
        ACCESS  read-write
        STATUS  mandatory
        DESCRIPTION
            "Value for type of number (TON) that should match with the TON of
            an address-to-be-converted in order for the GSM address conversion
            rule to apply."
        ::= { gsmAcEntry 11 }

    gsmAcInputNumberingPlanIdentification OBJECT-TYPE
        SYNTAX  NumberingPlanIdentification
        ACCESS  read-write
        STATUS  mandatory
        DESCRIPTION
            "Value for numbering plan identification (NPI) that should match
            with the NPI of an address-to-be-converted in order for the GSM
            address conversion rule to apply."
        ::= { gsmAcEntry 12 }

    gsmAcInputAddressPrefix OBJECT-TYPE
        SYNTAX  GsmAddress
        ACCESS  read-write
        STATUS  mandatory
        DESCRIPTION
            "Value for prefix that address-to-be-converted should start with
            in order for the GSM address conversion rule to apply."
        ::= { gsmAcEntry 13 }

    gsmAcInputMinimumAddressLength OBJECT-TYPE
        SYNTAX  GsmAddressLength
        ACCESS  read-write
        STATUS  mandatory
        DESCRIPTION

            "Minimum value for length of an address-to-be-converted in order
            for the GSM address conversion rule to apply."
        ::= { gsmAcEntry 14 }

    gsmAcInputMaximumAddressLength OBJECT-TYPE
        SYNTAX  GsmAddressLength
        ACCESS  read-write
        STATUS  mandatory
        DESCRIPTION
            "Maximum value for length of an address-to-be-converted in order
            for the GSM address conversion rule to apply."
        ::= { gsmAcEntry 15 }

    gsmAcOutputAddressPrefix OBJECT-TYPE
        SYNTAX  GsmAddressPrefixWithAreaCodeSpecifier
        ACCESS  read-write
        STATUS  mandatory
        DESCRIPTION
            "Prefix that will replace the prefix that address-to-be-converted
            matched with. As an option, the prefix may be terminated with an
            at sign (@). This sign represents the area code of the originator
            address. So, when the prefix is specified as '31@' and the area
            code in the originator address is 20, the prefix that
            address-to-be- converted matched with will be replaced with
            '3120'."
        ::= { gsmAcEntry 21 }

    gsmAcOutputType OBJECT-TYPE
        SYNTAX  GsmAcOutputType
        ACCESS  read-write
        STATUS  mandatory
        DESCRIPTION
            "Indicator specifying how address is classified. Default is 
            'determinedByLength'."
        ::= { gsmAcEntry 22 }

    moTagTable OBJECT-TYPE
        SYNTAX  SEQUENCE OF MoTagEntry
        ACCESS  not-accessible
        STATUS  mandatory
        DESCRIPTION
            "A table containing information about tags that can be specified
            in an MO/SM to trigger a specific function (e.g. phase 1 status
            report)."
        ::= { sms 7 }

    moTagEntry OBJECT-TYPE
        SYNTAX  MoTagEntry
        ACCESS  not-accessible
        STATUS  mandatory
        DESCRIPTION
            "Table entry specifying a single GSM address conversion rule."
        INDEX   { moTagIndex }
        ::= { moTagTable 1 }

    MoTagEntry ::=
        SEQUENCE {
            moTagIndex                            MoTagTableIndex,
            moTagAdminState                       AdminState,
            moTagString                           MoTagString,
            moTagFunction                         MoTagFunction
        }

    moTagIndex OBJECT-TYPE
        SYNTAX  MoTagTableIndex
        ACCESS  read-write
        STATUS  mandatory
        DESCRIPTION
            "Index of entry in MO tag table."
        ::= { moTagEntry 1 }

    moTagAdminState OBJECT-TYPE
        SYNTAX  AdminState
        ACCESS  read-write
        STATUS  mandatory
        DESCRIPTION
            "Administrative state of an MO tag."
        ::= { moTagEntry 2 }

    moTagString OBJECT-TYPE
        SYNTAX  MoTagString
        ACCESS  read-write
        STATUS  mandatory
        DESCRIPTION
            "String containing a tag that triggers a specific function. In
            advanced tag mode, the string may only contain alphanumeric
            characters."
        ::= { moTagEntry 3 }

    moTagFunction OBJECT-TYPE
        SYNTAX  MoTagFunction
        ACCESS  read-write
        STATUS  mandatory
        DESCRIPTION
            "Function that is being triggered as result of an MO/SM that
            starts with the tag."
        ::= { moTagEntry 4 }


    fwProperties OBJECT IDENTIFIER ::= { sms 8 }

    fwPropMtActionForUnknownSccpAddress OBJECT-TYPE
        SYNTAX  MtAction
        ACCESS  read-write
        STATUS  mandatory
        DESCRIPTION
            "Action to be executed when TextPass receives an MtForwardSm
            operation or SendRoutingInfoForSm operation with an SMSC address
            at SCCP level that cannot be associated with any of the defined
            mobile network entities. Default action is
            'blockWithNoResponse'."
        ::= { fwProperties 1 }

    fwPropMtActionForUnknownMapAddress OBJECT-TYPE
        SYNTAX  MtAction
        ACCESS  read-write
        STATUS  mandatory
        DESCRIPTION
            "Action to be executed when TextPass receives an MtForwardSm
            operation or SendRoutingInfoForSm operation with an SMSC address
            at MAP level that cannot be associated with any of the defined
            mobile network entities. Default action is
            'blockWithNoResponse'."
        ::= { fwProperties 2 }

    fwPropMtActionForConflictingAddress OBJECT-TYPE
        SYNTAX  MtAction
        ACCESS  read-write
        STATUS  mandatory
        DESCRIPTION
            "Action to be executed when TextPass receives an operation with
            SMSC address at SCCP level that belongs to another network than
            the SMSC address at MAP level. Default action is
            'blockWithNoResponse'."
        ::= { fwProperties 3 }

    fwPropMtActionForUnsolicitedMtFwdSm OBJECT-TYPE
        SYNTAX  MtAction
        ACCESS  read-write
        STATUS  mandatory
        DESCRIPTION
            "Action to be executed when TextPass receives an MtForwardSm
            operation that can not be related to a previously received
            SendRoutingInfoForSm operation. The action only pertains to
            MtForwardSm operations that satisfy the following two conditions:
            - recipient of the MT/SM is a subscriber of the operator's own
              network
            - SMSC is not trusted
            The value 'pass' is not supported. Default action is
            'blockWithNoResponse'."
        ::= { fwProperties 4 }

    fwPropMtActionForMapSmscAddressSpoofing OBJECT-TYPE
        SYNTAX  MtAction
        ACCESS  read-write
        STATUS  mandatory
        DESCRIPTION
            "Action to be executed when TextPass receives an MtForwardSm
            operation with an SMSC address at MAP level from another country
            or mobile network than the SMSC address at MAP level used in the
            relating SendRoutingInfoForSm operation. The action only pertains
            to MtForwardSm operations that satisfy the following two
            conditions:
            - recipient of the MT/SM is a subscriber of the operator's own
              network
            - SMSC is not trusted
            Default action is 'blockWithNoResponse'."
        ::= { fwProperties 5 }

    fwPropMtActionForSccpSmscAddressSpoofing OBJECT-TYPE
        SYNTAX  MtAction
        ACCESS  read-write
        STATUS  mandatory
        DESCRIPTION
            "Action to be executed when TextPass receives an MtForwardSm
            operation with an SMSC address at SCCP level from another country
            or mobile network than the SMSC address at MAP level used in the
            relating SendRoutingInfoForSm operation. The action only pertains
            to MtForwardSm operations that satisfy the following two
            conditions:
            - recipient of the MT/SM is a subscriber of the operator's own
              network
            - SMSC is not trusted
            Default action is 'blockWithNoResponse'."
        ::= { fwProperties 6 }

    fwPropMoActionForOriginatingAddressSpoofing OBJECT-TYPE
        SYNTAX  MoSpoofingAction
        ACCESS  read-write
        STATUS  mandatory
        DESCRIPTION
            "Action to be executed when TextPass receives an MoForwardSm
            operation with an originating address that has been spoofed. The
            values supported are: 'discardWithNak', 'discardWithAck',
            'discardWithNoResponse' and 'pass'.
            Default action is 'discardWithNoResponse'."
        ::= { fwProperties 11 }

    fwPropMoActionForSpoofingCheckFailureDueToCallBarred OBJECT-TYPE
        SYNTAX  SpoofErrorAction
        ACCESS  read-write
        STATUS  mandatory
        DESCRIPTION
            "Action to be executed when MO spoofing check fails with a call 
            barred error. Default action is 'treatAsIfSpoofing'."
        ::= { fwProperties 12 }

    fwPropMoActionForSpoofingCheckFailureDueToTsvcNotProv OBJECT-TYPE
        SYNTAX  SpoofErrorAction
        ACCESS  read-write
        STATUS  mandatory
        DESCRIPTION
            "Action to be executed when MO spoofing check fails with a 
            teleservice not provisioned error. Default action is 
            'treatAsIfSpoofing'."
        ::= { fwProperties 13 }

    fwPropMoFwdSmWithSpoofingThreshold OBJECT-TYPE
        SYNTAX  INTEGER(0..1000000)
        ACCESS  read-write
        STATUS  mandatory
        DESCRIPTION
            "Threshold uppon which a trap is generated to
             indicate that the number of incoming MO spoofing 
             attempts exceeds the provisioned threshold. Range
             is 0 to 1000000. 0 (default) means disable checking."
    ::= { fwProperties 14 }
    
    fwPropMoFwdSmWithSpoofingPeriod OBJECT-TYPE
        SYNTAX  INTEGER(1..86400)
        ACCESS  read-write
        STATUS  mandatory
        DESCRIPTION
            "Period within which the fwPropMoFwdSmWithSpoofingThreshold
             is checked. Range is 1 to 86400, default 3600 (second)."
    ::= { fwProperties 15 }
    
    fwPropMtFwdSmWithSpoofingThreshold OBJECT-TYPE
        SYNTAX  INTEGER(0..1000000)
        ACCESS  read-write
        STATUS  mandatory
        DESCRIPTION
            "Threshold upon which a trap is generated to
             indicate that the number of incoming MT spoofing 
             attempts exceeds the provisioned threshold. Range
             is 0 to 1000000. 0 (default) means disable checking."
    ::= { fwProperties 16 }
    
    fwPropMtFwdSmWithSpoofingPeriod OBJECT-TYPE
        SYNTAX  INTEGER(1..86400)
        ACCESS  read-write
        STATUS  mandatory
        DESCRIPTION
            "Period within which the fwPropMtFwdSmWithSpoofingThreshold
             is checked. Range is 1 to 86400, default 3600 (second)."
    ::= { fwProperties 17 }

    fwPropAcceptNonNumericMtOriginatorMsisdn OBJECT-TYPE
        SYNTAX  Boolean
        ACCESS  read-write
        STATUS  mandatory
        DESCRIPTION
            "Boolean switch to accept non-numeric originator MSISDNs in
            incoming MT messages. By default, non-numeric originator MSISDNs
            are rejected (false).
            Note that this switch does not affect the handling of alphanumeric
            originators, but the handling of numeric MSISDNs that contain any
            of the non-decimal digits a-f. If the switch is set to allow
            non-numeric originator MSISDNs, then the format of the originator
            must not be changed (by means of an MT modifier. Attempting to do
            so will lead to misformatted outgoing MT traffic. See also
            bilPropFcdrAlphanumericFormatInConstruct."
    ::= { fwProperties 18 }

    fwPropMaxIntervalBetweenSriSmAndMtFwdSm OBJECT-TYPE
        SYNTAX  MtTimer
        ACCESS  read-write
        STATUS  mandatory
        DESCRIPTION
            "Maximum time span allowed between an SendRoutingInfoForSm
            operation and a MtForwardSm operation. Expressed in number of
            seconds. Default is 60."
        ::= { fwProperties 21 }

    fwPropMoSpoofingCheckCondition OBJECT-TYPE
        SYNTAX MoSpoofingCheckCondition
        ACCESS  read-write
        STATUS  mandatory
        DESCRIPTION
            "Condition to be satisfied in order to trigger TextPass to check
            on MO spoofing. Default is 'always'."
        ::= { fwProperties 22 }

    fwPropMoSpoofingHlrQueryCeiling OBJECT-TYPE
        SYNTAX Throughput
        ACCESS  read-write
        STATUS  mandatory
        DESCRIPTION
            "Maximum number of HLR queries that TextPass may issue as a
            result of check for MO spoofing. Default is 65535."
        ::= { fwProperties 23 }

    fwPropAssumeProperTimeZoneGeneratingBySmsc OBJECT-TYPE
        SYNTAX  Boolean
        ACCESS  read-write
        STATUS  mandatory
        DESCRIPTION
            "Boolean specifies whether the timezone of an inbound MT/SM
            should be considered as valid. When set to 'true', the assumption
            is that the SMSC generates proper timezones. When set to 'false',
            the assumption is that the SMSC does not generate proper
            timezones. The latter is often the case. Operators only rarely
            modify the timezone settings to reflect their situation. Note
            that some SMSC brands do not automatically change the timezone at
            the point that daylight saving becomes active or inactive. The
            result is that the timezone needs to be changed explicitly at
            each daylight saving transition by the operator, which is likely
            to be forgotten at occasions.
            This attribute allows to select the basis of the correction of
            the timezone (using the MT modifier). When set to 'false', which
            is the default, the timezone of TextPass is taken as a base. When
            set to 'true', the timezone as specified by the SMSC is taken as
            a base."
        ::= { fwProperties 24 }

    fwPropEnableMtRtgRuleEvaluationForSriSmResponse  OBJECT-TYPE
        SYNTAX  Boolean
        ACCESS  read-write
        STATUS  mandatory
        DESCRIPTION
            "Boolean specifying whether the MT routing rules should be
            evaluated for the response of the SendRoutingInfoForSm operation.
            When set to 'true', the MT routing rules are evaluated for the
            response of the SendRoutingInfoForSm operation. When set to
            'false', the MT routing rules are not evaluated for the response
            of the SendRoutingInfoForSm operation. Default is 'false'."
        ::= { fwProperties 25 }
    
    fwPropMultiSimServiceEnabled OBJECT-TYPE
        SYNTAX  Boolean
        ACCESS  read-write
        STATUS  mandatory
        DESCRIPTION
            "Boolean specifying whether support for the multi-SIM service is
            to be enabled. When set to 'true', the firewall will only report
            a case of spoofing when the originator as well as any alias as
            defined on the HLR fails the spoof check. When set to 'false',
            the firewall will do the spoof check on the originator only.
            Default is 'false'."
        ::= { fwProperties 26 }

    fwPropTrustedSmscList OBJECT-TYPE
        SYNTAX  NameString
        ACCESS  read-write
        STATUS  mandatory
        DESCRIPTION
            "Name of a list that specifies the addresses of the SMSC that
            should be regarded as trusted. In order for an SMSC to be
            considered as trusted, the GT within the SCCP calling party
            address as well as the MAP-SMSC address within an
            SendRoutingInfoForSm or MtForwardSm operation need to be on the
            trusted SMSC list."
        ::= { fwProperties 27 }

    fwPropMoSpoofingDigits OBJECT-TYPE
        SYNTAX      GtDigitCount
        ACCESS      read-write
        STATUS      mandatory
        DESCRIPTION 
            "Number of digits from the beginning of the MSC GT used for the 
            MO spoofing check. Any further digits may differ, and no spoofing 
            is detected. Default is 4."
        ::= { fwProperties 28 }

    fwPropUssdRequestForRetrievingMultiSimStatus OBJECT-TYPE
        SYNTAX      UssdString
        ACCESS      read-write
        STATUS      mandatory
        DESCRIPTION 
            "String that is to be used in the USSD request that checks
            whether or not an MSISDN is subscribed to the multi-SIM service.
            Default is '*137#'. When the string is not specified, no USSD
            request is issued."
        ::= { fwProperties 29 }

    fwPropUssdResponseForMultiSimStatusDisabled OBJECT-TYPE
        SYNTAX      UssdString
        ACCESS      read-write
        STATUS      mandatory
        DESCRIPTION 
            "String that the HLR returns in the USSD response to indicates
            that an MSISDN is not subscribed to the multi-SIM service.
            Default is 'NOT SUCCESSFUL'."
        ::= { fwProperties 30 }

    --  fwProperties 31 

    fwPropMoFwdSmSccpCdpaGtaiWhiteList OBJECT-TYPE
        SYNTAX  NameString
        ACCESS  read-write
        STATUS  mandatory
        DESCRIPTION
            "Name of a list with MSISDN-s that should be matched with the
            SMSC GT as specified in the SCCP CDPA of an inbound MoForwardSm
            operation. If a name has been specified for the list and a match
            has been found, the MoForwardSm operation will be sent
            transparently to the SMSC. If no name has been specified for the
            list or no match has been found, TextPass will process the
            MoForwardSm operation."
        ::= { fwProperties 32 }

    fwPropCheckMoSpoofingAfterExtCondRules OBJECT-TYPE
        SYNTAX  Boolean
        ACCESS  read-write
        STATUS  mandatory
        DESCRIPTION
            "Indicator specifying that MO spoofing is only checked before or
            after the evaluation of the MO External Condition (MOX) rules.
            When set to 'false', the spoofing check precedes the evaluation
            of MOX rules. When set to 'true', the spoofing check is done
            after the evaluation of MOX rules.
            Default is 'false'."
        ::= { fwProperties 34 }

    fwPropMoSpoofingSriSmMscOrSgsnWhiteList1 OBJECT-TYPE
        SYNTAX  NameString
        ACCESS  read-write
        STATUS  mandatory
        DESCRIPTION
            "Name of first list with MSISDN-s that should be matched with the 
            MSC or SGSN as returned by the SendRoutingInfoForSm operation that 
            has been issued for the MO spoofing check.
            If the MSC or SGSN matches with an MSISDN on the list, the MO 
            spoof check is considered to be successfully passed."
        ::= { fwProperties 35 }

    fwPropExtAttrForMoSpoofingSriSmMscOrSgsnWhiteList1 OBJECT-TYPE
        SYNTAX  ExtAttrId
        ACCESS  read-write
        STATUS  mandatory
        DESCRIPTION
            "Index of external attribute that will be set when MSC or SGSN
            as returned by the SendRoutingInfoForSm operation that has been 
            issued for the MO spoofing check matches with an MSISDN of the 
            list specified by fwPropMoSpoofingSriSmMscOrSgsnWhiteList1.
            Default value is 0, implying that no external attribute will be
            set."
        ::= { fwProperties 36 }

    fwPropMoSpoofingSriSmMscOrSgsnWhiteList2 OBJECT-TYPE
        SYNTAX  NameString
        ACCESS  read-write
        STATUS  mandatory
        DESCRIPTION
            "Name of second list with MSISDN-s that should be matched with the
            MSC or SGSN as returned by the SendRoutingInfoForSm operation that 
            has been issued for the MO spoofing check.
            If the MSC or SGSN matches with an MSISDN on the list, the MO 
            spoof check is considered to be successfully passed."
        ::= { fwProperties 37 }

    fwPropExtAttrForMoSpoofingSriSmMscOrSgsnWhiteList2 OBJECT-TYPE
        SYNTAX  ExtAttrId
        ACCESS  read-write
        STATUS  mandatory
        DESCRIPTION
            "Index of external attribute that will be set when MSC or SGSN
            as returned by the SendRoutingInfoForSm operation that has been 
            issued for the MO spoofing check matches with an MSISDN of the 
            list specified by fwPropMoSpoofingSriSmMscOrSgsnWhiteList2.
            Default value is 0, implying that no external attribute will be
            set."
        ::= { fwProperties 38 }

    fwPropNoSpoofCheckWhiteListedRecipientImsi OBJECT-TYPE
        SYNTAX  OCTET STRING
        ACCESS  read-write
        STATUS  mandatory
        DESCRIPTION
            "Comma separated list of IMSI prefixes for which the firewall 
            will bypass spoof checks. For example   2341655,234161234   
            means all IMSI numbers that begin with 2341655 or 234161234. 
            IMSI ranges so specified must not overlap with the Scrambling 
            Ranges in the mtScramblingTable."
        ::= { fwProperties 39 }

    fwPropReportUnknownSmscAddressNotifications OBJECT-TYPE
        SYNTAX  EventReportingType
        ACCESS  read-write
        STATUS  mandatory
        DESCRIPTION
            "Indicator specifying how to report that an SendRoutingForSm or
            MtForwardSm operation is received with an unknown SCCP or MAP 
            address for the SMSC. The default is 'asTrap'."
        ::= { fwProperties 41 }

    fwPropMoFwdSmBeginWithoutComponentCdpaList OBJECT-TYPE
        SYNTAX  ListTableRef
        ACCESS  read-write
        STATUS  mandatory
        DESCRIPTION
            "SNMP index of a list with MSISDN-s that should be matched with
            the Called Party address (Cdpa) found in received BEGIN without
            component for MO/SM messages. If the list matches (also see
            fwPropMoFwdSmBeginWithoutComponentCdpaListType), the BEGIN
            without component message will be forwarded to the Cdpa
            transparently. This object will only be effective when
            referring to an existing, active list of the listTable.
            By default, no list is referred to (value 0)."
        ::= { fwProperties 42 }

    fwPropMoFwdSmBeginWithoutComponentCdpaListType OBJECT-TYPE
        SYNTAX  ListType
        ACCESS  read-write
        STATUS  mandatory
        DESCRIPTION
            "This parameter controls whether the
            fwPropMoFwdSmBeginWithoutComponentCdpaList, when in use, shall be
            used as a blacklist or a whitelist. By default, the list shall be
            used as a whitelist."
        ::= { fwProperties 43 }

    fwPropMscSgsnAddressInSuspectSriSmResponse OBJECT-TYPE
        SYNTAX  GsmAddress
        ACCESS  read-write
        STATUS  mandatory
        DESCRIPTION
            "Address, specified in international format, which is returned to
            the SMSC for MSC/SGSN in a SendRoutingInfoForSm response when
            acting in suspect mode. When no address is specified, which is
            the default, the TextPass GT is used."
        ::= { fwProperties 51 }    

    fwPropUseHlrAddressAsSccpCgPaInSuspectSriSmResponse OBJECT-TYPE
        SYNTAX  Boolean
        ACCESS  read-write
        STATUS  mandatory
        DESCRIPTION
            "Indicator specifying that the HLR address is to be used as SCCP 
            calling party address for the SendRoutingInfoForSm response. When
            set to FALSE, which is the default, the TextPass GT is used."
        ::= { fwProperties 52 }    

    fwPropMnpRoutingNumberForOwnNetwork OBJECT-TYPE
        SYNTAX  GsmAddress
        ACCESS  read-write
        STATUS  mandatory
        DESCRIPTION
            "Routing number (RN) as used in the SCCP called party address for 
            operations towards the HLR when MNP is in use. An RN is typically
            a three digits number that is squeezed in a GT between the country
            code and the national significant number (e.g. the number 
            31627093038 with the RN of 014 results in 31014627093038).
            Any operation that contains a routing number which is different 
            from the specified routing number, is returned to the STP. 
            TextPass only accepts RN not starting with a 0."
        ::= { fwProperties 53 }    

    fwPropUseCommonAddressInSuspectMtForwardSm OBJECT-TYPE
        SYNTAX  Boolean
        ACCESS  read-write
        STATUS  mandatory
        DESCRIPTION
            "Indicator specifying that the SMSC address at MAP layer in a
            suspect MtForwardSm request is to be replaced with the common
            address that is assigned for TextPass. When set to 'true', the
            SMSC address at MAP layer is replaced. When set to 'false', which
            is the default, the SMSC address is not replaced."
        ::= { fwProperties 54 }    

    fwPropRepublishSriSmNetworks OBJECT-TYPE
        SYNTAX  RepublishSriSmNetworks
        ACCESS  read-write
        STATUS  mandatory
        DESCRIPTION
            "String specifying the networks for which republishing a 
            SendRoutingInfoForSm is applicable. Republishing implies that the 
            firewall re-issues the SendRoutingInfoForSm request after it has
            received the SendRoutingInfoForSm response from the HLR and it 
            turns out that the MSISDN has ported to one of the specified 
            networks. Goal of republishing is to handle the case of multiple 
            networks within a country deploying a firewall and at least one 
            network having the firewall before the MNP/SRF. 
            When a SendRoutingInfoForSm request is republished, it is issued 
            with:
            - SCCP CGPA equal to SCCP CGPA as specified in the 
              SendRoutingInfoForSm request from the SMSC. 
            - SCCP CDPA equal to the SCCP CGPA as specified in the 
              SendRoutingInfoForSm response from the HLR. 
            When this object is assigned a value, it is implicitly assumed
            that republishing is applicable for all SendRoutingInfoForSm
            requests that are classified as suspect. For suspect
            SendRoutingInfoForSm requests, republishing is done whenever the
            network as associated with the IMSI is equal to one of the
            specified networks.
            Republishing of trusted SendRoutingInfoForSm requests is
            controlled by the
            fwPropEnableSriSmRepublishingForTrustedSmscList.            
            Refer to the description on the RepublishSriSmNetworks type, for
            the format of the string.
            Note that specification of a network that cannot be matched with
            an entry in the mobNetworkTable will not be rejected."
        ::= { fwProperties 61 }    
    
    fwPropEnableSriSmRepublishingForTrustedSmscList OBJECT-TYPE
        SYNTAX  Boolean
        ACCESS  read-write
        STATUS  mandatory
        DESCRIPTION
            "Indicator specifying whether a SendRoutingInfoForSm request as
            issued by an SMSC from the trusted list needs to be re-published
            in case the SendRoutingInfoForSm response indicates that the
            MSISDN has ported out. 
            Note that republishing as result of this object is restricted 
            in the sense that:
            - This object only applies to trusted SMSC-s that are on the
              trusted list. This object excludes any SMSC that is classified
              as trusted as result of another criterion (i.e. OPC of
              SendRouting not being an STP).
            - Re-publishing for SMSC-s of the trusted list only occurs if the 
              MSISDN has ported to one of the networks that is specified by 
              fwPropRepublishSriSmNetworks. This is determined by verifying 
              whether the network associated by the MSISDN is equal to own 
              network and network associated with IMSI is equal to one of the 
              networks specified by fwPropRepublishSriSmNetworks.
            Default value for this object is 'false'."
        ::= { fwProperties 62 }   
    
    fwPropRepublishSrismCdpaSetSameAsInitialSrism OBJECT-TYPE
        SYNTAX  Boolean
        ACCESS  read-write
        STATUS  mandatory
        DESCRIPTION
            "For a republish SRISM message the SCCP CdPA is usually set to 
            the CgPA of the immediately preceding response message. This 
            flag changes this behavior to force the SCCP CdPA to be the 
            same as that of the first SRISM in the dialog."
        ::= { fwProperties 63 }

    fwTrapInfo OBJECT IDENTIFIER ::= { sms 9 }

    fwTrapUnknownSccpSmscAddress OBJECT-TYPE
        SYNTAX  GsmAddress
        ACCESS  read-write
        STATUS  mandatory
        DESCRIPTION
            "SMSC address at SCCP layer that could not be associated with any
             of the defined mobile networks."
        ::= { fwTrapInfo 1 }

    fwTrapUnknownMapSmscAddress OBJECT-TYPE
        SYNTAX  GsmAddress
        ACCESS  read-write
        STATUS  mandatory
        DESCRIPTION
            "SMSC address at MAP layer that could not be associated with any
             of the defined mobile networks."
        ::= { fwTrapInfo 2 }

    fwTrapConflictingSccpSmscAddress OBJECT-TYPE
        SYNTAX  GsmAddress
        ACCESS  read-write
        STATUS  mandatory
        DESCRIPTION
            "SMSC address at SCCP layer that conflicts with address at MAP
             layer."
        ::= { fwTrapInfo 3 }

    fwTrapConflictingMapSmscAddress OBJECT-TYPE
        SYNTAX  GsmAddress
        ACCESS  read-write
        STATUS  mandatory
        DESCRIPTION
            "SMSC address at MAP layer that conflicts with address at SCCP
             layer."
        ::= { fwTrapInfo 4 }

    fwTrapSccpSmscAddressInSriSm OBJECT-TYPE
        SYNTAX  GsmAddress
        ACCESS  read-write
        STATUS  mandatory
        DESCRIPTION
            "SMSC address at SCCP layer specified in SendRoutingInfoForSm
            operation that conflicts with address used in MtForwardSm
            operation."
        ::= { fwTrapInfo 5 }

    fwTrapSccpSmscAddressInMtFwdSm OBJECT-TYPE

        SYNTAX  GsmAddress
        ACCESS  read-write
        STATUS  mandatory
        DESCRIPTION
            "SMSC address at SCCP layer specified in MtForwardSm operation
            that conflicts with address used in SendRoutingInfoForSm
            operation."
        ::= { fwTrapInfo 6 }

    fwTrapMapSmscAddressInSriSm OBJECT-TYPE
        SYNTAX  GsmAddress
        ACCESS  read-write
        STATUS  mandatory
        DESCRIPTION
            "SMSC address at MAP layer specified in SendRoutingInfoForSm
            operation that conflicts with address used in MtForwardSm
            operation."
        ::= { fwTrapInfo 7 }

    fwTrapMapSmscAddressInMtFwdSm OBJECT-TYPE
        SYNTAX  GsmAddress
        ACCESS  read-write
        STATUS  mandatory
        DESCRIPTION
            "SMSC address at MAP layer specified in MtForwardSm operation that
            conflicts with address used in SendRoutingInfoForSm operation."
        ::= { fwTrapInfo 8 }

    fwTrapOriginatorAddressInMoFwdSm OBJECT-TYPE
        SYNTAX  GsmAddress
        ACCESS  read-write
        STATUS  mandatory
        DESCRIPTION
            "Originator address specified in MoForwardSm operation that has
            been spoofed."
        ::= { fwTrapInfo 9 }

    fwTrapMscOrSgsnAddressInMoFwdSm OBJECT-TYPE
        SYNTAX  GsmAddress
        ACCESS  read-write
        STATUS  mandatory
        DESCRIPTION
            "MSC/SGSN address specified in MoForwardSm operation that possibly
            conflicts with MSC/SGSN address according to HLR."
        ::= { fwTrapInfo 10 }

    fwTrapMscOrSgsnAddressInSriSm OBJECT-TYPE
        SYNTAX  GsmAddress
        ACCESS  read-write
        STATUS  mandatory
        DESCRIPTION
            "MSC/SGSN address that has been retrieved from HLR using a
            SendRoutingInfoForSm operation and that possibly conflicts with
            the MSC/SGSN address specified in MoForwardSm."
        ::= { fwTrapInfo 11 }

    fwTrapImsiInMoFwdSm OBJECT-TYPE
        SYNTAX  GsmAddress
        ACCESS  read-write
        STATUS  mandatory
        DESCRIPTION
            "IMSI specified in MoForwardSm operation that possibly conflicts
            with IMSI according to HLR."
        ::= { fwTrapInfo 12 }

    fwTrapImsiInSriSm OBJECT-TYPE
        SYNTAX  GsmAddress
        ACCESS  read-write
        STATUS  mandatory
        DESCRIPTION
            "IMSI that has been retrieved from HLR using a
            SendRoutingInfoForSm operation and that possibly conflicts with
            the IMSI specified in MoForwardSm."
        ::= { fwTrapInfo 13 }

    moSmTrustedOriginatorTable OBJECT-TYPE
        SYNTAX  SEQUENCE OF MoSmTrustedOriginatorEntry
        ACCESS  not-accessible
        STATUS  mandatory
        DESCRIPTION
            "A table specifying lists with with MO/SM Trusted Originators."
        ::= { sms 10 }


    moSmTrustedOriginatorEntry OBJECT-TYPE
        SYNTAX  MoSmTrustedOriginatorEntry
        ACCESS  not-accessible
        STATUS  mandatory
        DESCRIPTION
            "Table entry specifying a list with MO/SM Trusted Originators."
        INDEX   { moSmTrustedOriginatorIndex }
        ::= { moSmTrustedOriginatorTable 1 }

    MoSmTrustedOriginatorEntry ::=
        SEQUENCE {
            moSmTrustedOriginatorIndex        MoSmTrustedOriginatorTableIndex,
            moSmTrustedOriginatorList         NameString
        }

    moSmTrustedOriginatorIndex OBJECT-TYPE
        SYNTAX  MoSmTrustedOriginatorTableIndex
        ACCESS  read-write
        STATUS  mandatory
        DESCRIPTION
            "Index of entry in MO/SM Trusted Originator table."
        ::= { moSmTrustedOriginatorEntry 1 }

    moSmTrustedOriginatorList OBJECT-TYPE
        SYNTAX  NameString
        ACCESS  read-write
        STATUS  mandatory
        DESCRIPTION
            "Name of a list with MSISDN-s that should be matched with the
            originator MSISDN as specified in an moForwardSM operation.
            If the originator matches with an MSISDN on the list, the MO/SM 
            is always considered as trusted."
        ::= { moSmTrustedOriginatorEntry 2 }

    moRtgRuleTable OBJECT-TYPE
        SYNTAX  SEQUENCE OF MoRtgRuleEntry
        ACCESS  not-accessible
        STATUS  mandatory
        DESCRIPTION
            "A table containing properties, conditions, counters and action
            parameters for each MO routing rule. When the action for an MO
            routing rule involves routing to an SMSC, a subordinate table
            moRtgRuleSmscTable contains the related action parameters.

            An MO routing rule matches when both of the following conditions
            are met:
            1) its administrative state is active;
            2) all its conditions do satisfy;

            In case multiple rules match, the priority of the MO routing rule
            determines which rule applies. When multiple rules have the same
            priority, the MO routing rule with the lowest index has
            precedence."
        ::= { sms 11 }


    moRtgRuleEntry OBJECT-TYPE
        SYNTAX  MoRtgRuleEntry
        ACCESS  not-accessible
        STATUS  mandatory
        DESCRIPTION
            "Table entry specifying a single MO routing rule."
        INDEX   { moRtgRuleIndex }
        ::= { moRtgRuleTable 1 }

    MoRtgRuleEntry ::=
        SEQUENCE {
            moRtgRuleIndex                        MoRtgRuleTableIndex,
            moRtgRuleAdminState                   AdminState,
            moRtgRuleName                         NameString,
            moRtgRulePriority                     Priority,
            moRtgRuleAppliedCounter               Counter,
            moRtgRuleFallbackAppliedCounter       Counter,
            moRtgRuleSuccessOnPrimaryCounter      Counter,                               
            moRtgRuleFailureOnPrimaryCounter      Counter,                               
            moRtgRuleSuccessOnFallbackCounter     Counter,                               
            moRtgRuleFailureOnFallbackCounter     Counter,                               
            moRtgRuleFallbackNotAppliedDueToPermanentErrorOnPrimaryCounter Counter,      
            moRtgRuleFallbackNotAppliedDueToUnavailabilityCounter Counter,               
            moRtgRuleAction                       MoAction,
            moRtgRuleModifier                     MoModifierRef,
            moRtgRuleApplication                  ApplicationTableIndex,
            moRtgRuleLoadBalancingGroup           LoadBalancingGroupReference,
            moRtgRuleDecimation                   Decimation,
            moRtgRuleAlwaysRespondWithAck         Boolean,
            moRtgRuleAmsQueue                     AmsQueueIndex,
            moRtgRuleCdpaBasedForwarding          Boolean,
            moRtgRuleTransparentForwarding        TransparentForwarding,
            moRtgRuleOriginatorCondition          ConditionSpec,
            moRtgRuleRecipientCondition           ConditionSpec,
            moRtgRuleSmscCondition                ConditionSpec,
            moRtgRuleMscOrSgsnCondition           ConditionSpec,
            moRtgRuleUserDataCondition            ConditionSpec,
            moRtgRuleUserDataHeaderCondition      ConditionSpec,
            moRtgRuleReplyPathCondition           ConditionSpec,
            moRtgRuleStatusReportRequestCondition ConditionSpec,
            moRtgRuleProtocolIdCondition          ConditionSpec,
            moRtgRuleDataCodingSchemeCondition    ConditionSpec,
            moRtgRuleRecipientTonCondition        ConditionSpec,
            moRtgRuleRecipientNpiCondition        ConditionSpec,
            moRtgRuleExternalAttributesCondition  ConditionSpec,
            moRtgRuleSubmitTimeCondition          ConditionSpec,
            moRtgRuleRecipientQueryResultCondition ConditionSpec,
            moRtgRuleRecipientRoutingNumberGroupCondition ConditionSpec,
            moRtgRuleOriginatorHlrCondition       ConditionSpec,
            moRtgRuleBilProfileForSubmission      BilProfile,
            moRtgRuleBilProfileForSuccessfulDelivery BilProfile,
            moRtgRuleBilProfileForFailedDelivery  BilProfile,
            moRtgRuleBilProfileForSuccessfulDeliveryOnFallback BilProfile,
            moRtgRuleBilProfileForFailedDeliveryOnFallback BilProfile,
            moRtgRuleBilProfileForDeliveryNotification BilProfile,
            moRtgRuleLogProfile                   LogProfile
        }

    moRtgRuleIndex OBJECT-TYPE
        SYNTAX  MoRtgRuleTableIndex
        ACCESS  read-write
        STATUS  mandatory
        DESCRIPTION
            "Index of entry in MO routing rule table."
        ::= { moRtgRuleEntry 1 }

    moRtgRuleAdminState OBJECT-TYPE
        SYNTAX  AdminState
        ACCESS  read-write
        STATUS  mandatory
        DESCRIPTION
            "Administrative state of the MO routing rule.

            Transition from 'inactive' to 'active' is only possible when:
            1) name has been supplied;
            2) name is not already in use by another rule;
            3) conditions of rule specifying a network refer to an 'active'
               country and an 'active' network;
            4) conditions of rule specifying a country refer to an 'active'
               country;
            5) conditions of rule specifying an application refer to an
               'active' application;
            6) in case routing to application, application being referred to
               exists;
            7) in case modifier specified, modifier being referred to exists.

            For details, refer to the comment on the AdminState type."
        ::= { moRtgRuleEntry 2 }

    moRtgRuleName OBJECT-TYPE
        SYNTAX  NameString
        ACCESS  read-write
        STATUS  mandatory
        DESCRIPTION
            "Name of the MO routing rule."
        ::= { moRtgRuleEntry 3 }

    moRtgRulePriority OBJECT-TYPE
        SYNTAX  Priority
        ACCESS  read-write
        STATUS  mandatory
        DESCRIPTION
            "Priority of the SMS routing rule.
            For details, refer to the comment on the Priority type."
        ::= { moRtgRuleEntry 4 }


    moRtgRuleAppliedCounter OBJECT-TYPE
        SYNTAX  Counter
        ACCESS  read-write
        STATUS  mandatory
        DESCRIPTION
            "Counter specifying the number of times that the routing rule
            has been applied."
        ::= { moRtgRuleEntry 11 }

    moRtgRuleFallbackAppliedCounter OBJECT-TYPE
        SYNTAX  Counter
        ACCESS  read-write
        STATUS  mandatory
        DESCRIPTION
            "Counter specifying the number of times that the fallback
            destination of the routing rule has been applied."
        ::= { moRtgRuleEntry 12 }

    moRtgRuleSuccessOnPrimaryCounter OBJECT-TYPE
        SYNTAX  Counter
        ACCESS  read-write
        STATUS  mandatory
        DESCRIPTION
            "Counter specifying the number of times that an MO/SM has been
            successfully routed to the primary destination of the routing
            rule."
        ::= { moRtgRuleEntry 13 }

    moRtgRuleFailureOnPrimaryCounter OBJECT-TYPE
        SYNTAX  Counter
        ACCESS  read-write
        STATUS  mandatory
        DESCRIPTION
            "Counter specifying the number of times that an MO/SM has not
            been successfully routed to the primary destination of the
            routing rule."
        ::= { moRtgRuleEntry 14 }

    moRtgRuleSuccessOnFallbackCounter OBJECT-TYPE
        SYNTAX  Counter
        ACCESS  read-write
        STATUS  mandatory
        DESCRIPTION
            "Counter specifying the number of times that an MO/SM has been
            successfully routed to the fallback destination of the routing
            rule."
        ::= { moRtgRuleEntry 15 }

    moRtgRuleFailureOnFallbackCounter OBJECT-TYPE
        SYNTAX  Counter
        ACCESS  read-write
        STATUS  mandatory
        DESCRIPTION
            "Counter specifying the number of times that an MO/SM has not
            been successfully routed to the fallback destination of the
            routing rule."
        ::= { moRtgRuleEntry 16 }

    moRtgRuleFallbackNotAppliedDueToPermanentErrorOnPrimaryCounter OBJECT-TYPE
        SYNTAX  Counter
        ACCESS  read-write
        STATUS  mandatory
        DESCRIPTION
            "Counter specifying the number of times that routing an MO/SM has
            failed on the primary destination with a permanent error."
        ::= { moRtgRuleEntry 17 }

    moRtgRuleFallbackNotAppliedDueToUnavailabilityCounter OBJECT-TYPE
        SYNTAX  Counter
        ACCESS  read-write
        STATUS  mandatory
        DESCRIPTION
            "Counter specifying the number of times that routing an MO/SM to
            the fallback destination was not possible because of
            unavailability of the fallback destination."
        ::= { moRtgRuleEntry 18 }
  
    moRtgRuleAction OBJECT-TYPE
        SYNTAX  MoAction
        ACCESS  read-write
        STATUS  mandatory
        DESCRIPTION
            "Action to execute when the MO routing rule applies.

            For details, refer to the comments on the MoAction type."
        ::= { moRtgRuleEntry 21 }

    moRtgRuleModifier OBJECT-TYPE
        SYNTAX  MoModifierRef
        ACCESS  read-write
        STATUS  mandatory
        DESCRIPTION
            "Reference to a modifier which is carried out when MO routing rule
            applies and action of MO routing rule is equal to

            routeToSmsc,
            routeToApplication,
            routeToMsFallbackToSmsc,
            routeToApplicationFallbackToStorage,
            storeForDeliveryToApplication, 
            routeToMsFallbackToStorage,
            storeForDeliveryToMs, 
            routeToMsFallbackToApplication,
            routeToSmscAsAo, 
            routeToMsFallbackToSmscAsAo and
            discardWithAck.

            Note that for the action of forwarding an MO message as MO/SM,
            modifiers can also be assigned to the message through the
            moRtgRuleSmscTable."
        ::= { moRtgRuleEntry 22 }

    moRtgRuleApplication OBJECT-TYPE
        SYNTAX  ApplicationTableIndex
        ACCESS  read-write
        STATUS  mandatory
        DESCRIPTION
            "Reference to an application. When 0 is specified, the rule
            routes to the application belonging to the short number that is
            specified in an MO/SM as recipient.

            Only applicable when action of MO routing rule is
            routeToApplication,
            routeToMsFallbackToApplication,
            routeToApplicationFallbackToStorage,
            storeForDeliveryToApplication, 
            routeToSmscAsAo,
            routeToMsFallbackToSmscAsAo.
            
            Note that the following applies for the application in case
            action of MO routing rule is routeToSmscAsAo or
            routeToMsFallbackToSmscAsAo:
            Application should have an applicationSessionModel attribute that
            is equal to either 'insideOnlyAllScs' or 'insideOnlyScList'."
        ::= { moRtgRuleEntry 23 }

    moRtgRuleLoadBalancingGroup OBJECT-TYPE
        SYNTAX  LoadBalancingGroupReference
        ACCESS  read-write
        STATUS  mandatory
        DESCRIPTION
            "Reference to a load balancing group. Currently, this parameter
            is only supported for AT-related routing actions such as
            'routeToApplication', 'routeToApplicationFallbackToStorage' and
            'storeForDeliveryToApplication'. Therefore, the load balancing
            group referred to must be of type 'application'.
            When both this field and the application parameter are specified,
            the application parameter overrides this field.
            By default, this parameter is set to 0."
        ::= { moRtgRuleEntry 24 }

    moRtgRuleDecimation OBJECT-TYPE
        SYNTAX  Decimation
        ACCESS  read-write
        STATUS  mandatory
        DESCRIPTION
            "Indicator specifying how many MO/SM's need to be delivered to an
            application and how many may be dropped. Only applicable if
            routing action is routeToApplication and
            routeToApplicationFallbackToStorage. 
            Default is 1/1.

            For details, Refer to comment on the Decimation type."
        ::= { moRtgRuleEntry 25 }

    moRtgRuleAlwaysRespondWithAck OBJECT-TYPE
        SYNTAX  Boolean
        ACCESS  read-write
        STATUS  mandatory
        DESCRIPTION
            "Indicator specifying whether an MO/SM should always be
            positively acknowledged, regardless of the delivery result. Only
            applicable if routing action is routeToApplication, 
            routeToApplicationFallbackToStorage, routeToSmscAsAo
            or routeToMs. Default is false."
        ::= { moRtgRuleEntry 26 }

    moRtgRuleAmsQueue OBJECT-TYPE
        SYNTAX  AmsQueueIndex
        ACCESS  read-write
        STATUS  mandatory
        DESCRIPTION
            "Specifier of an AMS queue.

            Only applicable and mandatory when action of MO routing rule is

            routeToApplicationFallbackToStorage,
            storeForDeliveryToApplication, 
            routeToMsFallbackToStorage,
            storeForDeliveryToMs."
        ::= { moRtgRuleEntry 27 }

    moRtgRuleCdpaBasedForwarding OBJECT-TYPE
        SYNTAX  Boolean
        ACCESS  read-write
        STATUS  mandatory
        DESCRIPTION
            "Indicator specifying whether a to-be-forwarded MO/SM should be
            routed towards the global title found in the Called Party address
            of the incoming MO/SM (when set to true), or to determine the
            target SMSC based on the SMSC's provisioned and linked to the
            MO routing rule based on the moRtgRuleSmsc table (when set to
            false). Currently, this setting is only meaningful in combination
            with the routing action 'routeToSmsc' or
            'routeToMsFallbackToSmsc' Also, when set to true, the rule can
            only match if the received Cdpa indicated routing on global title.
            By default, the flag is set to 'false'."
        ::= { moRtgRuleEntry 28 }

    moRtgRuleTransparentForwarding OBJECT-TYPE
        SYNTAX  TransparentForwarding
        ACCESS  read-write
        STATUS  mandatory
        DESCRIPTION
            "Indicator specifying if the incoming MO/SM should be forwarded
            transparently to an external SMSC. This setting is only considered
            if the moRtgRuleCdpaBasedForwarding flag is turned on. Otherwise,
            the global smsPropOptimisedMoRouting property is respected. For
            more information, consult the description of the
            TransparentForwarding type. By default, this object is set to
            'useGlobalSetting'."
        ::= { moRtgRuleEntry 29 }

    moRtgRuleOriginatorCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) SINGLEIMSI (*)
            7) IMSIRANGE (*)
            8) LIST

            For details on these formats, refer to the comment on the
            type.

            (*) Setting a condition on the IMSI is only possible when the
                setting smsPropAlwaysRetrieveOriginatorImsi is set to 'true'"
        ::= { moRtgRuleEntry 31 }

    moRtgRuleRecipientCondition OBJECT-TYPE
        SYNTAX  ConditionSpec

        ACCESS  read-write
        STATUS  mandatory
        DESCRIPTION
            "Condition pertaining to the recipient that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST
            12) ALPHANUMADDRESS
            
            For details on these formats, refer to the comment on the
            ConditionSpec type."
        ::= { moRtgRuleEntry 32 }

    moRtgRuleSmscCondition OBJECT-TYPE
        SYNTAX  ConditionSpec
        ACCESS  read-write
        STATUS  mandatory
        DESCRIPTION
            "Condition pertaining to the SMSC that is specified in the SM. For
            the specification for this condition, the following formats apply:

            1) NONE
            2) SINGLEMSISDN
            3) MSISDNRANGE
            4) MSISDNPREFIX
            5) LIST

            For details on these formats, refer to the comment on the
            ConditionSpec type."
        ::= { moRtgRuleEntry 33 }

    moRtgRuleMscOrSgsnCondition OBJECT-TYPE
        SYNTAX  ConditionSpec
        ACCESS  read-write
        STATUS  mandatory
        DESCRIPTION
            "Condition pertaining to the originating MSC/SGSN that is
            specified in the SM. For the specification for this condition,
            the following formats apply:

            1) NONE
            2) SINGLEMSISDN
            3) MSISDNRANGE
            4) MSISDNPREFIX
            5) NETWORK
            6) COUNTRY
            7) SINGLEPOINTCODE
            8) POINTCODERANGE
            9) LIST

            For details on these formats, refer to the comment on the
            ConditionSpec type."
        ::= { moRtgRuleEntry 34 }

    moRtgRuleUserDataCondition  OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT

            For details on these formats, refer to the comment on the
            ConditionSpec type."
        ::= { moRtgRuleEntry 35 }

    moRtgRuleUserDataHeaderCondition  OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to GSM 03.40. The
            values for most common information element identifiers are:

            00 hex - Concatenated short message
            01 hex - Special SMS Message Indication
            04 hex - application port addressing scheme, 8 bit address
            05 hex - application port addressing scheme, 16 bit address
            06 hex - SMSC Control Parameters
            07 hex - UDH Source Indicator "
        ::= { moRtgRuleEntry 36 }

    moRtgRuleReplyPathCondition  OBJECT-TYPE
        SYNTAX  ConditionSpec
        ACCESS  read-write
        STATUS  mandatory
        DESCRIPTION
            "Condition pertaining to the reply path bit specified in the SM.
            For the specification for this condition, the following formats
            apply:

            1) NONE
            2) BITVALUE

            For details on these formats, refer to the comment on the
            ConditionSpec type."
        ::= { moRtgRuleEntry 37 }

    moRtgRuleStatusReportRequestCondition  OBJECT-TYPE
        SYNTAX  ConditionSpec
        ACCESS  read-write
        STATUS  mandatory
        DESCRIPTION
            "Condition pertaining to the status report request bit specified
            in the SM. For the specification for this condition, the
            following formats apply:

            1) NONE
            2) BITVALUE

            For details on these formats, refer to the comment on the
            ConditionSpec type."
        ::= { moRtgRuleEntry 38 }

    moRtgRuleProtocolIdCondition  OBJECT-TYPE
        SYNTAX  ConditionSpec
        ACCESS  read-write
        STATUS  mandatory
        DESCRIPTION
            "Condition pertaining to the protocol ID specified in the SM. For
            the specification for this condition, the following formats apply:

            1) NONE
            2) BYTEVALUE

            For details on these formats, refer to the comment on the
            ConditionSpec type.

            For details on the values supported for the protocol ID, refer to
            GSM 03.40."
        ::= { moRtgRuleEntry 39 }


    moRtgRuleDataCodingSchemeCondition  OBJECT-TYPE
        SYNTAX  ConditionSpec
        ACCESS  read-write
        STATUS  mandatory
        DESCRIPTION
            "Condition pertaining to the data coding scheme specified in the
            SM. For the specification for this condition, the following
            formats apply:

            1) NONE
            2) BYTEVALUE

            For details on these formats, refer to the comment on the
            ConditionSpec type.

            For details on the values supported for the data coding scheme,
            refer to GSM 03.38."
        ::= { moRtgRuleEntry 40 }

    moRtgRuleRecipientTonCondition  OBJECT-TYPE
        SYNTAX  ConditionSpec
        ACCESS  read-write
        STATUS  mandatory
        DESCRIPTION
            "Condition pertaining to the type of number (TON) specified for
            the recipient of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { moRtgRuleEntry 41 }

    moRtgRuleRecipientNpiCondition  OBJECT-TYPE
        SYNTAX  ConditionSpec
        ACCESS  read-write
        STATUS  mandatory
        DESCRIPTION
            "Condition pertaining to the numbering plan identification (NPI)
            specified for the recipient of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { moRtgRuleEntry 42 }

    moRtgRuleExternalAttributesCondition  OBJECT-TYPE
        SYNTAX  ConditionSpec
        ACCESS  read-write
        STATUS  mandatory
        DESCRIPTION
            "Condition on the 32 boolean atributes that can be set by an 
            external approval application. For the specification for this 
            condition, the following formats apply:

            1) NONE
            2) EXTERNALATTRIBUTES

            When the format is EXTERNALATTRIBUTES, the relating bit mask
            string specifies which external attributes apply and the relating
            bit value string specifies the values for the external
            attributes.          
            Each bit in the bit strings relates to a specific attribute. The
            bit strings consist of 32 bits. The least significant bit
            corresponds to attribute 0. The most significant bit corresponds
            to attribute 31. 
            A bit with value 1 in the bit mask string indicates that the
            relating attribute applies and needs to be checked. A bit with
            value 0 in the bit mask string indicates that the relating
            attribute does not apply and does not need to be checked. 
            A bit with value 1 in the bit value string indicates that the
            relating attribute should be TRUE. A bit with value 0 in the bit
            value string indicates that the relating attribute should be
            FALSE. 

            For further details on these formats, refer to the comment on the
            ConditionSpec type."
        ::= { moRtgRuleEntry 43 }

    moRtgRuleSubmitTimeCondition OBJECT-TYPE
        SYNTAX  ConditionSpec
        ACCESS  read-write
        STATUS  mandatory
        DESCRIPTION
            "Condition on the submit-time of the message. For the
            specification for this condition, the following formats apply:

            1) NONE
            2) TIMESPEC

            For further details on these formats, refer to the comment on the
            ConditionSpec type."
        ::= { moRtgRuleEntry 44 }

    moRtgRuleRecipientQueryResultCondition OBJECT-TYPE
        SYNTAX  ConditionSpec
        ACCESS  read-write
        STATUS  mandatory
        DESCRIPTION
            "Condition on the result of the HLR query for the recipient. In
            order for the condition to work, the recipient HLR query must
            have been performed before the MO routing rules are matched. This
            can be achieved through the
            smsPropHlrQueryForRecipientBeforeApproval property. For the
            specification for this condition, the following formats apply:

            1) NONE
            2) BITSTRING

            When the format is BITSTRING, the relating bit string specifies
            which HLR query results apply. Each bit in the bit string relates
            to a specific (or group of) query result(s). The (non-inverted)
            condition evaluates to true if the bit corresponding to the HLR
            query result is set to 1. Otherwise, the condition evaluates to
            false.

            Bit   Meaning
            -------------
            1     (any) permanent error
            2     (any) temporary error
            3-5   reserved for future error class types
            6     timeout
            7     system failure
            8     data missing
            9     unexpected data value
            10    facility not supported
            11    unknown subscriber
            12    absent subscriber
            13    call barred
            14    teleservice not provisioned
            15    tcap aborted
            16    sccp aborted
            17    other errors

            By default, the condition is set to NONE.

            The MIB counts from 1, so for example to match against any
            permanent error;

            s00000000000000001

            To match against timeout and data missing;

            s00000000010100000

            Trailing zeros can be omitted."
        ::= { moRtgRuleEntry 45 }

    moRtgRuleRecipientRoutingNumberGroupCondition OBJECT-TYPE
        SYNTAX  ConditionSpec
        ACCESS  read-write
        STATUS  mandatory
        DESCRIPTION
            "Condition on the group to which the routing number associated
            with the recipient address belongs. For the specification for
            this condition, the following formats apply:

            1) NONE
            2) SNMPINDEX

            When the format is SNMPINDEX, the SNMP index will refer to the
            routingNumberGroupTable. The (non-inverted) condition will
            never match if either the routing number group referred to by
            the condition is not active, or if no routing number has been
            determined for the recipient of the message under consideration.
            The RoutingNumberGroupIndex determines the range of valid numbers
            for the SNMP index."
        ::= { moRtgRuleEntry 46 }

    moRtgRuleOriginatorHlrCondition OBJECT-TYPE
        SYNTAX  ConditionSpec
        ACCESS  read-write
        STATUS  mandatory
        DESCRIPTION
            "Condition pertaining to the address of the HLR that is
            serving the originator of the message. In order to meaningfully
            apply this condition, the MNP or spoofing check must be applied
            before the MO rules, such that the HLR address is available to
            the router. For the specification for this condition, the
            following formats apply:

            1) NONE
            2) SINGLEMSISDN
            3) MSISDNRANGE
            4) MSISDNPREFIX
            5) NETWORK
            6) COUNTRY
            7) SINGLEPOINTCODE
            8) POINTCODERANGE
            9) LIST

            For details on these formats, refer to the comment on the
            ConditionSpec type."
        ::= { moRtgRuleEntry 47 }

    moRtgRuleBilProfileForSubmission OBJECT-TYPE
        SYNTAX  BilProfile
        ACCESS  read-write
        STATUS  mandatory
        DESCRIPTION
            "Identifier specifying which billing profile should be used for
            submission records. Default is 0 (i.e 'none').
            This attribute is applicable for all routing actions."
        ::= { moRtgRuleEntry 101 }

    moRtgRuleBilProfileForSuccessfulDelivery OBJECT-TYPE
        SYNTAX  BilProfile
        ACCESS  read-write
        STATUS  mandatory
        DESCRIPTION
            "Identifier specifying which billing profile should be used for
            delivery records in case the routing action succeeds. Default is 0
            (i.e. 'none').
            This attribute is applicable if the routing action is equal to
            routeToSmsc, routeToApplication, routeToMsFallbackToSmsc,
            discardWithAck, routeToMsFallbackToApplication, routeToMs,
            routeToApplicationFallbackToStorage, routeToMsFallbackToStorage,
            routeToSmscAsAo, routeToMsFallbackToSmscAsAo.
            
            When the routing action is routeToMsFallbackToSmsc,
            routeToMsFallbackToStorage, routeToApplicationFallbackToStorage,
            routeToMsFallbackToApplication, or routeToMsFallbackToSmscAsAo,
            this identifier pertains to the case that the routing action to
            the  MS succeeds."
        ::= { moRtgRuleEntry 102 }

    moRtgRuleBilProfileForFailedDelivery OBJECT-TYPE
        SYNTAX  BilProfile
        ACCESS  read-write
        STATUS  mandatory
        DESCRIPTION
            "Identifier specifying which billing profile should be used for
            delivery records in case the routing action fails. Default is 0
            (i.e. 'none').
            This attribute is applicable if the routing action is equal to
            routeToApplication, routeToMsFallbackToSmsc, routeToMs,
            routeToMsFallbackToApplication, routeToMsFallbackToStorage, 
            routeToApplicationFallbackToStorage, routeToSmscAsAo, or 
            routeToMsFallbackToSmscAsAo.
            When the routing action is routeToMsFallbackToSmsc,
            routeToMsFallbackToApplication,
            routeToApplicationFallbackToStorage,
            or routeToMsFallbackToStorage, or routeToMsFallbackToSmscAsAo,
            this identifier pertains to the case that the routing action
            to the MS fails with a permanent error."
        ::= { moRtgRuleEntry 103 }

    moRtgRuleBilProfileForSuccessfulDeliveryOnFallback OBJECT-TYPE
        SYNTAX  BilProfile
        ACCESS  read-write
        STATUS  mandatory
        DESCRIPTION
            "Identifier specifying which billing profile should be used for
            delivery records in case the routing action on the fallback leg
            succeeds. Default is 0 (i.e. 'none').
            This attribute is applicable if the routing action is equal to
            routeToMsFallbackToSmsc, routeToMsFallbackToApplication,
            routeToMsFallbackToStore, routeToApplicationFallbackToStore or
            routeToMsFallbackToSmscAsAo."
        ::= { moRtgRuleEntry 104 }

    moRtgRuleBilProfileForFailedDeliveryOnFallback OBJECT-TYPE
        SYNTAX  BilProfile
        ACCESS  read-write
        STATUS  mandatory
        DESCRIPTION
            "Identifier specifying which billing profile should be used for
            delivery records in case the routing action on the fallback leg
            fails. Default is 0 (i.e. 'none').
            This attribute is applicable if the routing action is equal to
            routeToMsFallbackToSmsc, routeToMsFallbackToApplication,
            routeToApplicationFallbackToStorage, routeToMsFallbackToStorage,
            or routeToMsFallbackToSmscAsAo."
        ::= { moRtgRuleEntry 105 }

    moRtgRuleBilProfileForDeliveryNotification OBJECT-TYPE
        SYNTAX  BilProfile
        ACCESS  read-write
        STATUS  mandatory
        DESCRIPTION
            "Identifier specifying which billing profile should be used for
            delivery notification. Default is 0 (i.e. 'none').
            This attribute is applicable if the routing action is equal to
            routeToApplication, routeToMsFallbackToSmsc, routeToMs,
            discardWithAck, routeToMsFallbackToApplication, 
            routeToApplicationFallbackToStorage, routeToMsFallbackToStorage,
            routeToSmscAsAo, and routeToMsFallbackToSmscAsAo"
        ::= { moRtgRuleEntry 106 }

    moRtgRuleLogProfile OBJECT-TYPE
        SYNTAX  LogProfile
        ACCESS  read-write
        STATUS  mandatory
        DESCRIPTION
            "Identifier specifying which logging profile should be used. 
            Default is 0 (i.e. 'none')."
        ::= { moRtgRuleEntry 111 }

    moRtgRuleSmscTable OBJECT-TYPE
        SYNTAX  SEQUENCE OF MoRtgRuleSmscEntry
        ACCESS  not-accessible
        STATUS  mandatory
        DESCRIPTION
            "A table containing SMSC-specific action parameters for an MO
            routing rule. Each MO routing rule whose action involves routing
            to the SMSC should have a table of this type.

            This table does not define SMSC's itself. It refers to the table
            smscTable, which defines the generic parameters of the SMSC like
            its address and which keeps track of its operational status.

            The table allows configuring multiple SMSC's for a single MO
            routing rule, to implement a prioritized, weighted load balancing
            scheme for the distribution of the SM's to the SMSC's, and to
            throttle the number of SM's sent to each SMSC per unit of time by
            means of maximum throughput regulation scheme.

            The logic for the prioritized, weighted load balancing scheme is
            as following:

            1) Only SMSC's for which the following conditions apply are
               considered:
               a) The operational state of the SMSC as defined in smscTable is
                  'available'
               b) The operational state of the SMSC as defined in this table
                  is 'available'
            2) Always, SM's are routed to the SMSC with the highest priority.
            3) In case multiple SMSC's have the same priority, SM's are
               distributed by considering the weights that are defined for the
               SMSC's. The higher the weight that is defined for an SMSC, the
               more SM's it will receive.

            The following sample aims to illustrate the prioritized, weighted
            load balancing scheme:

            Suppose that the following SMSC's have been defined for an MO
            routing rule:

                                          smscTable's        this table's
                      priority  weight  operationalState   operationalState
                    ---------------------------------------------------------
                SMSC1     3       5         available           available
                SMSC2     5       1       notReachable          available
                SMSC3     6       1         available      throughputExceeded
                SMSC4     4       2         available           available
                SMSC5     4       3         available           available

            The distribution of the SM's for the MO routing rule will be as
            following:

            1) SMSC1 will not receive any SM's, since its priority is too low.
            2) SMSC2 will not receive any SM's, since the operationalState of
               the SMSC in the smscTable is not 'available'
            3) SMSC3 will not receive any SM's, since the operationalState of
               the SMSC in this table is not 'available'
            4) SMSC4 will receive 40% of the SM's, as its weight (=2) is 40%
               of the total weight of the SMSC's that are considered (=2+3=5)
            5) SMSC5 will receive 60% of the SM's, as its weight (=3) is 60%
               of the total weight of the SMSC's that are considered (=2+3=5)
            "
        ::= { sms 12 }

    moRtgRuleSmscEntry OBJECT-TYPE
        SYNTAX  MoRtgRuleSmscEntry
        ACCESS  not-accessible
        STATUS  mandatory
        DESCRIPTION
            "Table entry specifying action parameters for a single SMSC that
            is referred by an MO routing rule."
        INDEX   { moRtgRuleSmscIndex1, moRtgRuleSmscIndex2 }
        ::= { moRtgRuleSmscTable 1 }

    MoRtgRuleSmscEntry ::=
        SEQUENCE {
            moRtgRuleSmscIndex1                   MoRtgRuleTableIndex,
            moRtgRuleSmscIndex2                   SmscTableIndex,
            moRtgRuleSmscAdminState               AdminState,
            moRtgRuleSmscOperationalState         MoSmscRefOperationalState,
            moRtgRuleSmscPriority                 Priority,
            moRtgRuleSmscThroughput               Throughput,
            moRtgRuleSmscWeight                   Weight,
            moRtgRuleSmscModifier                 MoModifierRef
        }

    moRtgRuleSmscIndex1 OBJECT-TYPE
        SYNTAX  MoRtgRuleTableIndex
        ACCESS  read-write
        STATUS  mandatory
        DESCRIPTION
            "Index of entry in table containing SMSC-specific action
            parameters for an MO routing rule. This index is actually a
            reference to the related MO routing rule. Its value is equal to
            the index of the moRtgRuleTable entry that specifies the MO
            routing rule."
        ::= { moRtgRuleSmscEntry 1 }


    moRtgRuleSmscIndex2 OBJECT-TYPE
        SYNTAX  SmscTableIndex
        ACCESS  read-write
        STATUS  mandatory
        DESCRIPTION
            "Index of table entry containing SMSC-specific action parameters
            for an MO routing rule. This index is actually a reference to the
            SMSC for which the SMSC-specific action parameters apply. Its
            value is equal to the index of the smscTable entry that defines
            the related SMSC."
        ::= { moRtgRuleSmscEntry 2 }

    moRtgRuleSmscAdminState OBJECT-TYPE
        SYNTAX  AdminState

        ACCESS  read-write
        STATUS  mandatory
        DESCRIPTION
            "Administrative state of the SMSC for an MO routing rule.

            Transition from 'inactive' to 'active' is only possible when:
            1) SMSC being referred to exists and is active;
            2) in case modifier specified, modifier being referred to exists.

            For details, refer to the comment on the AdminState type."
        ::= { moRtgRuleSmscEntry 3 }

    moRtgRuleSmscOperationalState OBJECT-TYPE
        SYNTAX  MoSmscRefOperationalState
        ACCESS  read-only
        STATUS  mandatory
        DESCRIPTION
            "Operational state of the SMSC for an MO routing rule."
        ::= { moRtgRuleSmscEntry 4 }

    moRtgRuleSmscPriority OBJECT-TYPE
        SYNTAX  Priority
        ACCESS  read-write
        STATUS  mandatory
        DESCRIPTION
            "Priority of the SMSC in an MO routing rule.
            For details, refer to the comment on the Priority type."
        ::= { moRtgRuleSmscEntry 5 }

    moRtgRuleSmscThroughput OBJECT-TYPE
        SYNTAX  Throughput
        ACCESS  read-write
        STATUS  mandatory
        DESCRIPTION
            "Maximum throughput in terms of SM's routed per second for an SMSC
            in an MO routing rule. Behavior for values at or near zero is
            undefined."
        ::= { moRtgRuleSmscEntry 6 }

    moRtgRuleSmscWeight OBJECT-TYPE
        SYNTAX  Weight
        ACCESS  read-write
        STATUS  mandatory
        DESCRIPTION
            "Weight in load-balancing scheme for an SMSC in an MO routing
            rule."
        ::= { moRtgRuleSmscEntry 7 }

    moRtgRuleSmscModifier OBJECT-TYPE
        SYNTAX  MoModifierRef
        ACCESS  read-write
        STATUS  mandatory
        DESCRIPTION
            "Reference to a modifier which is carried out when SMSC is
             selected."
        ::= { moRtgRuleSmscEntry 8 }

    -- moExtCondRuleTable


    moExtCondRuleTable OBJECT-TYPE
        SYNTAX  SEQUENCE OF MoExtCondRuleEntry
        ACCESS  not-accessible
        STATUS  mandatory
        DESCRIPTION
            "A table containing properties, conditions, counters and action
            parameters for each MO ExternalCondition rule.

            An MO ExternalCondition rule matches when all of the following
            conditions are met:

            1) its administrative state is active;
            2) all its (internal) conditions do satisfy;

            In case multiple rules match, all matching rules are applied in
            order of priority of the rules.
            For each matching rule, the specified ExternalCondition is
            evaluated by sending a validationRequest to the ExternalCondition
            application, which will return a evaluationResponse.
            When the ExternalCondition evaluates to True, the next rule will
            be processed. When all matching ExternalCondition rules evaluate
            to True, the MO SM will be routed according to the MO routing
            rules.
            When during the processing of an ExternalCondition rule a rule
            evaluates to False, the FailureAction of that rule will be
            exectuted and further processing of the ExternalCondition rules
            is stopped for this SM."
        ::= { sms 13 }

    moExtCondRuleEntry OBJECT-TYPE
        SYNTAX  MoExtCondRuleEntry
        ACCESS  not-accessible
        STATUS  mandatory
        DESCRIPTION
            "Table entry specifying a single MO ExternalCondition rule."
        INDEX   { moExtCondRuleIndex }
        ::= { moExtCondRuleTable 1 }

    MoExtCondRuleEntry ::=
        SEQUENCE {
            moExtCondRuleIndex                                 MoExtCondRuleTableIndex,
            moExtCondRuleAdminState                            AdminState,
            moExtCondRuleName                                  NameString,
            moExtCondRulePriority                              EciPriority,
            moExtCondRuleLogProfile                            LogProfile,
            moExtCondRuleTotalAppliedCounter                   Counter,
            moExtCondRulePassedMoFwdSmCounter                  Counter,
            moExtCondRuleBlockedMoFwdSmCounter                 Counter,
            moExtCondRuleFailureAction                         ExtCondMoAction,
            moExtCondRuleExternalCondition                     ConditionSpec,
            moExtCondRuleOriginatorCondition                   ConditionSpec,
            moExtCondRuleRecipientCondition                    ConditionSpec,
            moExtCondRuleSmscCondition                         ConditionSpec,
            moExtCondRuleMscOrSgsnCondition                    ConditionSpec,
            moExtCondRuleUserDataCondition                     ConditionSpec,
            moExtCondRuleUserDataHeaderCondition               ConditionSpec,
            moExtCondRuleReplyPathCondition                    ConditionSpec,
            moExtCondRuleStatusReportRequestCondition          ConditionSpec,
            moExtCondRuleProtocolIdCondition                   ConditionSpec,
            moExtCondRuleDataCodingSchemeCondition             ConditionSpec,
            moExtCondRuleRecipientTonCondition                 ConditionSpec,
            moExtCondRuleRecipientNpiCondition                 ConditionSpec,
            moExtCondRuleSubmitTimeCondition                   ConditionSpec,
            moExtCondRuleExternalAttributesCondition           ConditionSpec,
            moExtCondRuleRecipientQueryResultCondition         ConditionSpec,
            moExtCondRuleRecipientRoutingNumberGroupCondition  ConditionSpec,
            moExtCondRuleOriginatorHlrCondition                ConditionSpec
        }

    moExtCondRuleIndex OBJECT-TYPE
        SYNTAX  MoExtCondRuleTableIndex
        ACCESS  read-write
        STATUS  mandatory
        DESCRIPTION
            "Index of entry in MO ExternalCondition rule table."
        ::= { moExtCondRuleEntry 1 }

    moExtCondRuleAdminState OBJECT-TYPE
        SYNTAX  AdminState
        ACCESS  read-write
        STATUS  mandatory
        DESCRIPTION
            "Administrative state of the MO ExternalCondition rule.

            Transition from 'inactive' to 'active' is only possible when:
            1) name has been supplied;
            2) name is not already in use by another rule;
            3) conditions of rule specifying a network refer to an 'active'

               country and an 'active' network;
            4) conditions of rule specifying a country refer to an 'active'
               country;
            5) ExternalConditionApp refers to an 'active' ExternalCondition
               application;

            For details, refer to the comment on the AdminState type."
        ::= { moExtCondRuleEntry 2 }

    moExtCondRuleName OBJECT-TYPE
        SYNTAX  NameString
        ACCESS  read-write
        STATUS  mandatory
        DESCRIPTION
            "Name of the MO ExternalCondition rule."
        ::= { moExtCondRuleEntry 3 }

    moExtCondRulePriority OBJECT-TYPE
        SYNTAX  EciPriority
        ACCESS  read-write
        STATUS  mandatory
        DESCRIPTION
            "Priority of the MO ExternalCondition rule.
            For details, refer to the comment on the EciPriority type."
        ::= { moExtCondRuleEntry 4 }

    moExtCondRuleLogProfile OBJECT-TYPE
        SYNTAX  LogProfile
        ACCESS  read-write
        STATUS  mandatory
        DESCRIPTION
            "Identifier specifying which logging profile should be used. 
            Default is 0 (i.e. 'none')."
        ::= { moExtCondRuleEntry 5 }

    moExtCondRuleTotalAppliedCounter OBJECT-TYPE
        SYNTAX  Counter
        ACCESS  read-write
        STATUS  mandatory
        DESCRIPTION
            "Counter specifying the number of times that the ExternalCondition
            rule has been applied."
        ::= { moExtCondRuleEntry 11 }

    moExtCondRulePassedMoFwdSmCounter OBJECT-TYPE
        SYNTAX  Counter
        ACCESS  read-write
        STATUS  mandatory
        DESCRIPTION
            "Counter specifying the number of times that the ExternalCondition
            rule has been applied to a MoFwdSm with result 'pass'."
        ::= { moExtCondRuleEntry 12 }

    moExtCondRuleBlockedMoFwdSmCounter OBJECT-TYPE
        SYNTAX  Counter
        ACCESS  read-write
        STATUS  mandatory
        DESCRIPTION
            "Counter specifying the number of times that the ExternalCondition
            rule has been applied to a MoFwdSm with result 'block'."
        ::= { moExtCondRuleEntry 13 }

    moExtCondRuleFailureAction OBJECT-TYPE
        SYNTAX  ExtCondMoAction
        ACCESS  read-write

        STATUS  mandatory
        DESCRIPTION
            "Action to execute when the MO ExternalCondition rule matches,
            but the ExternalCondition evaluates to False.
            For details, refer to the comments on the ExtCondMoAction type."
        ::= { moExtCondRuleEntry 21 }

    moExtCondRuleExternalCondition OBJECT-TYPE
        SYNTAX  ConditionSpec
        ACCESS  read-write
        STATUS  mandatory
        DESCRIPTION
            "Condition refering to an external condition application
            which has to validate this rule.
            The following formats apply:
            1) EXTERNALCONDITION

            For details, refer to the ConditionSpec type."
        ::= { moExtCondRuleEntry 22 }

    moExtCondRuleOriginatorCondition OBJECT-TYPE
        SYNTAX  ConditionSpec

        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) SINGLEIMSI (*)
            7) IMSIRANGE (*)
            8) LIST

            For details on these formats, refer to the comment on the
            type.

            (*) Setting a condition on the IMSI is only possible when the
                setting smsPropAlwaysRetrieveOriginatorImsi is set to 'true'"
        ::= { moExtCondRuleEntry 31 }

    moExtCondRuleRecipientCondition OBJECT-TYPE
        SYNTAX  ConditionSpec
        ACCESS  read-write
        STATUS  mandatory
        DESCRIPTION
            "Condition pertaining to the recipient that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST
            12) ALPHANUMADDRESS

            For details on these formats, refer to the comment on the
            ConditionSpec type."
        ::= { moExtCondRuleEntry 32 }

    moExtCondRuleSmscCondition OBJECT-TYPE
        SYNTAX  ConditionSpec
        ACCESS  read-write
        STATUS  mandatory
        DESCRIPTION
            "Condition pertaining to the SMSC that is specified in the SM. For
            the specification for this condition, the following formats apply:

            1) NONE
            2) SINGLEMSISDN
            3) MSISDNRANGE
            4) MSISDNPREFIX
            5) LIST

            For details on these formats, refer to the comment on the
            ConditionSpec type."
        ::= { moExtCondRuleEntry 33 }

    moExtCondRuleMscOrSgsnCondition OBJECT-TYPE
        SYNTAX  ConditionSpec
        ACCESS  read-write
        STATUS  mandatory
        DESCRIPTION
            "Condition pertaining to the originating MSC/SGSN that is
            specified in the SM. For the specification for this condition,
            the following formats apply:

            1) NONE
            2) SINGLEMSISDN
            3) MSISDNRANGE
            4) MSISDNPREFIX
            5) NETWORK
            6) COUNTRY
            7) SINGLEPOINTCODE
            8) POINTCODERANGE
            9) LIST

            For details on these formats, refer to the comment on the
            ConditionSpec type."
        ::= { moExtCondRuleEntry 34 }

    moExtCondRuleUserDataCondition OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT

            For details on these formats, refer to the comment on the
            ConditionSpec type."
        ::= { moExtCondRuleEntry 35 }


    moExtCondRuleUserDataHeaderCondition OBJECT-TYPE

        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to GSM 03.40. The
            values for most common information element identifiers are:

            00 hex - Concatenated short message
            01 hex - Special SMS Message Indication
            04 hex - application port addressing scheme, 8 bit address
            05 hex - application port addressing scheme, 16 bit address
            06 hex - SMSC Control Parameters
            07 hex - UDH Source Indicator
            08 hex - Concatenated short message "
        ::= { moExtCondRuleEntry 36 }

    moExtCondRuleReplyPathCondition OBJECT-TYPE
        SYNTAX  ConditionSpec
        ACCESS  read-write
        STATUS  mandatory
        DESCRIPTION
            "Condition pertaining to the reply path bit specified in the SM.
            For the specification for this condition, the following formats
            apply:

            1) NONE
            2) BITVALUE

            For details on these formats, refer to the comment on the
            ConditionSpec type."
        ::= { moExtCondRuleEntry 37 }

    moExtCondRuleStatusReportRequestCondition OBJECT-TYPE
        SYNTAX  ConditionSpec
        ACCESS  read-write
        STATUS  mandatory
        DESCRIPTION
            "Condition pertaining to the status report request bit specified
            in the SM. For the specification for this condition, the
            following formats apply:

            1) NONE
            2) BITVALUE

            For details on these formats, refer to the comment on the
            ConditionSpec type."
        ::= { moExtCondRuleEntry 38 }

    moExtCondRuleProtocolIdCondition OBJECT-TYPE
        SYNTAX  ConditionSpec
        ACCESS  read-write
        STATUS  mandatory
        DESCRIPTION
            "Condition pertaining to the protocol ID specified in the SM. For
            the specification for this condition, the following formats apply:

            1) NONE
            2) BYTEVALUE

            For details on these formats, refer to the comment on the
            ConditionSpec type.

            For details on the values supported for the protocol ID, refer to
            GSM 03.40."
        ::= { moExtCondRuleEntry 39 }

    moExtCondRuleDataCodingSchemeCondition OBJECT-TYPE
        SYNTAX  ConditionSpec

        ACCESS  read-write
        STATUS  mandatory
        DESCRIPTION
            "Condition pertaining to the data coding scheme specified in the
            SM. For the specification for this condition, the following
            formats apply:

            1) NONE
            2) BYTEVALUE

            For details on these formats, refer to the comment on the
            ConditionSpec type.

            For details on the values supported for the data coding scheme,
            refer to GSM 03.38."
        ::= { moExtCondRuleEntry 40 }

    moExtCondRuleRecipientTonCondition OBJECT-TYPE
        SYNTAX  ConditionSpec
        ACCESS  read-write
        STATUS  mandatory
        DESCRIPTION
            "Condition pertaining to the type of number (TON) specified for
            the recipient of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { moExtCondRuleEntry 41 }

    moExtCondRuleRecipientNpiCondition OBJECT-TYPE
        SYNTAX  ConditionSpec
        ACCESS  read-write
        STATUS  mandatory
        DESCRIPTION
            "Condition pertaining to the numbering plan identification (NPI)
            specified for the recipient of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { moExtCondRuleEntry 42 }

    moExtCondRuleSubmitTimeCondition OBJECT-TYPE
        SYNTAX  ConditionSpec
        ACCESS  read-write
        STATUS  mandatory
        DESCRIPTION
            "Condition on the submit-time of the message. For the
            specification for this condition, the following formats apply:

            1) NONE
            2) TIMESPEC

            For further details on these formats, refer to the comment on the
            ConditionSpec type."
        ::= { moExtCondRuleEntry 43 }

    moExtCondRuleExternalAttributesCondition  OBJECT-TYPE
        SYNTAX  ConditionSpec
        ACCESS  read-write
        STATUS  mandatory
        DESCRIPTION
            "Condition on the 32 boolean atributes that can be set by an 
            external approval application. For the specification for this 
            condition, the following formats apply:

            1) NONE
            2) EXTERNALATTRIBUTES

            When the format is EXTERNALATTRIBUTES, the relating bit mask 
            string specifies which external attributes apply and the 
            relating bit value string specifies the values for the external 
            attributes.          
            Each bit in the bit strings relates to a specific attribute. The 
            bit strings consist of 32 bits. The least significant bit 
            corresponds to attribute 0. The most significant bit corresponds 
            to attribute 31. 
            A bit with value 1 in the bit mask string indicates that the 
            relating attribute applies and needs to be checked. A bit with 
            value 0 in the bit mask string indicates that the relating 
            attribute does not apply and does not need to be checked. 
            A bit with value 1 in the bit value string indicates that the 
            relating attribute should be TRUE. A bit with value 0 in the bit 
            value string indicates that the relating attribute should be 
            FALSE. 

            For further details on these formats, refer to the comment on the
            ConditionSpec type."
        ::= { moExtCondRuleEntry 44 }

    moExtCondRuleRecipientQueryResultCondition OBJECT-TYPE
        SYNTAX  ConditionSpec
        ACCESS  read-write
        STATUS  mandatory
        DESCRIPTION
            "Condition on the result of the HLR query for the recipient. In
            order for the condition to work, the recipient HLR query must have
            been performed before the MO routing rules are matched. This can
            be achieved through the smsPropHlrQueryForRecipientBeforeApproval
            property. For the specification for this condition, the following
            formats apply:

            1) NONE
            2) BITSTRING

            When the format is BITSTRING, the relating bit string specifies
            which HLR query results apply. Each bit in the bit string relates
            to a specific (or group of) query result(s). The (non-inverted)
            condition evaluates to true if the bit corresponding to the HLR
            query result is set to 1. Otherwise, the condition evaluates to
            false.

            Bit   Meaning
            -------------
            1     (any) permanent error
            2     (any) temporary error
            3-5   reserved for future error class types
            6     timeout
            7     system failure
            8     data missing
            9     unexpected data value
            10    facility not supported
            11    unknown subscriber
            12    absent subscriber
            13    call barred
            14    teleservice not provisioned
            15    tcap aborted
            16    sccp aborted
            17    other errors

            By default, the condition is set to NONE."
        ::= { moExtCondRuleEntry 45 }

    moExtCondRuleRecipientRoutingNumberGroupCondition OBJECT-TYPE
        SYNTAX  ConditionSpec
        ACCESS  read-write
        STATUS  mandatory
        DESCRIPTION
            "Condition on the group to which the routing number associated
            with the recipient address belongs. For the specification for
            this condition, the following formats apply:

            1) NONE
            2) SNMPINDEX

            When the format is SNMPINDEX, the SNMP index will refer to the
            routingNumberGroupTable. The (non-inverted) condition will
            never match if either the routing number group referred to by
            the condition is not active, or if no routing number has been
            determined for the recipient of the message under consideration.
            The RoutingNumberGroupIndex determines the range of valid numbers
            for the SNMP index."
        ::= { moExtCondRuleEntry 46 }

    moExtCondRuleOriginatorHlrCondition OBJECT-TYPE
        SYNTAX  ConditionSpec
        ACCESS  read-write
        STATUS  mandatory
        DESCRIPTION
            "Condition pertaining to the address of the HLR that is
            serving the originator of the message. In order to meaningfully
            apply this condition, the MNP or spoofing check must be applied
            before the MO rules, such that the HLR address is available to
            the router. For the specification for this condition, the
            following formats apply:

            1) NONE
            2) SINGLEMSISDN
            3) MSISDNRANGE
            4) MSISDNPREFIX
            5) NETWORK
            6) COUNTRY
            7) SINGLEPOINTCODE
            8) POINTCODERANGE
            9) LIST

            For details on these formats, refer to the comment on the
            ConditionSpec type."
        ::= { moExtCondRuleEntry 47 }

    -- mtRtgRuleTable

    mtRtgRuleTable OBJECT-TYPE
        SYNTAX  SEQUENCE OF MtRtgRuleEntry
        ACCESS  not-accessible
        STATUS  mandatory
        DESCRIPTION
            "A table containing properties, conditions, counters and action
            parameters for each MT routing rule.

            An MT routing rule matches when both of the following conditions
            are met:
            1) its administrative state is active;
            2) all its conditions do satisfy;

            In case multiple rules match, the priority of the MT routing rule
            determines which rule applies. When multiple rules have the same
            priority, the MT routing rule with the lowest index has 
            precedence."
        ::= { sms 16 }


    mtRtgRuleEntry OBJECT-TYPE
        SYNTAX  MtRtgRuleEntry
        ACCESS  not-accessible
        STATUS  mandatory
        DESCRIPTION
            "Table entry specifying a single MT routing rule."
        INDEX   { mtRtgRuleIndex }
        ::= { mtRtgRuleTable 1 }

    MtRtgRuleEntry ::=
        SEQUENCE {
            mtRtgRuleIndex                        MtRtgRuleTableIndex,
            mtRtgRuleAdminState                   AdminState,
            mtRtgRuleName                         NameString,
            mtRtgRulePriority                     Priority,
            mtRtgRuleAppliedCounter               Counter,
            mtRtgRuleAppliedForSriSmOfMtMtPathCounter Counter,
            mtRtgRuleAppliedForMtFwdSmOfMtMtPathCounter Counter,
            mtRtgRuleAppliedForSriSmOfAoMtPathCounter Counter,
            mtRtgRuleAppliedForMtFwdSmOfAoMtPathCounter Counter,
            mtRtgRuleAppliedForSriSmOfMoMtMoPathCounter Counter,
            mtRtgRuleAppliedForMtFwdSmOfMoMtMoPathCounter Counter,
            mtRtgRuleAppliedForSriSmOfMoMtAtPathCounter Counter,
            mtRtgRuleAppliedForMtFwdSmOfMoMtAtPathCounter Counter,
            mtRtgRuleAppliedForSriSmRespOfMtMtPathCounter Counter,
            mtRtgRuleAction                       MtAction,
            mtRtgRuleThroughput                   Throughput,
            mtRtgRuleModifier                     MtModifierRef,
            mtRtgRuleAppliedForSriSmOfMoMtPathCounter Counter,
            mtRtgRuleAppliedForMtFwdSmOfMoMtPathCounter Counter,	     
            mtRtgRuleDecimationSkippedCounter     Counter,
            mtRtgRuleOriginatorCondition          ConditionSpec,
            mtRtgRuleRecipientCondition           ConditionSpec,
            mtRtgRuleSmscCondition                ConditionSpec,
            mtRtgRuleMscOrSgsnCondition           ConditionSpec,
            mtRtgRuleUserDataCondition            ConditionSpec,
            mtRtgRuleUserDataHeaderCondition      ConditionSpec,
            mtRtgRuleReplyPathCondition           ConditionSpec,
            mtRtgRuleStatusReportIndicationCondition ConditionSpec,
            mtRtgRuleProtocolIdCondition          ConditionSpec,
            mtRtgRuleDataCodingSchemeCondition    ConditionSpec,
            mtRtgRuleOriginatorTonCondition       ConditionSpec,
            mtRtgRuleOriginatorNpiCondition       ConditionSpec,
            mtRtgRuleExternalAttributesCondition  ConditionSpec,
            mtRtgRuleMessageTypeCondition         ConditionSpec,
            mtRtgRuleXsMessageTypeCondition ConditionSpec,
            mtRtgRuleDecimation                   Decimation,
            mtRtgRuleBilProfileForSubmission      BilProfile,
            mtRtgRuleBilProfileForSuccessfulDelivery BilProfile,
            mtRtgRuleBilProfileForFailedDelivery  BilProfile,
            mtRtgRuleBilProfileForBlockedDelivery BilProfile,
            mtRtgRuleBilProfileForDeliveryNotification BilProfile,
            mtRtgRuleBilProfileForBimsiRetrieval  BilProfile,
            mtRtgRuleLogProfile                   LogProfile
        }

    mtRtgRuleIndex OBJECT-TYPE
        SYNTAX  MtRtgRuleTableIndex
        ACCESS  read-write
        STATUS  mandatory
        DESCRIPTION
            "Index of entry in MT routing rule table."
        ::= { mtRtgRuleEntry 1 }

    mtRtgRuleAdminState OBJECT-TYPE
        SYNTAX  AdminState
        ACCESS  read-write
        STATUS  mandatory
        DESCRIPTION
            "Administrative state of the MT routing rule.

            Transition from 'inactive' to 'active' is only possible when:
            1) name has been supplied;
            2) name is not already in use by another rule;
            3) conditions of rule specifying a network refer to an 'active'
               country and an 'active' network;
            4) conditions of rule specifying a country refer to an 'active'
               country;
            5) conditions of rule specifying an application refer to an
               'active' application;

            For details, refer to the comment on the AdminState type."
        ::= { mtRtgRuleEntry 2 }

    mtRtgRuleName OBJECT-TYPE
        SYNTAX  NameString
        ACCESS  read-write
        STATUS  mandatory
        DESCRIPTION
            "Name of the MT routing rule."
        ::= { mtRtgRuleEntry 3 }

    mtRtgRulePriority OBJECT-TYPE
        SYNTAX  Priority
        ACCESS  read-write
        STATUS  mandatory
        DESCRIPTION
            "Priority of the MT routing rule."
        ::= { mtRtgRuleEntry 4 }

    mtRtgRuleAppliedCounter OBJECT-TYPE
        SYNTAX  Counter
        ACCESS  read-only
        STATUS  mandatory
        DESCRIPTION
            "Counter specifying the number of times that the routing rule
            has been applied."
        ::= { mtRtgRuleEntry 11 }

    mtRtgRuleAppliedForSriSmOfMtMtPathCounter OBJECT-TYPE
        SYNTAX  Counter
        ACCESS  read-only
        STATUS  mandatory
        DESCRIPTION
            "Counter specifying the number of times that the routing rule has
            been applied for an SendRoutingInfoForSm operation that was to be
            issued for the MT-MT path."
        ::= { mtRtgRuleEntry 12 }

    mtRtgRuleAppliedForMtFwdSmOfMtMtPathCounter OBJECT-TYPE
        SYNTAX  Counter
        ACCESS  read-only
        STATUS  mandatory
        DESCRIPTION
            "Counter specifying the number of times that the routing rule has
            been applied for an MtForwardSm operation that was to be issued
            for the MT-MT path."
        ::= { mtRtgRuleEntry 13 }

    mtRtgRuleAppliedForSriSmOfAoMtPathCounter OBJECT-TYPE
        SYNTAX  Counter
        ACCESS  read-only
        STATUS  mandatory
        DESCRIPTION
            "Counter specifying the number of times that the routing rule has
            been applied for an SendRoutingInfoForSm operation that was to be
            issued for the AO-MT path."
        ::= { mtRtgRuleEntry 14 }

    mtRtgRuleAppliedForMtFwdSmOfAoMtPathCounter OBJECT-TYPE
        SYNTAX  Counter
        ACCESS  read-only
        STATUS  mandatory
        DESCRIPTION
            "Counter specifying the number of times that the routing rule has
            been applied for an MtForwardSm operation that was to be issued
            for the AO-MT path."
        ::= { mtRtgRuleEntry 15 }

    mtRtgRuleAppliedForSriSmOfMoMtMoPathCounter OBJECT-TYPE
        SYNTAX  Counter
        ACCESS  read-only
        STATUS  mandatory
        DESCRIPTION
            "Counter specifying the number of times that the routing rule has
            been applied for an SendRoutingInfoForSm operation that was to be
            issued for the MO-MT-MO path."
        ::= { mtRtgRuleEntry 16 }

    mtRtgRuleAppliedForMtFwdSmOfMoMtMoPathCounter OBJECT-TYPE
        SYNTAX  Counter
        ACCESS  read-only
        STATUS  mandatory
        DESCRIPTION
            "Counter specifying the number of times that the routing rule has
            been applied for an MtForwardSm operation that was to be issued
            for the MO-MT-MO path."
        ::= { mtRtgRuleEntry 17 }

    mtRtgRuleAppliedForSriSmOfMoMtAtPathCounter OBJECT-TYPE
        SYNTAX  Counter
        ACCESS  read-only
        STATUS  mandatory
        DESCRIPTION
            "Counter specifying the number of times that the routing rule has
            been applied for an SendRoutingInfoForSm operation that was to be
            issued for the MO-MT-AT path."
        ::= { mtRtgRuleEntry 18 }

    mtRtgRuleAppliedForMtFwdSmOfMoMtAtPathCounter OBJECT-TYPE
        SYNTAX  Counter
        ACCESS  read-only
        STATUS  mandatory
        DESCRIPTION
            "Counter specifying the number of times that the routing rule has
            been applied for an MtForwardSm operation that was to be issued
            for the MO-MT-AT path."
        ::= { mtRtgRuleEntry 19 }

    mtRtgRuleAppliedForSriSmRespOfMtMtPathCounter OBJECT-TYPE
        SYNTAX  Counter
        ACCESS  read-only
        STATUS  mandatory
        DESCRIPTION
            "Counter specifying the number of times that the routing rule has
            been applied for a response to a SendRoutingInfoForSm that was 
            received for the MT-MT path."
        ::= { mtRtgRuleEntry 20 }

    mtRtgRuleAction OBJECT-TYPE
        SYNTAX  MtAction
        ACCESS  read-write
        STATUS  mandatory
        DESCRIPTION
            "Action to execute when the MT routing rule applies."
        ::= { mtRtgRuleEntry 21 }

    mtRtgRuleThroughput OBJECT-TYPE
        SYNTAX  Throughput
        ACCESS  read-write
        STATUS  mandatory
        DESCRIPTION
            "Maximum number of MT/SM's per second that are allowed before the
            MT routing rule is effective. Only applicable if MT routing rule
            matches."
        ::= { mtRtgRuleEntry 22 }

    mtRtgRuleModifier OBJECT-TYPE
        SYNTAX  MtModifierRef
        ACCESS  read-write
        STATUS  mandatory
        DESCRIPTION
            "Reference to a modifier which is carried out when MT routing rule
            applies and action of MT routing rule is equal to pass."
        ::= { mtRtgRuleEntry 23 }

    mtRtgRuleAppliedForSriSmOfMoMtPathCounter OBJECT-TYPE
        SYNTAX  Counter
        ACCESS  read-only
        STATUS  mandatory
        DESCRIPTION
            "Counter specifying the number of times that the routing rule has
            been applied for an MtForwardSm operation that was to be issued
            for the MO-MT path."
        ::= { mtRtgRuleEntry 24 }

    mtRtgRuleAppliedForMtFwdSmOfMoMtPathCounter OBJECT-TYPE
        SYNTAX  Counter
        ACCESS  read-only
        STATUS  mandatory
        DESCRIPTION
            "Counter specifying the number of times that the routing rule has
            been applied for an MtForwardSm operation that was to be
            issued for the MO-MT path."
        ::= { mtRtgRuleEntry 25 }

    mtRtgRuleDecimationSkippedCounter OBJECT-TYPE
        SYNTAX  Counter
        ACCESS  read-only
        STATUS  mandatory
        DESCRIPTION
            "Counter specifying the number of times that the routing rule's
            action was not executed because mtRtgRuleDecimation is set to a
            non-unity setting (any valid setting other than 1/1)."
        ::= { mtRtgRuleEntry 27 }

    mtRtgRuleOriginatorCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) SINGLESHORTNUMBER
            6) SHORTNUMBERRANGE
            7) SHORTNUMBERPREFIX
            8) APPLICATION
            9) COUNTRY
            10) LIST
            11) ALPHANUMADDRESS 
           
            For details on these formats, refer to the comment on the
            ConditionSpec type."
        ::= { mtRtgRuleEntry 31 }

    mtRtgRuleRecipientCondition OBJECT-TYPE
        SYNTAX  ConditionSpec
        ACCESS  read-write
        STATUS  mandatory
        DESCRIPTION
            "Condition pertaining to the recipient that is specified in the
            SM.  For the specification for this condition, the following
            formats apply:

            1) NONE
            2) SINGLEMSISDN
            3) MSISDNRANGE
            4) MSISDNPREFIX
            5) COUNTRY
            6) NETWORK
            7) SINGLEIMSI
            8) IMSIRANGE
            9) LIST

            For details on these formats, refer to the comment on the
            ConditionSpec type."
        ::= { mtRtgRuleEntry 32 }

    mtRtgRuleSmscCondition OBJECT-TYPE
        SYNTAX  ConditionSpec
        ACCESS  read-write
        STATUS  mandatory
        DESCRIPTION
            "Condition pertaining to the SMSC that is specified in the SM. For
            the specification for this condition, the following formats apply:

            1) NONE
            2) SINGLEMSISDN
            3) MSISDNRANGE
            4) MSISDNPREFIX
            5) COUNTRY
            6) NETWORK
            7) LIST

            For details on these formats, refer to the comment on the
            ConditionSpec type."
        ::= { mtRtgRuleEntry 33 }

    mtRtgRuleMscOrSgsnCondition OBJECT-TYPE
        SYNTAX  ConditionSpec
        ACCESS  read-write
        STATUS  mandatory
        DESCRIPTION
            "Condition pertaining to the terminating MSC/SGSN that is
            specified in the SM. For the specification for this condition,
            the following formats apply:

            1) NONE
            2) SINGLEMSISDN
            3) MSISDNRANGE
            4) MSISDNPREFIX
            5) COUNTRY
            6) NETWORK
            7) SINGLEPOINTCODE
            8) POINTCODERANGE
            9) LIST

            For details on these formats, refer to the comment on the
            ConditionSpec type."
        ::= { mtRtgRuleEntry 34 }

    mtRtgRuleUserDataCondition  OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT

            For details on these formats, refer to the comment on the
            ConditionSpec type."
        ::= { mtRtgRuleEntry 35 }

    mtRtgRuleUserDataHeaderCondition  OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to GSM 03.40. The
            values for most common information element identifiers are:

            00 hex - Concatenated short message
            01 hex - Special SMS Message Indication
            04 hex - application port addressing scheme, 8 bit address

            05 hex - application port addressing scheme, 16 bit address
            06 hex - SMSC Control Parameters
            07 hex - UDH Source Indicator "
        ::= { mtRtgRuleEntry 36 }

    mtRtgRuleReplyPathCondition  OBJECT-TYPE
        SYNTAX  ConditionSpec
        ACCESS  read-write
        STATUS  mandatory
        DESCRIPTION
            "Condition pertaining to the reply path bit specified in the SM.
            For the specification for this condition, the following formats
            apply:

            1) NONE
            2) BITVALUE

            For details on these formats, refer to the comment on the
            ConditionSpec type."
        ::= { mtRtgRuleEntry 37 }

    mtRtgRuleStatusReportIndicationCondition  OBJECT-TYPE
        SYNTAX  ConditionSpec
        ACCESS  read-write
        STATUS  mandatory
        DESCRIPTION
            "Condition pertaining to the status report indication bit
            specified in the SM. For the specification for this condition,
            the following formats apply:

            1) NONE
            2) BITVALUE

            For details on these formats, refer to the comment on the
            ConditionSpec type."
        ::= { mtRtgRuleEntry 38 }

    mtRtgRuleProtocolIdCondition  OBJECT-TYPE
        SYNTAX  ConditionSpec
        ACCESS  read-write
        STATUS  mandatory
        DESCRIPTION
            "Condition pertaining to the protocol ID specified in the SM. For
            the specification for this condition, the following formats apply:

            1) NONE
            2) BYTEVALUE

            For details on these formats, refer to the comment on the
            ConditionSpec type.

            For details on the values supported for the protocol ID, refer to
            GSM 03.40."
        ::= { mtRtgRuleEntry 39 }


    mtRtgRuleDataCodingSchemeCondition  OBJECT-TYPE
        SYNTAX  ConditionSpec
        ACCESS  read-write
        STATUS  mandatory
        DESCRIPTION
            "Condition pertaining to the data coding scheme specified in the
            SM. For the specification for this condition, the following
            formats apply:

            1) NONE
            2) BYTEVALUE

            For details on these formats, refer to the comment on the
            ConditionSpec type.

            For details on the values supported for the data coding scheme,
            refer to GSM 03.38."
        ::= { mtRtgRuleEntry 40 }

    mtRtgRuleOriginatorTonCondition  OBJECT-TYPE
        SYNTAX  ConditionSpec
        ACCESS  read-write
        STATUS  mandatory
        DESCRIPTION
            "Condition pertaining to the type of number (TON) specified for
            the originator of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { mtRtgRuleEntry 41 }

    mtRtgRuleOriginatorNpiCondition  OBJECT-TYPE
        SYNTAX  ConditionSpec
        ACCESS  read-write
        STATUS  mandatory
        DESCRIPTION
            "Condition pertaining to the numbering plan identification (NPI)
            specified for the originator of the SM. For the specification for
            this condition, the following formats apply:

            1) NONE
            2) BITSTRING

            When the format is BITSTRING, the relating bit string specifies
            which values for the NPI apply. Each bit in the bit string
            relates to a NPI value. If the bit is 1, the relating NPI value
            applies.  Otherwise, if the bit is 0, the relating NPI value does
            not apply.  The range of value for the NPI is 0-15. As such, the
            bit string consists of 16 bits with the least significant bit
            indicating whether NPI value 0 applies and the most significant
            bit indicating whether NPI value 15 applies.

            For further details on these formats, refer to the comment on the
            ConditionSpec type.

            For details on the values supported for the NPI, refer to GSM
            03.40."
        ::= { mtRtgRuleEntry 42 }

    mtRtgRuleExternalAttributesCondition OBJECT-TYPE
        SYNTAX  ConditionSpec
        ACCESS  read-write
        STATUS  mandatory
        DESCRIPTION
           "Condition on the 32 boolean atributes that can be set by an 
            external approval application. For the specification for this 
            condition, the following formats apply:

            1) NONE
            2) EXTERNALATTRIBUTES

            When the format is EXTERNALATTRIBUTES, the relating bit mask
            string specifies which external attributes apply and the relating
            bit value string specifies the values for the external
            attributes.          Each bit in the bit strings relates to a
            specific attribute. The bit strings consist of 32 bits. The least
            significant bit corresponds to attribute 0. The most significant
            bit corresponds to attribute 31. 
            A bit with value 1 in the bit mask string indicates that the
            relating attribute applies and needs to be checked. A bit with
            value 0 in the bit mask string indicates that the relating
            attribute does not apply and does not need to be checked. 
            A bit with value 1 in the bit value string indicates that the
            relating attribute should be TRUE. A bit with value 0 in the bit
            value string indicates that the relating attribute should be
            FALSE. 

            For further details on these formats, refer to the comment on the
            ConditionSpec type."
        ::= { mtRtgRuleEntry 43 }

    mtRtgRuleXsMessageTypeCondition OBJECT-TYPE
        SYNTAX  ConditionSpec
        ACCESS  read-write
        STATUS  mandatory
        DESCRIPTION
            "Condition pertaining to the external service (XS) message type
            applicable for this SM.
            For the specification for this condition, the following formats
            apply:

            1) NONE
            2) BITSTRING

            When the format is BITSTRING, the relating bit string specifies
            which values for the XS message type apply. Each bit in the bit
            string relates to a XS message type. If the bit is 1, the relating
            XS message type applies. Otherwise, if the bit is 0, the relating
            XS message type does not apply.
            The valid message types are:
                noXsMessage(0),
                forwardedMessage (1),
                copiedMessage (2)

            The range of valid values is 0-3. As such, the bit string consists
            of 3 bits, with the least significant bit indicating whether
            XS message type 0 (noXsMessage) applies and the most significant
            bit indicating whether XS message type 2 (copiedMessage) applies.

            For further details on these formats, refer to the comment on the
            ConditionSpec type."
        ::= { mtRtgRuleEntry 44 }

    mtRtgRuleMessageTypeCondition OBJECT-TYPE
        SYNTAX  ConditionSpec
        ACCESS  read-write
        STATUS  mandatory
        DESCRIPTION
            "Condition pertaining to the message type applicable for this SM.
            For the specification for this condition, the following formats
            apply:

            1) NONE
            2) BITSTRING

            When the format is BITSTRING, the relating bit string specifies
            which values for the message type apply. Each bit in the bit
            string relates to a message type. If the bit is 1, the relating
            message type applies. Otherwise, if the bit is 0, the relating
            message type does not apply.

            The valid message types are:
                shortMessage (0),
                sendRoutingInfoForSmRequest (1),
                sendRoutingInfoForSmResponse (2),
                statusReport (3)

            The range of valid values is 0-3. As such, the bit string consists
            of 4 bits, with the least significant bit indicating whether
            message type 0 (shortMessage) applies and the most significant bit
            indicating whether message type 3 (statusReport) applies.

            For further details on these formats, refer to the comment on the
            ConditionSpec type."
        ::= { mtRtgRuleEntry 45 }

    mtRtgRuleDecimation OBJECT-TYPE
        SYNTAX  Decimation
        ACCESS  read-write
        STATUS  mandatory
        DESCRIPTION
            "This option instructs the RTR to not execute the routing rule's
            action for a defined ratio of messages. The format is N/M,
            where N and M are in the range 1 through 9999. For example, 3/10
            means that the RTR will execute the routing rule's action for 3
            messages, then will not execute the action for the following 7
            messages. The default is 1/1, which means that the action is
            executed for all messages. If the action is not executed due
            to the rule matching ratio then mtRtgRuleDecimationSkippedCounter
            is incremented and subsequent rules are processed in priority
            order. This means a skipping of the rule has the same behavior
            as if the rule were not matched w.r.t. processing of subsequent
            rules."
        ::= { mtRtgRuleEntry 46 }

    mtRtgRuleBilProfileForSubmission OBJECT-TYPE
        SYNTAX  BilProfile
        ACCESS  read-write
        STATUS  mandatory
        DESCRIPTION
            "Identifier specifying which billing profile should be used for
            submission records. Default is 0 (i.e none)."
        ::= { mtRtgRuleEntry 101 }

    mtRtgRuleBilProfileForSuccessfulDelivery OBJECT-TYPE
        SYNTAX  BilProfile
        ACCESS  read-write
        STATUS  mandatory
        DESCRIPTION
            "Identifier specifying which billing profile should be used for
            delivery records in case the MT/SM is successfully delivered.
            Default is 0 (i.e. 'none'). This attribute is only applicable
            for the 'pass' action."
        ::= { mtRtgRuleEntry 102 }

    mtRtgRuleBilProfileForFailedDelivery OBJECT-TYPE
        SYNTAX  BilProfile
        ACCESS  read-write
        STATUS  mandatory
        DESCRIPTION
            "Identifier specifying which billing profile should be used for
            delivery records in case delivering the MT/SM resulted in a
            failure. Default is 0 (i.e. 'none'). This attribute is only
            applicable for the 'pass' action."
        ::= { mtRtgRuleEntry 103 }

    mtRtgRuleBilProfileForBlockedDelivery OBJECT-TYPE
        SYNTAX  BilProfile
        ACCESS  read-write
        STATUS  mandatory
        DESCRIPTION
            "Identifier specifying which billing profile should be used for
            delivery records in case the MT/SM is blocked by the rule.
            Default is 0 (i.e. 'none'). This attribute is only applicable
            for the actions that can block the MT/SM."
        ::= { mtRtgRuleEntry 104 }

    mtRtgRuleBilProfileForDeliveryNotification OBJECT-TYPE
        SYNTAX  BilProfile
        ACCESS  read-write
        STATUS  mandatory
        DESCRIPTION
            "Identifier specifying which billing profile should be used for
            delivery notification. Default is 0 (i.e. 'none')."
        ::= { mtRtgRuleEntry 105 }

    mtRtgRuleBilProfileForBimsiRetrieval OBJECT-TYPE
        SYNTAX  BilProfile
        ACCESS  read-write
        STATUS  mandatory
        DESCRIPTION
            "Identifier specifying which billing profile should be used for
            B-IMSI retrieval.  This is an atypical billing record; it is
            really a submission record.  It exists because in some cases,
            submission records do not specify the B-IMSI.  To compensate
            for this, a billing record can be created upon successful B-IMSI
            lookup and that billing record will contain the missing B-IMSI.

            Note that only FCDR format is supported.  Other formats will cause
            a silent run-time error, where the billing record is not
            written.

            Default is 0 (i.e. 'none')."
        ::= { mtRtgRuleEntry 106 }

    mtRtgRuleLogProfile OBJECT-TYPE
        SYNTAX  LogProfile
        ACCESS  read-write
        STATUS  mandatory
        DESCRIPTION
            "Identifier specifying which logging profile should be used.
            Default is 0 (i.e. 'none')."
        ::= { mtRtgRuleEntry 111 }

    -- mtExtCondRuleTable

    mtExtCondRuleTable OBJECT-TYPE
        SYNTAX  SEQUENCE OF MtExtCondRuleEntry
        ACCESS  not-accessible
        STATUS  mandatory
        DESCRIPTION
            "A table containing properties, conditions, counters and action
            parameters for each MT ExternalCondition rule.

            An MT ExternalCondition rule matches when all of the following
            conditions are met:
            1) its administrative state is active;
            2) all its (internal) conditions do satisfy;

            In case multiple rules match, all matching rules are applied in
            order of priority of the rules.
            For each matching rule, the specified ExternalCondition is
            evaluated by sending a validationRequest to the ExternalCondition
            application, which will return a evaluationResponse.
            When the ExternalCondition evaluates to True, the next rule will
            be processed. When all matching ExternalCondition rules evaluate
            to True, the MT SM will be routed according to the MT routing
            rules.  When during the processing of an ExternalCondition rule a
            rule evaluates to False, the FailureAction of that rule will be
            exectuted and further processing of the ExternalCondition rules
            is stopped for this SM."
        ::= { sms 17 }


    mtExtCondRuleEntry OBJECT-TYPE
        SYNTAX  MtExtCondRuleEntry
        ACCESS  not-accessible
        STATUS  mandatory
        DESCRIPTION
            "Table entry specifying a single MT ExternalCondition rule."
        INDEX   { mtExtCondRuleIndex }
        ::= { mtExtCondRuleTable 1 }

    MtExtCondRuleEntry ::=
        SEQUENCE {
            mtExtCondRuleIndex                                 MtExtCondRuleTableIndex,
            mtExtCondRuleAdminState                            AdminState,
            mtExtCondRuleName                                  NameString,
            mtExtCondRulePriority                              EciPriority,
            mtExtCondRuleLogProfile                            LogProfile,
            mtExtCondRuleTotalAppliedCounter                   Counter,
            mtExtCondRulePassedMtFwdSmCounter                  Counter,
            mtExtCondRuleBlockedMtFwdSmCounter                 Counter,
            mtExtCondRulePassedSriSmReqCounter                 Counter,
            mtExtCondRuleBlockedSriSmReqCounter                Counter,
            mtExtCondRulePassedSriSmRspCounter                 Counter,
            mtExtCondRuleBlockedSriSmRspCounter                Counter,
            mtExtCondRulePassedStatusReportCounter             Counter,
            mtExtCondRuleBlockedStatusReportCounter            Counter,
            mtExtCondRuleFailureAction                         ExtCondMtAction,
            mtExtCondRuleExternalCondition                     ConditionSpec,
            mtExtCondRuleOriginatorCondition                   ConditionSpec,
            mtExtCondRuleRecipientCondition                    ConditionSpec,
            mtExtCondRuleSmscCondition                         ConditionSpec,
            mtExtCondRuleMscOrSgsnCondition                    ConditionSpec,
            mtExtCondRuleUserDataCondition                     ConditionSpec,
            mtExtCondRuleUserDataHeaderCondition               ConditionSpec,
            mtExtCondRuleReplyPathCondition                    ConditionSpec,
            mtExtCondRuleStatusReportIndicationCondition       ConditionSpec,
            mtExtCondRuleProtocolIdCondition                   ConditionSpec,
            mtExtCondRuleDataCodingSchemeCondition             ConditionSpec,
            mtExtCondRuleMessageTypeCondition                  ConditionSpec,
            mtExtCondRuleOriginatorTonCondition                ConditionSpec,
            mtExtCondRuleOriginatorNpiCondition                ConditionSpec,
            mtExtCondRuleExternalAttributesCondition           ConditionSpec,
            mtExtCondRuleXsMessageTypeCondition                ConditionSpec
        }

    mtExtCondRuleIndex OBJECT-TYPE
        SYNTAX  MtExtCondRuleTableIndex
        ACCESS  read-write
        STATUS  mandatory
        DESCRIPTION
            "Index of entry in MT ExternalCondition rule table."
        ::= { mtExtCondRuleEntry 1 }

    mtExtCondRuleAdminState OBJECT-TYPE
        SYNTAX  AdminState
        ACCESS  read-write
        STATUS  mandatory
        DESCRIPTION
            "Administrative state of the MT ExternalCondition rule.

            Transition from 'inactive' to 'active' is only possible when:
            1) name has been supplied;
            2) name is not already in use by another rule;
            3) conditions of rule specifying a network refer to an 'active'
               country and an 'active' network;
            4) conditions of rule specifying a country refer to an 'active'
               country;
            5) ExternalConditionApp refers to an 'active' ExternalCondition
               application;

            For details, refer to the comment on the AdminState type."
        ::= { mtExtCondRuleEntry 2 }

    mtExtCondRuleName OBJECT-TYPE

        SYNTAX  NameString
        ACCESS  read-write
        STATUS  mandatory
        DESCRIPTION
            "Name of the MT ExternalCondition rule."
        ::= { mtExtCondRuleEntry 3 }

    mtExtCondRulePriority OBJECT-TYPE
        SYNTAX  EciPriority
        ACCESS  read-write
        STATUS  mandatory
        DESCRIPTION
            "Priority of the MT ExternalCondition rule.
            For details, refer to the comment on the EciPriority type."
        ::= { mtExtCondRuleEntry 4 }

    mtExtCondRuleLogProfile OBJECT-TYPE
        SYNTAX  LogProfile
        ACCESS  read-write
        STATUS  mandatory
        DESCRIPTION
            "Identifier specifying which logging profile should be used. 
            Default is 0 (i.e. 'none')."
        ::= { mtExtCondRuleEntry 5 }

    mtExtCondRuleTotalAppliedCounter OBJECT-TYPE
        SYNTAX  Counter
        ACCESS  read-write
        STATUS  mandatory
        DESCRIPTION
            "Counter specifying the number of times that the ExternalCondition
            rule has been applied."
        ::= { mtExtCondRuleEntry 11 }

    mtExtCondRulePassedMtFwdSmCounter OBJECT-TYPE
        SYNTAX  Counter
        ACCESS  read-write
        STATUS  mandatory
        DESCRIPTION
            "Counter specifying the number of times that the ExternalCondition
            rule has been applied to a MtFwdSm with result 'pass'."
        ::= { mtExtCondRuleEntry 12 }

    mtExtCondRuleBlockedMtFwdSmCounter OBJECT-TYPE
        SYNTAX  Counter
        ACCESS  read-write
        STATUS  mandatory
        DESCRIPTION
            "Counter specifying the number of times that the ExternalCondition
            rule has been applied to a MtFwdSm with result 'block'."
        ::= { mtExtCondRuleEntry 13 }

    mtExtCondRulePassedSriSmReqCounter OBJECT-TYPE
        SYNTAX  Counter
        ACCESS  read-write
        STATUS  mandatory
        DESCRIPTION
            "Counter specifying the number of times that the ExternalCondition
            rule has been applied to a SriSm request with result 'pass'."
        ::= { mtExtCondRuleEntry 14 }

    mtExtCondRuleBlockedSriSmReqCounter OBJECT-TYPE
        SYNTAX  Counter
        ACCESS  read-write
        STATUS  mandatory
        DESCRIPTION
            "Counter specifying the number of times that the ExternalCondition
            rule has been applied to a SriSm request with result 'block'."
        ::= { mtExtCondRuleEntry 15 }

    mtExtCondRulePassedSriSmRspCounter OBJECT-TYPE
        SYNTAX  Counter
        ACCESS  read-write
        STATUS  mandatory
        DESCRIPTION
            "Counter specifying the number of times that the ExternalCondition
            rule has been applied to a SriSm response with result 'pass'."
        ::= { mtExtCondRuleEntry 16 }

    mtExtCondRuleBlockedSriSmRspCounter OBJECT-TYPE
        SYNTAX  Counter
        ACCESS  read-write
        STATUS  mandatory
        DESCRIPTION
            "Counter specifying the number of times that the ExternalCondition
            rule has been applied to a SriSm response with result 'block'."
        ::= { mtExtCondRuleEntry 17 }

    mtExtCondRulePassedStatusReportCounter OBJECT-TYPE
        SYNTAX  Counter
        ACCESS  read-write
        STATUS  mandatory
        DESCRIPTION
            "Counter specifying the number of times that the ExternalCondition
            rule has been applied to a StatusReport with result 'pass'."
        ::= { mtExtCondRuleEntry 18 }

    mtExtCondRuleBlockedStatusReportCounter OBJECT-TYPE
        SYNTAX  Counter
        ACCESS  read-write
        STATUS  mandatory
        DESCRIPTION
            "Counter specifying the number of times that the ExternalCondition
            rule has been applied to a StatusReport with result 'block'."
        ::= { mtExtCondRuleEntry 19 }

    mtExtCondRuleFailureAction OBJECT-TYPE
        SYNTAX  ExtCondMtAction
        ACCESS  read-write
        STATUS  mandatory
        DESCRIPTION
            "Action to execute when the MT ExternalCondition rule matches,
            but the ExternalCondition evaluates to False.
            For details, refer to the comments on the ExtCondMtAction type."
        ::= { mtExtCondRuleEntry 21 }

    mtExtCondRuleExternalCondition OBJECT-TYPE
        SYNTAX  ConditionSpec
        ACCESS  read-write
        STATUS  mandatory
        DESCRIPTION
            "Condition refering to an external condition application
            which has to validate this rule.
            The following formats apply:
            1) EXTERNALCONDITION

            For details, refer to the ConditionSpec type."
        ::= { mtExtCondRuleEntry 22 }

    mtExtCondRuleOriginatorCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) SINGLESHORTNUMBER
            6) SHORTNUMBERRANGE
            7) SHORTNUMBERPREFIX
            8) APPLICATION
            9) COUNTRY
            10) LIST
            11) ALPHANUMADDRESS 

            For details on these formats, refer to the comment on the
            ConditionSpec type."
        ::= { mtExtCondRuleEntry 31 }

    mtExtCondRuleRecipientCondition OBJECT-TYPE
        SYNTAX  ConditionSpec
        ACCESS  read-write
        STATUS  mandatory
        DESCRIPTION
            "Condition pertaining to the recipient that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) APPLICATION
            10) LIST

            For details on these formats, refer to the comment on the

            ConditionSpec type."
        ::= { mtExtCondRuleEntry 32 }

    mtExtCondRuleSmscCondition OBJECT-TYPE
        SYNTAX  ConditionSpec
        ACCESS  read-write
        STATUS  mandatory
        DESCRIPTION
            "Condition pertaining to the SMSC that is specified in the SM. For
            the specification for this condition, the following formats apply:

            1) NONE
            2) SINGLEMSISDN
            3) MSISDNRANGE
            4) MSISDNPREFIX
            5) COUNTRY
            6) NETWORK
            7) LIST

            For details on these formats, refer to the comment on the
            ConditionSpec type."
        ::= { mtExtCondRuleEntry 33 }

    mtExtCondRuleMscOrSgsnCondition OBJECT-TYPE
        SYNTAX  ConditionSpec
        ACCESS  read-write
        STATUS  mandatory
        DESCRIPTION
            "Condition pertaining to the terminating MSC/SGSN that is
            specified in the SM. For the specification for this condition,
            the following formats apply:

            1) NONE
            2) SINGLEMSISDN
            3) MSISDNRANGE
            4) MSISDNPREFIX
            5) COUNTRY
            6) NETWORK
            7) SINGLEPOINTCODE
            8) POINTCODERANGE
            9) LIST

            For details on these formats, refer to the comment on the
            ConditionSpec type."
        ::= { mtExtCondRuleEntry 34 }

    mtExtCondRuleUserDataCondition OBJECT-TYPE
        SYNTAX  ConditionSpec
        ACCESS  read-write
        STATUS  mandatory
        DESCRIPTION
            "Condition pertaining to the text that is specified in the user
            data of the SM. For the specification for this condition, the
            following formats apply:

            1) NONE
            2) FULLTEXT

            3) TEXTTAG
            4) SUBTEXT

            For details on these formats, refer to the comment on the
            ConditionSpec type."
        ::= { mtExtCondRuleEntry 35 }

    mtExtCondRuleUserDataHeaderCondition OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.


            For details on the values supported for the information element
            identifiers of the user data header, refer to GSM 03.40. The
            values for most common information element identifiers are:

            00 hex - Concatenated short message
            01 hex - Special SMS Message Indication
            04 hex - application port addressing scheme, 8 bit address
            05 hex - application port addressing scheme, 16 bit address
            06 hex - SMSC Control Parameters
            07 hex - UDH Source Indicator
            08 hex - Concatenated short message "
        ::= { mtExtCondRuleEntry 36 }

    mtExtCondRuleReplyPathCondition OBJECT-TYPE
        SYNTAX  ConditionSpec
        ACCESS  read-write
        STATUS  mandatory
        DESCRIPTION
            "Condition pertaining to the reply path bit specified in the SM.
            For the specification for this condition, the following formats
            apply:

            1) NONE
            2) BITVALUE

            For details on these formats, refer to the comment on the
            ConditionSpec type."
        ::= { mtExtCondRuleEntry 37 }

    mtExtCondRuleStatusReportIndicationCondition OBJECT-TYPE
        SYNTAX  ConditionSpec
        ACCESS  read-write
        STATUS  mandatory
        DESCRIPTION
            "Condition pertaining to the status report indication bit
            specified in the SM. For the specification for this condition,
            the following formats apply:

            1) NONE
            2) BITVALUE

            For details on these formats, refer to the comment on the
            ConditionSpec type."
        ::= { mtExtCondRuleEntry 38 }

    mtExtCondRuleProtocolIdCondition OBJECT-TYPE
        SYNTAX  ConditionSpec
        ACCESS  read-write
        STATUS  mandatory
        DESCRIPTION
            "Condition pertaining to the protocol ID specified in the SM. For
            the specification for this condition, the following formats apply:

            1) NONE
            2) BYTEVALUE

            For details on these formats, refer to the comment on the
            ConditionSpec type.

            For details on the values supported for the protocol ID, refer to
            GSM 03.40."
        ::= { mtExtCondRuleEntry 39 }

    mtExtCondRuleDataCodingSchemeCondition OBJECT-TYPE
        SYNTAX  ConditionSpec
        ACCESS  read-write
        STATUS  mandatory
        DESCRIPTION
            "Condition pertaining to the data coding scheme specified in the
            SM. For the specification for this condition, the following
            formats apply:

            1) NONE
            2) BYTEVALUE

            For details on these formats, refer to the comment on the
            ConditionSpec type.

            For details on the values supported for the data coding scheme,
            refer to GSM 03.38."
        ::= { mtExtCondRuleEntry 40 }

    mtExtCondRuleMessageTypeCondition OBJECT-TYPE
        SYNTAX  ConditionSpec
        ACCESS  read-write
        STATUS  mandatory
        DESCRIPTION
            "Condition pertaining to the message type applicable for this SM.
            For the specification for this condition, the following formats
            apply:

            1) NONE
            2) BITSTRING

            When the format is BITSTRING, the relating bit string specifies
            which values for the message type apply. Each bit in the bit
            string relates to a message type. If the bit is 1, the relating
            message type applies. Otherwise, if the bit is 0, the relating
            message type does not apply.
            The valid message types are:
                shortMessage (0),
                sendRoutingInfoForSmRequest (1),
                sendRoutingInfoForSmResponse (2),
                statusReport (3)

            The range of valid values is 0-3. As such, the bit string consists
            of 4 bits, with the least significant bit indicating whether
            message type 0 (shortMessage) applies and the most significant bit
            indicating whether message type 3 (statusReport) applies.

            For further details on these formats, refer to the comment on the
            ConditionSpec type."
        ::= { mtExtCondRuleEntry 42 }

    mtExtCondRuleOriginatorTonCondition  OBJECT-TYPE
        SYNTAX  ConditionSpec
        ACCESS  read-write
        STATUS  mandatory
        DESCRIPTION
            "Condition pertaining to the type of number (TON) specified for
            the originator of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { mtExtCondRuleEntry 43 }

    mtExtCondRuleOriginatorNpiCondition  OBJECT-TYPE
        SYNTAX  ConditionSpec
        ACCESS  read-write
        STATUS  mandatory
        DESCRIPTION
            "Condition pertaining to the numbering plan identification (NPI)
            specified for the originator of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { mtExtCondRuleEntry 44 }

    mtExtCondRuleExternalAttributesCondition  OBJECT-TYPE
        SYNTAX  ConditionSpec
        ACCESS  read-write
        STATUS  mandatory
        DESCRIPTION
            "Condition on the 32 boolean atributes that can be set by an 
            external approval application. For the specification for this 
            condition, the following formats apply:

            1) NONE
            2) EXTERNALATTRIBUTES

            When the format is EXTERNALATTRIBUTES, the relating bit mask 
            string specifies which external attributes apply and the relating 
            bit value string specifies the values for the external attributes.          
            Each bit in the bit strings relates to a specific attribute. The 
            bit strings consist of 32 bits. The least significant bit 
            corresponds to attribute 0. The most significant bit corresponds 
            to attribute 31. 
            A bit with value 1 in the bit mask string indicates that the 
            relating attribute applies and needs to be checked. A bit with 
            value 0 in the bit mask string indicates that the relating 
            attribute does not apply and does not need to be checked. 
            A bit with value 1 in the bit value string indicates that the 
            relating attribute should be TRUE. A bit with value 0 in the bit 
            value string indicates that the relating attribute should be 
            FALSE. 

            For further details on these formats, refer to the comment on the
            ConditionSpec type."
        ::= { mtExtCondRuleEntry 45 }

    mtExtCondRuleXsMessageTypeCondition OBJECT-TYPE
        SYNTAX  ConditionSpec
        ACCESS  read-write
        STATUS  mandatory
        DESCRIPTION
            "Condition pertaining to the external service (XS) message type
            applicable for this SM.
            For the specification for this condition, the following formats
            apply:

            1) NONE
            2) BITSTRING

            When the format is BITSTRING, the relating bit string specifies
            which values for the XS message type apply. Each bit in the bit
            string relates to a XS message type. If the bit is 1, the relating
            XS message type applies. Otherwise, if the bit is 0, the relating
            XS message type does not apply.
            The valid message types are:
                noXsMessage(0),
                forwardedMessage (1),
                copiedMessage (2)

            The range of valid values is 0-3. As such, the bit string consists
            of 3 bits, with the least significant bit indicating whether
            XS message type 0 (noXsMessage) applies and the most significant
            bit indicating whether XS message type 2 (copiedMessage) applies.

            For further details on these formats, refer to the comment on the
            ConditionSpec type."
        ::= { mtExtCondRuleEntry 46 }
        
    -- moModifierTable

    moModifierTable OBJECT-TYPE
        SYNTAX  SEQUENCE OF MoModifierEntry
        ACCESS  not-accessible
        STATUS  mandatory
        DESCRIPTION
            "A list of MO modifier entries."
        ::= { sms 20 }

    moModifierEntry OBJECT-TYPE
        SYNTAX  MoModifierEntry
        ACCESS  not-accessible
        STATUS  mandatory
        DESCRIPTION
            "Table entry specifying a single MO modifier."
        INDEX   { moModifierIndex }
        ::= { moModifierTable 1 }

    MoModifierEntry ::=
        SEQUENCE {
            moModifierIndex                      MoModifierTableIndex,
            moModifierAdminState                 AdminState,
            moModifierName                       NameString,
            moModifierOriginator                 E164Address,
            moModifierRecipient                  E164Address,
            moModifierImsi                       Imsi,
            moModifierUserDataCharsToStrip       UserDataLength,
            moModifierReplyPath                  BitValueModifier,
            moModifierStatusReportRequest        BitValueModifier,
            moModifierProtocolId                 ByteValueModifier,
            moModifierDataCodingScheme           ByteValueModifier,
            moModifierSmscAddress                E164Address
        }

    moModifierIndex OBJECT-TYPE
        SYNTAX  MoModifierTableIndex
        ACCESS  not-accessible
        STATUS  mandatory
        DESCRIPTION
            "Index of entry in MO modifier table."
        ::= { moModifierEntry 1 }

    moModifierAdminState OBJECT-TYPE
        SYNTAX  AdminState
        ACCESS  read-write
        STATUS  mandatory
        DESCRIPTION
            "Administrative state of the MO modifier.

            Transition from 'inactive' to 'active' is only possible when:
            1) name supplied and not already in use by another MO modifier;

            Transition from 'active' to 'inactive' is only possible when:
            1) MO modifier is not being referred.

            For details, refer to the comment on the AdminState type."
        ::= { moModifierEntry 2 }

    moModifierName OBJECT-TYPE
        SYNTAX  NameString
        ACCESS  read-write
        STATUS  mandatory
        DESCRIPTION
            "Name of the MO modifier."
        ::= { moModifierEntry 3 }

    moModifierOriginator OBJECT-TYPE
        SYNTAX  E164Address
        ACCESS  read-write
        STATUS  mandatory
        DESCRIPTION
            "E164 address that the MO modifier uses to change the originator
            of the SM. If a short number is to be set for the originator, the
            E164 address should contain that short number. In any other case,
            the E164 address should be specified in international format
            without the international prefix.

            Note that TextPass uses smsPropMaxLengthForShortNumber to
            determine whether a short number or a regular number is
            specified.

            If not specified or a zero-length E164 address is specified, the
            MO modifier does not affect the originator of the SM."
        ::= { moModifierEntry 4 }

    moModifierRecipient OBJECT-TYPE
        SYNTAX  E164Address
        ACCESS  read-write
        STATUS  mandatory
        DESCRIPTION
            "E164 address that the MO modifier uses to change the recipient
            of the SM. If a short number is to be set for the recipient, the
            E164 address should contain that short number. In any other case,
            the E164 address should be specified in international format
            without the international prefix.

            Note that TextPass uses smsPropMaxLengthForShortNumber to
            determine whether a short number or a regular number is
            specified.

            If not specified or a zero-length E164 address is specified, the
            MO modifier does not affect the recipient of the SM."
        ::= { moModifierEntry 5 }

    moModifierImsi OBJECT-TYPE
        SYNTAX  Imsi
        ACCESS  read-write
        STATUS  mandatory
        DESCRIPTION
            "Value that the MO modifier uses to change the IMSI of the SM.

            If not specified or a zero-length value is specified, the MO
            modifier does not affect the IMSI of the SM."
        ::= { moModifierEntry 6 }

    moModifierUserDataCharsToStrip OBJECT-TYPE
        SYNTAX  UserDataLength
        ACCESS  read-write
        STATUS  mandatory
        DESCRIPTION
            "Number of characters to strip from start of text string in user
            data of the SM.

            If not specified or a zero value is specified, the MO modifier
            does not affect the user data of the SM."
        ::= { moModifierEntry 7 }

    moModifierReplyPath OBJECT-TYPE
        SYNTAX  BitValueModifier
        ACCESS  read-write
        STATUS  mandatory
        DESCRIPTION
            "Value that the MO modifier uses to change the reply path bit of
            the SM.

            If not specified or -1 is specified, the MO modifier does not
            affect the reply path bit of the SM."
        ::= { moModifierEntry 8 }

    moModifierStatusReportRequest OBJECT-TYPE
        SYNTAX  BitValueModifier
        ACCESS  read-write
        STATUS  mandatory
        DESCRIPTION
            "Value that the MO modifier uses to change the status report
            request bit of the SM.

            If not specified or -1 is specified, the MO modifier does not
            affect the status report request bit of the SM."
        ::= { moModifierEntry 9 }

    moModifierProtocolId OBJECT-TYPE
        SYNTAX  ByteValueModifier
        ACCESS  read-write
        STATUS  mandatory
        DESCRIPTION
            "Value that the MO modifier uses to change the protocol ID of the
            SM.

            If not specified or -1 is specified, the MO modifier does not
            affect the protocol ID of the SM."
        ::= { moModifierEntry 10 }

    moModifierDataCodingScheme OBJECT-TYPE
        SYNTAX  ByteValueModifier
        ACCESS  read-write
        STATUS  mandatory
        DESCRIPTION
            "Value that the MO modifier uses to change the data coding scheme
            of the SM.

            If not specified or -1 is specified, the MO modifier does not
            affect the data coding scheme of the SM."
        ::= { moModifierEntry 11 }

    moModifierSmscAddress OBJECT-TYPE
        SYNTAX  E164Address
        ACCESS  read-write
        STATUS  mandatory
        DESCRIPTION
            "E164 address that the MO modifier uses to change the SMSC address
            at the MAP layer of the SM. The E164 address should be specified
            in international format without the international prefix.

            If not specified or a zero-length E164 address is specified, the
            MO modifier does not affect the recipient of the SM."
        ::= { moModifierEntry 12 }

    MtScramblingTableIndex ::=
        INTEGER(1..50)
   
    mtScramblingTable OBJECT-TYPE
        SYNTAX  SEQUENCE OF MtScramblingEntry
        ACCESS  not-accessible
        STATUS  mandatory
        DESCRIPTION
            "A list of MT scrambling entries used to define Scrambled IMSI
            ranges for the purposes of Spoof Checking. Also used to define
            the own network for plain Home Routing."
        ::= { sms 18 }

    mtScramblingEntry OBJECT-TYPE
        SYNTAX  MtScramblingEntry
        ACCESS  not-accessible
        STATUS  mandatory
        DESCRIPTION
            "Table entry specifying a single MT scrambling entry."
        INDEX   { mtScramblingIndex }
        ::= { mtScramblingTable 1 }

    MtScramblingEntry ::=
        SEQUENCE {
            mtScramblingIndex                          MtScramblingTableIndex,
            mtScramblingAdminState                     AdminState,
            mtScramblingName                           NameString,
            mtScramblingPriority                       Priority,
            mtScramblingImsiPrefix                     Imsi,
            mtScramblingRange                          ImsiRange,
            mtScramblingCount                          Counter
        }

    mtScramblingIndex OBJECT-TYPE
        SYNTAX  MtScramblingTableIndex
        ACCESS  read-write
        STATUS  mandatory
        DESCRIPTION
            "Index of entry in MT scrambling table."
        ::= { mtScramblingEntry 1 }
        
    mtScramblingAdminState OBJECT-TYPE
        SYNTAX  AdminState
        ACCESS  read-write
        STATUS  mandatory
        DESCRIPTION
            "Administrative state of the MT scrambling entry.

            For details, refer to the comment on the AdminState type."
        ::= { mtScramblingEntry 2 }
        
    mtScramblingName OBJECT-TYPE
        SYNTAX  NameString
        ACCESS  read-write
        STATUS  mandatory
        DESCRIPTION
            "Name of the MT scrambling entry."
        ::= { mtScramblingEntry 3 }
        
    mtScramblingPriority OBJECT-TYPE
        SYNTAX  Priority
        ACCESS  read-write
        STATUS  mandatory
        DESCRIPTION
            "Priority of the MT scrambling entry."
        ::= { mtScramblingEntry 4 }
        
    mtScramblingImsiPrefix OBJECT-TYPE
        SYNTAX  Imsi
        ACCESS  read-write
        STATUS  mandatory
        DESCRIPTION
            "The IMSI prefix is matched against the subscriber's IMSI returned
            in the SRI-SM response from the HLR. If a match is found, the 
            RTR/FWL applies either plain Home Routing (no IMSI scrambling) to 
            the corresponding MT message or scrambled Home Routing (using a 
            scrambled IMSI from the configured IMSI Scrambling Range) to the 
            corresponding MT message. 
            
            For instance, a 5 or 6 digit IMSI prefix can be used to match the 
            MCC+MNC of the IMSI.
                     
            An empty mtScrambleImsiPrefix matches always."
        ::= { mtScramblingEntry 5 }
        
    mtScramblingRange OBJECT-TYPE
        SYNTAX  ImsiRange
        ACCESS  read-write
        STATUS  mandatory
        DESCRIPTION
            "A range of IMSI's from which a Scrambled IMSI will be randomly
            chosen. The range must be expressed by two IMSI's, 5-15 digits
            long, both of the same length, the second higher than the first,
            separated by a dash, e.g. 204126100000000-204126199999999.
             
            Typically, a Scrambling IMSI Range would be selected to use the
            same prefixes as the IMSI Prefix of the IMSI it substitutes."
        ::= { mtScramblingEntry 6 }
        
    mtScramblingCount OBJECT-TYPE
        SYNTAX  Counter
        ACCESS  read-write
        STATUS  mandatory
        DESCRIPTION
            "Counter specifying the total number of times a scrambling table
            entry was applied."
        ::= { mtScramblingEntry 7 }

    -- mtModifierTable

    mtModifierTable OBJECT-TYPE
        SYNTAX  SEQUENCE OF MtModifierEntry
        ACCESS  not-accessible
        STATUS  mandatory
        DESCRIPTION
            "A list of MT modifier entries."
        ::= { sms 19 }

    mtModifierEntry OBJECT-TYPE
        SYNTAX  MtModifierEntry
        ACCESS  not-accessible
        STATUS  mandatory
        DESCRIPTION
            "Table entry specifying a single MT modifier."
        INDEX   { mtModifierIndex }
        ::= { mtModifierTable 1 }

    MtModifierEntry ::=
        SEQUENCE {
            mtModifierIndex                         MtModifierTableIndex,
            mtModifierAdminState                    AdminState,
            mtModifierName                          NameString,
            mtModifierTimeZone                      TimeZone,
            mtModifierReplyPath                     BitValueModifier,
            mtModifierSmsc                          E164Address,
            mtModifierOriginatorFormat              AddressFormat,
            mtModifierSmscAddressForSrism           E164Address,
            mtModifierSmscAddressForReportStatus    E164Address,
            mtModifierTruncateSrismRequestSccpCdpa  INTEGER(0..20),
            mtModifierPrefixSrismRequestSccpCdpa    E164Address,
            mtModifierReplaceSrismRequestSccpCdpa   E164Address
        }

    mtModifierIndex OBJECT-TYPE
        SYNTAX  MtModifierTableIndex
        ACCESS  not-accessible
        STATUS  mandatory
        DESCRIPTION
            "Index of entry in MT modifier table."
        ::= { mtModifierEntry 1 }

    mtModifierAdminState OBJECT-TYPE
        SYNTAX  AdminState
        ACCESS  read-write
        STATUS  mandatory
        DESCRIPTION
            "Administrative state of the MT modifier.

            Transition from 'inactive' to 'active' is only possible when:
            1) name supplied and not already in use by another MT modifier;

            Transition from 'active' to 'inactive' is only possible when:
            1) MT modifier is not being referred.

            For details, refer to the comment on the AdminState type."
        ::= { mtModifierEntry 2 }

    mtModifierName OBJECT-TYPE
        SYNTAX  NameString
        ACCESS  read-write
        STATUS  mandatory
        DESCRIPTION
            "Name of the MT modifier."
        ::= { mtModifierEntry 3 }

    mtModifierTimeZone OBJECT-TYPE
        SYNTAX  TimeZone
        ACCESS  read-write
        STATUS  mandatory
        DESCRIPTION
            "Timezone specification that the MT modifier uses to adapt fields
            in the SM that are specified an an absolute time with a timezone
            offset. The adaption comprises changing the timezone offset to
            the offset of the specified timezone and converting the absolute
            time to the corresponding value in the specified timezone.

            The relating fields are TP-SCTS (Service Centre Timestamp) in the
            SMS-DELIVER PDU and TP-SCTS (Service Centre Timestamp) and TP-DT
            (Discharge Time) of the STATUS-REPORT PDU.

            If not specified or a zero-length timezone is specified, the MT
            modifier does not adapt the time fields.

            This modifier is not applicable for MtForwardSm operations that
            are issued from an SMSC that is classied as 'suspect'."
        ::= { mtModifierEntry 4 }

    mtModifierReplyPath OBJECT-TYPE
        SYNTAX  BitValueModifier
        ACCESS  read-write
        STATUS  mandatory
        DESCRIPTION
            "Value that the MT modifier uses to change the reply path bit of
            the SM.

            If not specified or -1 is specified, the MT modifier does not
            affect the reply path bit of the SM."
        ::= { mtModifierEntry 5 }

    mtModifierSmsc OBJECT-TYPE
        SYNTAX  E164Address
        ACCESS  read-write
        STATUS  mandatory
        DESCRIPTION
            "E164 address that the MT modifier uses to change the SMSC
            address of the SM. The E164 address should be specified in
            international format without the international prefix.

            If not specified or a zero-length E164 address is specified, the
            MT modifier does not affect the SMSC of the SM."
        ::= { mtModifierEntry 6 }

    mtModifierOriginatorFormat OBJECT-TYPE
        SYNTAX  AddressFormat
        ACCESS  read-write
        STATUS  mandatory
        DESCRIPTION
            "Indicator specifying how the MT modifier will change the
            originator address in the SM:
            - If the value is 'national', the MT modifier will change the 
              originator address in the SM to  national format. 
            - When the value is equal to 'international', the originator in 
              the MT/SM will be encoded as international.
            - If the value is 'transparent', the MT  modifier does not affect 
              the originator address. 
            
            Note that this object has precedence over the
            smsPropFormatMtOriginatorForDomesticTraffic object. 
            smsPropFormatMtOriginatorForDomesticTraffic will only have effect 
            when this object is equal to 'transparent'.

            Default is transparent."
        ::= { mtModifierEntry 7 }

    mtModifierSmscAddressForSrism OBJECT-TYPE
        SYNTAX  E164Address
        ACCESS  read-write
        STATUS  mandatory
        DESCRIPTION
            "E164 address that the MT modifier uses to change the SMSC
            address of the SM during SRI_SM (SendRoutingInfoForSM) operation.
            The E164 address should be specified in international format
            without international prefix.

            If not specified or a zero-length E164 address is specified, the
            MT modifier does not affect the SMSC of the SM. If specified, it
            takes precedence over smsPropSmscAddressForHlrOperations."
        ::= { mtModifierEntry 8 }

    mtModifierSmscAddressForReportStatus OBJECT-TYPE
        SYNTAX  E164Address
        ACCESS  read-write
        STATUS  mandatory
        DESCRIPTION
            "E164 address that the MT modifier uses to change the SMSC
            address of the SM during Report SM Delivery Status operation. 
            The E164 address should be specified in international format
            without international prefix.

            If not specified or a zero-length E164 address is specified, the
            MT modifier does not affect the SMSC of the SM. If specified, it
            takes precedence over smsPropSmscAddressForHlrOperations."
        ::= { mtModifierEntry 9 }

    mtModifierTruncateSrismRequestSccpCdpa OBJECT-TYPE
        SYNTAX  INTEGER(0..20)
        ACCESS  read-write
        STATUS  mandatory
        DESCRIPTION
            "Number of digits to strip from the front of the global title to
            be used for the SCCP called party address of an SRI-SM request.
            The default value is zero. If the truncate length is greater than
            the SCCP CDPA address length, the entire address will be removed.
            A value of 20 will always remove the entire SCCP CDPA address.
            If not specified or set to zero, this MT modifier does not affect
            the SCCP called party address of the SRISM request.

            Truncation of the global title can be combined with prefixing, and
            gets overruled when combined with replacement."
        ::= { mtModifierEntry 10 }

    mtModifierPrefixSrismRequestSccpCdpa OBJECT-TYPE
        SYNTAX  E164Address
        ACCESS  read-write
        STATUS  mandatory
        DESCRIPTION
            "E164 address (part) to prefix in from of the global title to be
            used for the SCCP called party address of an SRI-SM request. The
            default value is empty. If not specified or a zero-length E164
            address is specified, the MT modifier does not affect the SCCP
            called party address of the SRISM request.

            Prefixing of the global title can be combined with truncation, and
            gets overruled when combined with replacement."
        ::= { mtModifierEntry 11 }

    mtModifierReplaceSrismRequestSccpCdpa OBJECT-TYPE
        SYNTAX  E164Address
        ACCESS  read-write
        STATUS  mandatory
        DESCRIPTION
            "E164 address to replace the global title to be used for the SCCP
            called party address of a SRISM request. The E164 address must be
            specified in international format without the international
            prefix.  The default value is empty. If not specified or a
            zero-length E164 address is specified, the MT modifier does not
            affect the SCCP called party address of the SRISM request.

            Replacement of the global title overrides truncation and
            prefixing, and should therefore not be configured together with
            truncation and prefixing."
        ::= { mtModifierEntry 12 }


    moCntRuleTable OBJECT-TYPE
        SYNTAX  SEQUENCE OF MoCntRuleEntry
        ACCESS  not-accessible
        STATUS  mandatory
        DESCRIPTION
            "A table containing properties, conditions, and counters for each
            MO counting rule.

            An MO counting rule matches when both of the following conditions
            are met:
            1) its administrative state is active;
            2) all its conditions do satisfy."
        ::= { sms 21 }

    moCntRuleEntry OBJECT-TYPE
        SYNTAX  MoCntRuleEntry
        ACCESS  not-accessible
        STATUS  mandatory
        DESCRIPTION
            "Table entry specifying a single MO counting rule."
        INDEX   { moCntRuleIndex }
        ::= { moCntRuleTable 1 }

    MoCntRuleEntry ::=
        SEQUENCE {
            moCntRuleIndex                        MoCntRuleTableIndex,
            moCntRuleAdminState                   AdminState,
            moCntRuleName                         NameString,
            moCntRuleLogProfile                   LogProfile,
            moCntRuleOriginatorCondition          ConditionSpec,
            moCntRuleRecipientCondition           ConditionSpec,
            moCntRuleSmscCondition                ConditionSpec,
            moCntRuleMscOrSgsnCondition           ConditionSpec,
            moCntRuleUserDataCondition            ConditionSpec,
            moCntRuleUserDataHeaderCondition      ConditionSpec,
            moCntRuleReplyPathCondition           ConditionSpec,
            moCntRuleStatusReportRequestCondition ConditionSpec,
            moCntRuleProtocolIdCondition          ConditionSpec,
            moCntRuleDataCodingSchemeCondition    ConditionSpec,
            moCntRuleRecipientTonCondition        ConditionSpec,
            moCntRuleRecipientNpiCondition        ConditionSpec,
            moCntRuleExternalAttributesCondition  ConditionSpec,
            moCntRuleSubmitTimeCondition          ConditionSpec,
            moCntRuleRecipientQueryResultCondition ConditionSpec,
            moCntRuleRecipientRoutingNumberGroupCondition ConditionSpec,
            moCntRuleOriginatorHlrCondition       ConditionSpec,
            moCntRuleMoTotalCounter               Counter,
            moCntRuleMoSuccessfulCounter          Counter,
            moCntRuleMoTimeoutCounter             Counter,
            moCntRuleMoDroppedCounter             Counter,
            moCntRuleMoDiscardWithNakCounter      Counter,
            moCntRuleMoRejectedByTprCounter       Counter,
            moCntRuleMoRejectedByAppCounter       Counter,
            moCntRuleMoUnknownResultCounter       Counter,
            moCntRuleMoSysFailErrorCounter        Counter,
            moCntRuleMoDataMisErrorCounter        Counter,
            moCntRuleMoUnexpDataValErrorCounter   Counter,
            moCntRuleMoFacNotSuppErrorCounter     Counter,
            moCntRuleMoUnkScErrorCounter          Counter,
            moCntRuleMoScCongErrorCounter         Counter,
            moCntRuleMoInvSmeAddrErrorCounter     Counter,
            moCntRuleMoSubNotScSubErrorCounter    Counter,
            moCntRuleMoOtherErrorsCounter         Counter,
            moCntRuleMoTcapAbortedCounter         Counter,
            moCntRuleMoSccpAbortedCounter         Counter
        }

    moCntRuleIndex OBJECT-TYPE
        SYNTAX  MoCntRuleTableIndex
        ACCESS  read-write
        STATUS  mandatory
        DESCRIPTION
            "Index of entry in MO counting rule table."

        ::= { moCntRuleEntry 1 }

    moCntRuleAdminState OBJECT-TYPE
        SYNTAX  AdminState
        ACCESS  read-write
        STATUS  mandatory
        DESCRIPTION
            "Administrative state of the MO counting rule.

            Transition from 'inactive' to 'active' is only possible when:
            1) name has been supplied;
            2) name is not already in use by another rule;
            3) conditions of rule specifying a network refer to an 'active'
               country and an 'active' network;
            4) conditions of rule specifying a country refer to an 'active'
               country;
            5) conditions of rule specifying an application refer to an
               'active' application;

            For details, refer to the comment on the AdminState type."
        ::= { moCntRuleEntry 2 }

    moCntRuleName OBJECT-TYPE
        SYNTAX  NameString
        ACCESS  read-write
        STATUS  mandatory
        DESCRIPTION
            "Name of the MO counting rule."
        ::= { moCntRuleEntry 3 }

    moCntRuleLogProfile OBJECT-TYPE
        SYNTAX  LogProfile
        ACCESS  read-write
        STATUS  mandatory
        DESCRIPTION
            "Identifier specifying which logging profile should be used.
            Default is 0 (i.e. 'none')."
        ::= { moCntRuleEntry 4 }

    moCntRuleOriginatorCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) SINGLEIMSI (*)
            7) IMSIRANGE (*)
            8) LIST

            For details on these formats, refer to the comment on the
            type.

            (*) Setting a condition on the IMSI is only possible when the
                setting smsPropAlwaysRetrieveOriginatorImsi is set to 'true'."
        ::= { moCntRuleEntry 21 }

    moCntRuleRecipientCondition OBJECT-TYPE
        SYNTAX  ConditionSpec
        ACCESS  read-write
        STATUS  mandatory
        DESCRIPTION
            "Condition pertaining to the recipient that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST
            12) ALPHANUMADDRESS

            For details on these formats, refer to the comment on the
            ConditionSpec type."
        ::= { moCntRuleEntry 22 }

    moCntRuleSmscCondition OBJECT-TYPE
        SYNTAX  ConditionSpec
        ACCESS  read-write
        STATUS  mandatory
        DESCRIPTION
            "Condition pertaining to the SMSC that is specified in the SM. For
            the specification for this condition, the following formats apply:

            1) NONE
            2) SINGLEMSISDN
            3) MSISDNRANGE
            4) MSISDNPREFIX
            5) LIST

            For details on these formats, refer to the comment on the
            ConditionSpec type."
        ::= { moCntRuleEntry 23 }

    moCntRuleMscOrSgsnCondition OBJECT-TYPE
        SYNTAX  ConditionSpec
        ACCESS  read-write
        STATUS  mandatory
        DESCRIPTION
            "Condition pertaining to the originating MSC that is specified in
            the SM. For the specification for this condition, the following
            formats apply:

            1) NONE
            2) SINGLEMSISDN
            3) MSISDNRANGE
            4) MSISDNPREFIX
            5) NETWORK
            6) COUNTRY
            7) SINGLEPOINTCODE
            8) POINTCODERANGE
            9) LIST

            For details on these formats, refer to the comment on the
            ConditionSpec type."
        ::= { moCntRuleEntry 24 }

    moCntRuleUserDataCondition  OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT

            For details on these formats, refer to the comment on the
            ConditionSpec type."
        ::= { moCntRuleEntry 25 }

    moCntRuleUserDataHeaderCondition  OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to GSM 03.40. The
            values for most common information element identifiers are:

            00 hex - Concatenated short message
            01 hex - Special SMS Message Indication
            04 hex - application port addressing scheme, 8 bit address
            05 hex - application port addressing scheme, 16 bit address
            06 hex - SMSC Control Parameters
            07 hex - UDH Source Indicator "
        ::= { moCntRuleEntry 26 }

    moCntRuleReplyPathCondition  OBJECT-TYPE
        SYNTAX  ConditionSpec
        ACCESS  read-write
        STATUS  mandatory
        DESCRIPTION
            "Condition pertaining to the reply path bit specified in the SM.
            For the specification for this condition, the following formats
            apply:

            1) NONE
            2) BITVALUE

            For details on these formats, refer to the comment on the
            ConditionSpec type."
        ::= { moCntRuleEntry 27 }

    moCntRuleStatusReportRequestCondition  OBJECT-TYPE
        SYNTAX  ConditionSpec
        ACCESS  read-write
        STATUS  mandatory
        DESCRIPTION
            "Condition pertaining to the status report request bit specified
            in the SM. For the specification for this condition, the
            following formats apply:

            1) NONE
            2) BITVALUE

            For details on these formats, refer to the comment on the
            ConditionSpec type."
        ::= { moCntRuleEntry 28 }

    moCntRuleProtocolIdCondition  OBJECT-TYPE
        SYNTAX  ConditionSpec
        ACCESS  read-write
        STATUS  mandatory
        DESCRIPTION
            "Condition pertaining to the protocol ID specified in the SM. For
            the specification for this condition, the following formats apply:

            1) NONE
            2) BYTEVALUE

            For details on these formats, refer to the comment on the
            ConditionSpec type.

            For details on the values supported for the protocol ID, refer to
            GSM 03.40."
        ::= { moCntRuleEntry 29 }


    moCntRuleDataCodingSchemeCondition  OBJECT-TYPE
        SYNTAX  ConditionSpec
        ACCESS  read-write
        STATUS  mandatory
        DESCRIPTION
            "Condition pertaining to the data coding scheme specified in the
            SM. For the specification for this condition, the following
            formats apply:

            1) NONE
            2) BYTEVALUE

            For details on these formats, refer to the comment on the
            ConditionSpec type.

            For details on the values supported for the data coding scheme,
            refer to GSM 03.38."
        ::= { moCntRuleEntry 30 }

    moCntRuleRecipientTonCondition  OBJECT-TYPE
        SYNTAX  ConditionSpec
        ACCESS  read-write
        STATUS  mandatory
        DESCRIPTION
            "Condition pertaining to the type of number (TON) specified for
            the recipient of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { moCntRuleEntry 31 }

    moCntRuleRecipientNpiCondition  OBJECT-TYPE
        SYNTAX  ConditionSpec
        ACCESS  read-write
        STATUS  mandatory
        DESCRIPTION
            "Condition pertaining to the numbering plan identification (NPI)
            specified for the recipient of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { moCntRuleEntry 32 }

    moCntRuleExternalAttributesCondition  OBJECT-TYPE
        SYNTAX  ConditionSpec
        ACCESS  read-write
        STATUS  mandatory
        DESCRIPTION
            "Condition on the 32 boolean atributes that can be set by an 
            external approval application. For the specification for this 
            condition, the following formats apply:

            1) NONE
            2) EXTERNALATTRIBUTES

            When the format is EXTERNALATTRIBUTES, the relating bit mask
            string specifies which external attributes apply and the relating
            bit value string specifies the values for the external
            attributes.          
            Each bit in the bit strings relates to a specific attribute. The
            bit strings consist of 32 bits. The least significant bit
            corresponds to attribute 0. The most significant bit corresponds
            to attribute 31. 
            A bit with value 1 in the bit mask string indicates that the
            relating attribute applies and needs to be checked. A bit with
            value 0 in the bit mask string indicates that the relating
            attribute does not apply and does not need to be checked. 
            A bit with value 1 in the bit value string indicates that the
            relating attribute should be TRUE. A bit with value 0 in the bit
            value string indicates that the relating attribute should be
            FALSE. 

            For further details on these formats, refer to the comment on the
            ConditionSpec type."
        ::= { moCntRuleEntry 33 }

    moCntRuleSubmitTimeCondition OBJECT-TYPE
        SYNTAX  ConditionSpec
        ACCESS  read-write
        STATUS  mandatory
        DESCRIPTION
            "Condition on the submit-time of the message. For the
            specification for this condition, the following formats apply:

            1) NONE
            2) TIMESPEC

            For further details on these formats, refer to the comment on the
            ConditionSpec type."
        ::= { moCntRuleEntry 34 }

    moCntRuleRecipientQueryResultCondition OBJECT-TYPE
        SYNTAX  ConditionSpec
        ACCESS  read-write
        STATUS  mandatory
        DESCRIPTION
            "Condition on the result of the HLR query for the recipient. In
            order for the condition to work, the recipient HLR query must have
            been performed before the MO routing rules are matched. This can
            be achieved through the smsPropHlrQueryForRecipientBeforeApproval
            property. For the specification for this condition, the following
            formats apply:

            1) NONE
            2) BITSTRING

            When the format is BITSTRING, the relating bit string specifies
            which HLR query results apply. Each bit in the bit string relates
            to a specific (or group of) query result(s). The (non-inverted)
            condition evaluates to true if the bit corresponding to the HLR
            query result is set to 1. Otherwise, the condition evaluates to
            false.

            Bit   Meaning
            -------------
            1     (any) permanent error
            2     (any) temporary error
            3-5   reserved for future error class types
            6     timeout
            7     system failure
            8     data missing
            9     unexpected data value
            10    facility not supported
            11    unknown subscriber
            12    absent subscriber
            13    call barred
            14    teleservice not provisioned
            15    tcap aborted
            16    sccp aborted
            17    other errors

            By default, the condition is set to NONE."
        ::= { moCntRuleEntry 35 }

    moCntRuleRecipientRoutingNumberGroupCondition OBJECT-TYPE
        SYNTAX  ConditionSpec
        ACCESS  read-write
        STATUS  mandatory
        DESCRIPTION
            "Condition on the group to which the routing number associated
            with the recipient address belongs. For the specification for
            this condition, the following formats apply:

            1) NONE
            2) SNMPINDEX

            When the format is SNMPINDEX, the SNMP index will refer to the
            routingNumberGroupTable. The (non-inverted) condition will
            never match if either the routing number group referred to by
            the condition is not active, or if no routing number has been
            determined for the recipient of the message under consideration.
            The RoutingNumberGroupIndex determines the range of valid numbers
            for the SNMP index."
        ::= { moCntRuleEntry 36 }

    moCntRuleOriginatorHlrCondition OBJECT-TYPE
        SYNTAX  ConditionSpec
        ACCESS  read-write
        STATUS  mandatory
        DESCRIPTION
            "Condition pertaining to the address of the HLR that is
            serving the originator of the message. In order to meaningfully
            apply this condition, the MNP or spoofing check must be applied
            before the MO rules, such that the HLR address is available to
            the router. For the specification for this condition, the
            following formats apply:

            1) NONE
            2) SINGLEMSISDN
            3) MSISDNRANGE
            4) MSISDNPREFIX
            5) NETWORK
            6) COUNTRY
            7) SINGLEPOINTCODE
            8) POINTCODERANGE
            9) LIST

            For details on these formats, refer to the comment on the
            ConditionSpec type."
        ::= { moCntRuleEntry 37 }

    moCntRuleMoTotalCounter OBJECT-TYPE
        SYNTAX  Counter
        ACCESS  read-write
        STATUS  mandatory
        DESCRIPTION
            "Counter specifying the total number of times an MO/SM was
            received."
        ::= { moCntRuleEntry 41 }

    moCntRuleMoSuccessfulCounter OBJECT-TYPE
        SYNTAX  Counter
        ACCESS  read-write
        STATUS  mandatory
        DESCRIPTION
            "Counter specifying the number of times an MO/SM was successfully
             routed to its destination. The following events result in
             incrementing of this counter:
             - receiving a MO/SM matching a rule with action equal to
               discardWithAck
             - receiving an ACK from an application as result of an MO/SM
               being routed to the application
             - receiving an ACK from an SMSC as result of an MO/SM being
               routed to the SMSC."
        ::= { moCntRuleEntry 42 }

    moCntRuleMoTimeoutCounter OBJECT-TYPE
        SYNTAX  Counter
        ACCESS  read-write
        STATUS  mandatory
        DESCRIPTION
            "Counter specifying the number of times that routing an MO/SM to
            its destination resulted in a timeout. The following events
            result in incrementing of this counter:
             - not receiving a response from an application on an MO/SM
               being routed to the application within the maximum response
               time
             - receiving an ACK from an SMSC as result of an MO/SM being
               routed to an SMSC within the maximum response time."
        ::= { moCntRuleEntry 43 }

    moCntRuleMoDroppedCounter OBJECT-TYPE
        SYNTAX  Counter
        ACCESS  read-write
        STATUS  mandatory
        DESCRIPTION
            "Counter specifying the number of times that an MO/SM has not
            been routed to its destination due to decimation (this is only
            applicable when routing to an application)."
        ::= { moCntRuleEntry 44 }

    moCntRuleMoDiscardWithNakCounter OBJECT-TYPE
        SYNTAX  Counter
        ACCESS  read-write
        STATUS  mandatory
        DESCRIPTION
            "Counter specifying the number of times that TPR has rejected an
            MO/SM as result of a routing rule with action equal to
            discardWithNak or because none of the routing rules match."
        ::= { moCntRuleEntry 45 }

    moCntRuleMoRejectedByTprCounter OBJECT-TYPE
        SYNTAX  Counter
        ACCESS  read-write
        STATUS  mandatory
        DESCRIPTION
            "Counter specifying the number of times that TPR has rejected an
            MO/SM as result of incorrect syntax of the MO/SM."
        ::= { moCntRuleEntry 46 }

    moCntRuleMoRejectedByAppCounter OBJECT-TYPE
        SYNTAX  Counter
        ACCESS  read-write
        STATUS  mandatory
        DESCRIPTION
            "Counter specifying the number of times that routing to an
            application resulted in the application rejecting the MO/SM by
            sending a NAK."
        ::= { moCntRuleEntry 47 }

    moCntRuleMoUnknownResultCounter OBJECT-TYPE
        SYNTAX  Counter
        ACCESS  read-write
        STATUS  mandatory
        DESCRIPTION
            "Counter specifying the number of times that the result of routing
            an MO/SM to its destination could not be retrieved (this is only
            applicable when using optimal routing towards an SMSC)."
        ::= { moCntRuleEntry 48 }

    moCntRuleMoSysFailErrorCounter OBJECT-TYPE
        SYNTAX  Counter
        ACCESS  read-write
        STATUS  mandatory
        DESCRIPTION
            "Counter specifying the number of times that routing to an SMSC
            resulted in the SMSC rejecting the MO/SM with a System-Failure
            error on MAP level."
        ::= { moCntRuleEntry 49 }

    moCntRuleMoDataMisErrorCounter OBJECT-TYPE
        SYNTAX  Counter
        ACCESS  read-write
        STATUS  mandatory
        DESCRIPTION
            "Counter specifying the number of times that routing to an SMSC
            resulted in the SMSC rejecting the MO/SM with a Data-Missing
            error on MAP level."
        ::= { moCntRuleEntry 50 }


    moCntRuleMoUnexpDataValErrorCounter OBJECT-TYPE
        SYNTAX  Counter
        ACCESS  read-write
        STATUS  mandatory
        DESCRIPTION
            "Counter specifying the number of times that routing to an SMSC
            resulted in the SMSC rejecting the MO/SM with a Unexpected-Data-
            Value error on MAP level."
        ::= { moCntRuleEntry 51 }

    moCntRuleMoFacNotSuppErrorCounter OBJECT-TYPE
        SYNTAX  Counter
        ACCESS  read-write
        STATUS  mandatory
        DESCRIPTION
            "Counter specifying the number of times that routing to an SMSC
            resulted in the SMSC rejecting the MO/SM with a Facility-Not-
            Supported error on MAP level."
        ::= { moCntRuleEntry 52 }

    moCntRuleMoUnkScErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Unknown-
            Service-Centre."
        ::= { moCntRuleEntry 53 }

    moCntRuleMoScCongErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to SC-
            Congestion."
        ::= { moCntRuleEntry 54 }

    moCntRuleMoInvSmeAddrErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Invalid-
            SME-Address."
        ::= { moCntRuleEntry 55 }

    moCntRuleMoSubNotScSubErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to
            Subscriber-Not-SC-Subscriber."
        ::= { moCntRuleEntry 56 }

    moCntRuleMoOtherErrorsCounter OBJECT-TYPE
        SYNTAX  Counter
        ACCESS  read-write
        STATUS  mandatory
        DESCRIPTION
            "Counter specifying the number of times that routing to an SMSC
            resulted in the SMSC rejecting the MO/SM with another MAP error
            (or possibly a failure cause) than specified for the
            other MO counters."
        ::= { moCntRuleEntry 57 }

    moCntRuleMoTcapAbortedCounter OBJECT-TYPE
        SYNTAX  Counter
        ACCESS  read-write
        STATUS  mandatory
        DESCRIPTION
            "Counter specifying the number of times that routing to an SMSC
            resulted in the SMSC rejecting the MO/SM by sending a TC-ABORT
            on TCAP level."
        ::= { moCntRuleEntry 58 }

    moCntRuleMoSccpAbortedCounter OBJECT-TYPE
        SYNTAX  Counter
        ACCESS  read-write
        STATUS  mandatory
        DESCRIPTION
            "Counter specifying the number of times that routing to an SMSC
            resulted in the SMSC rejecting the MO/SM by sending a UDTS on
            SCCP level."
        ::= { moCntRuleEntry 59 }


    mtCntRuleTable OBJECT-TYPE
        SYNTAX  SEQUENCE OF MtCntRuleEntry
        ACCESS  not-accessible
        STATUS  mandatory
        DESCRIPTION
            "A table containing properties, conditions, and counters for each
            MT counting rule.

            An MT counting rule matches when both of the following conditions
            are met:
            1) its administrative state is active
            2) all its conditions do satisfy"
        ::= { sms 22 }

    mtCntRuleEntry OBJECT-TYPE
        SYNTAX  MtCntRuleEntry
        ACCESS  not-accessible
        STATUS  mandatory
        DESCRIPTION
            "Table entry specifying a single MT counting rule."
        INDEX   { mtCntRuleIndex }

        ::= { mtCntRuleTable 1 }

    MtCntRuleEntry ::=
        SEQUENCE {
            mtCntRuleIndex                        MtCntRuleTableIndex,
            mtCntRuleAdminState                   AdminState,
            mtCntRuleName                         NameString,
            mtCntRuleLogProfile                   LogProfile,
            mtCntRuleOriginatorCondition          ConditionSpec,
            mtCntRuleRecipientCondition           ConditionSpec,
            mtCntRuleSmscCondition                ConditionSpec,
            mtCntRuleMscOrSgsnCondition           ConditionSpec,
            mtCntRuleUserDataCondition            ConditionSpec,
            mtCntRuleUserDataHeaderCondition      ConditionSpec,
            mtCntRuleReplyPathCondition           ConditionSpec,
            mtCntRuleStatusReportIndicationCondition ConditionSpec,
            mtCntRuleProtocolIdCondition          ConditionSpec,
            mtCntRuleDataCodingSchemeCondition    ConditionSpec,
            mtCntRuleOriginatorTonCondition       ConditionSpec,
            mtCntRuleOriginatorNpiCondition       ConditionSpec,
            mtCntRuleExternalAttributesCondition  ConditionSpec,
            mtCntRuleXsMessageTypeCondition       ConditionSpec,
            mtCntRuleMessageTypeCondition         ConditionSpec,
            mtCntRuleMtTotalCounter               Counter,
            mtCntRuleMtSuccessfulCounter          Counter,
            mtCntRuleMtTimeoutCounter             Counter,
            mtCntRuleMtAbsSubErrorCounter         Counter,
            mtCntRuleMtSysFailErrorCounter        Counter,
            mtCntRuleMtDataMisErrorCounter        Counter,
            mtCntRuleMtUnexpDataValErrorCounter   Counter,
            mtCntRuleMtFacNotSuppErrorCounter     Counter,
            mtCntRuleMtUnidenSubErrorCounter      Counter,
            mtCntRuleMtIllSubErrorCounter         Counter,
            mtCntRuleMtIllEquipErrorCounter       Counter,
            mtCntRuleMtSubBusyForMtSmErrorCounter Counter,
            mtCntRuleMtInvSmeAddrErrorCounter     Counter,
            mtCntRuleMtEquipProtErrorCounter      Counter,
            mtCntRuleMtEquipNotSmEquipErrorCounter Counter,
            mtCntRuleMtMemCapExcErrorCounter      Counter,
            mtCntRuleMtOtherErrorsCounter         Counter,
            mtCntRuleMtTcapAbortedCounter         Counter,
            mtCntRuleMtSccpAbortedCounter         Counter,
            mtCntRuleMtFallbackToVersion2Counter  Counter,
            mtCntRuleMtFallbackToVersion1Counter  Counter,
            mtCntRuleMtAlternatePathUsedCounter   Counter,
            mtCntRuleMtAlternatePathNotUsedCounter Counter,
            mtCntRuleSriSmTotalCounter            Counter,
            mtCntRuleSriSmSuccessCounter          Counter,
            mtCntRuleSriSmTimeoutCounter          Counter,
            mtCntRuleSriSmSysFailErrorCounter     Counter,
            mtCntRuleSriSmDataMisErrorCounter     Counter,
            mtCntRuleSriSmUnexpDataValErrorCounter Counter,
            mtCntRuleSriSmFacNotSuppErrorCounter  Counter,
            mtCntRuleSriSmUnkSubErrorCounter      Counter,
            mtCntRuleSriSmAbsSubErrorCounter      Counter,
            mtCntRuleSriSmCallBarredErrorCounter  Counter,
            mtCntRuleSriSmTeleServNotProvErrorCounter Counter,
            mtCntRuleSriSmOtherErrorsCounter      Counter,
            mtCntRuleSriSmTcapAbortedCounter      Counter,
            mtCntRuleSriSmSccpAbortedCounter      Counter,
            mtCntRuleSriSmFallbackToVersion2Counter Counter,
            mtCntRuleSriSmFallbackToVersion1Counter Counter,
            mtCntRuleRepStsTotalCounter           Counter,
            mtCntRuleRepStsSuccessCounter         Counter,
            mtCntRuleRepStsTimeoutCounter         Counter,
            mtCntRuleRepStsSysFailErrorCounter    Counter,
            mtCntRuleRepStsDataMisErrorCounter    Counter,
            mtCntRuleRepStsUnexpDataValErrorCounter Counter,
            mtCntRuleRepStsUnkSubErrorCounter     Counter,
            mtCntRuleRepStsMsgWaitListFullErrorCounter Counter,
            mtCntRuleRepStsOtherErrorsCounter     Counter,
            mtCntRuleRepStsTcapAbortedCounter     Counter,
            mtCntRuleRepStsSccpAbortedCounter     Counter,
            mtCntRuleRepStsFallbackToVersion2Counter Counter,
            mtCntRuleRepStsFallbackToVersion1Counter Counter
        }

    mtCntRuleIndex OBJECT-TYPE
        SYNTAX  MtCntRuleTableIndex
        ACCESS  read-write
        STATUS  mandatory
        DESCRIPTION
            "Index of entry in MT counting rule table."
        ::= { mtCntRuleEntry 1 }

    mtCntRuleAdminState OBJECT-TYPE
        SYNTAX  AdminState
        ACCESS  read-write
        STATUS  mandatory
        DESCRIPTION
            "Administrative state of the MT routing rule.

            Transition from 'inactive' to 'active' is only possible when:
            1) name has been supplied;
            2) name is not already in use by another rule;
            3) conditions of rule specifying a network refer to an 'active'
               country and an 'active' network;
            4) conditions of rule specifying a country refer to an 'active'
               country;
            5) conditions of rule specifying an application refer to an
               'active' application;

            For details, refer to the comment on the AdminState type."

        ::= { mtCntRuleEntry 2 }


    mtCntRuleName OBJECT-TYPE
        SYNTAX  NameString
        ACCESS  read-write
        STATUS  mandatory
        DESCRIPTION
            "Name of the MT routing rule."
        ::= { mtCntRuleEntry 3 }

    mtCntRuleLogProfile OBJECT-TYPE
        SYNTAX  LogProfile
        ACCESS  read-write
        STATUS  mandatory
        DESCRIPTION
            "Identifier specifying which logging profile should be used.
            Default is 0 (i.e. 'none')."
        ::= { mtCntRuleEntry 4 }

    mtCntRuleOriginatorCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) SINGLESHORTNUMBER
            6) SHORTNUMBERRANGE
            7) SHORTNUMBERPREFIX
            8) APPLICATION
            9) COUNTRY
            10) LIST
            11) ALPHANUMADDRESS 
           
            For details on these formats, refer to the comment on the
            ConditionSpec type."
        ::= { mtCntRuleEntry 21 }

    mtCntRuleRecipientCondition OBJECT-TYPE
        SYNTAX  ConditionSpec
        ACCESS  read-write
        STATUS  mandatory
        DESCRIPTION
            "Condition pertaining to the recipient that is specified in the
            SM.  For the specification for this condition, the following
            formats apply:

            1) NONE
            2) SINGLEMSISDN
            3) MSISDNRANGE
            4) MSISDNPREFIX
            5) COUNTRY
            6) NETWORK
            7) SINGLEIMSI
            8) IMSIRANGE
            9) LIST

            For details on these formats, refer to the comment on the
            ConditionSpec type."
        ::= { mtCntRuleEntry 22 }

    mtCntRuleSmscCondition OBJECT-TYPE
        SYNTAX  ConditionSpec
        ACCESS  read-write
        STATUS  mandatory
        DESCRIPTION
            "Condition pertaining to the SMSC that is specified in the SM. For
            the specification for this condition, the following formats apply:

            1) NONE
            2) SINGLEMSISDN
            3) MSISDNRANGE
            4) MSISDNPREFIX
            5) COUNTRY
            6) NETWORK
            7) LIST

            For details on these formats, refer to the comment on the
            ConditionSpec type."
        ::= { mtCntRuleEntry 23 }

    mtCntRuleMscOrSgsnCondition OBJECT-TYPE
        SYNTAX  ConditionSpec
        ACCESS  read-write
        STATUS  mandatory
        DESCRIPTION
            "Condition pertaining to the terminating MSC/SGSN that is
            specified in the SM. For the specification for this condition,
            the following formats apply:

            1) NONE
            2) SINGLEMSISDN
            3) MSISDNRANGE
            4) MSISDNPREFIX
            5) NETWORK
            6) COUNTRY
            7) SINGLEPOINTCODE
            8) POINTCODERANGE
            9) LIST

            For details on these formats, refer to the comment on the
            ConditionSpec type."
        ::= { mtCntRuleEntry 24 }

    mtCntRuleUserDataCondition  OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT

            For details on these formats, refer to the comment on the
            ConditionSpec type."
        ::= { mtCntRuleEntry 25 }

    mtCntRuleUserDataHeaderCondition  OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to GSM 03.40. The
            values for most common information element identifiers are:

            00 hex - Concatenated short message
            01 hex - Special SMS Message Indication
            04 hex - application port addressing scheme, 8 bit address

            05 hex - application port addressing scheme, 16 bit address
            06 hex - SMSC Control Parameters
            07 hex - UDH Source Indicator "
        ::= { mtCntRuleEntry 26 }

    mtCntRuleReplyPathCondition  OBJECT-TYPE
        SYNTAX  ConditionSpec
        ACCESS  read-write
        STATUS  mandatory
        DESCRIPTION
            "Condition pertaining to the reply path bit specified in the SM.
            For the specification for this condition, the following formats
            apply:

            1) NONE
            2) BITVALUE

            For details on these formats, refer to the comment on the
            ConditionSpec type."
        ::= { mtCntRuleEntry 27 }

    mtCntRuleStatusReportIndicationCondition  OBJECT-TYPE
        SYNTAX  ConditionSpec
        ACCESS  read-write
        STATUS  mandatory
        DESCRIPTION
            "Condition pertaining to the status report indication bit
            specified in the SM. For the specification for this condition,
            the following formats apply:

            1) NONE
            2) BITVALUE

            For details on these formats, refer to the comment on the
            ConditionSpec type."
        ::= { mtCntRuleEntry 28 }

    mtCntRuleProtocolIdCondition  OBJECT-TYPE
        SYNTAX  ConditionSpec
        ACCESS  read-write
        STATUS  mandatory
        DESCRIPTION
            "Condition pertaining to the protocol ID specified in the SM. For
            the specification for this condition, the following formats apply:

            1) NONE
            2) BYTEVALUE

            For details on these formats, refer to the comment on the
            ConditionSpec type.

            For details on the values supported for the protocol ID, refer to 
            GSM 03.40."
        ::= { mtCntRuleEntry 29 }


    mtCntRuleDataCodingSchemeCondition  OBJECT-TYPE
        SYNTAX  ConditionSpec
        ACCESS  read-write
        STATUS  mandatory
        DESCRIPTION
            "Condition pertaining to the data coding scheme specified in the
            SM. For the specification for this condition, the following
            formats apply:

            1) NONE
            2) BYTEVALUE

            For details on these formats, refer to the comment on the
            ConditionSpec type.

            For details on the values supported for the data coding scheme,
            refer to GSM 03.38."
        ::= { mtCntRuleEntry 30 }

    mtCntRuleOriginatorTonCondition  OBJECT-TYPE
        SYNTAX  ConditionSpec
        ACCESS  read-write
        STATUS  mandatory
        DESCRIPTION
            "Condition pertaining to the type of number (TON) specified for
            the originator of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { mtCntRuleEntry 31 }

    mtCntRuleOriginatorNpiCondition  OBJECT-TYPE
        SYNTAX  ConditionSpec
        ACCESS  read-write
        STATUS  mandatory
        DESCRIPTION
            "Condition pertaining to the numbering plan identification (NPI)
            specified for the originator of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { mtCntRuleEntry 32 }

    mtCntRuleExternalAttributesCondition  OBJECT-TYPE
        SYNTAX  ConditionSpec
        ACCESS  read-write
        STATUS  mandatory
        DESCRIPTION
            "Condition on the 32 boolean atributes that can be set by an 
            external approval application. For the specification for this 
            condition, the following formats apply:

            1) NONE
            2) EXTERNALATTRIBUTES

            When the format is EXTERNALATTRIBUTES, the relating bit mask
            string specifies which external attributes apply and the relating
            bit value string specifies the values for the external
            attributes.          
            Each bit in the bit strings relates to a specific attribute. The
            bit strings consist of 32 bits. The least significant bit
            corresponds to attribute 0. The most significant bit corresponds
            to attribute 31. 
            A bit with value 1 in the bit mask string indicates that the
            relating attribute applies and needs to be checked. A bit with
            value 0 in the bit mask string indicates that the relating
            attribute does not apply and does not need to be checked. 
            A bit with value 1 in the bit value string indicates that the
            relating attribute should be TRUE. A bit with value 0 in the bit
            value string indicates that the relating attribute should be
            FALSE. 

            For further details on these formats, refer to the comment on the
            ConditionSpec type."
        ::= { mtCntRuleEntry 33 }

    mtCntRuleXsMessageTypeCondition OBJECT-TYPE
        SYNTAX  ConditionSpec
        ACCESS  read-write
        STATUS  mandatory
        DESCRIPTION
            "Condition pertaining to the external service (XS) message type
            applicable for this SM.
            For the specification for this condition, the following formats
            apply:

            1) NONE
            2) BITSTRING

            When the format is BITSTRING, the relating bit string specifies
            which values for the XS message type apply. Each bit in the bit
            string relates to a XS message type. If the bit is 1, the relating
            XS message type applies. Otherwise, if the bit is 0, the relating
            XS message type does not apply.
            The valid message types are:
                noXsMessage(0),
                forwardedMessage (1),
                copiedMessage (2)

            The range of valid values is 0-3. As such, the bit string consists
            of 3 bits, with the least significant bit indicating whether
            XS message type 0 (noXsMessage) applies and the most significant
            bit indicating whether XS message type 2 (copiedMessage) applies.

            For further details on these formats, refer to the comment on the
            ConditionSpec type."
        ::= { mtCntRuleEntry 34 }

    mtCntRuleMessageTypeCondition OBJECT-TYPE
        SYNTAX  ConditionSpec
        ACCESS  read-write
        STATUS  mandatory
        DESCRIPTION
            "Condition pertaining to the message type applicable for this SM.
            For the specification for this condition, the following formats
            apply:

            1) NONE
            2) BITSTRING

            When the format is BITSTRING, the relating bit string specifies
            which values for the message type apply. Each bit in the bit
            string relates to a message type. If the bit is 1, the relating
            message type applies. Otherwise, if the bit is 0, the relating
            message type does not apply.
            The valid message types are:
                shortMessage (0),
                sendRoutingInfoForSmRequest (1),
                sendRoutingInfoForSmResponse (2),
                statusReport (3)

            Note that for SendRoutingInfoForSm responses, the MT counting
            rules are currently not evaluated, and setting the corresponding
            bit to 1 therefore has no effect.

            As such, the bit string consists of 4 bits, with the least
            significant bit indicating whether message type 0 (shortMessage)
            applies and the most significant bit indicating whether message
            type 3 (statusReport) applies.

            For further details on these formats, refer to the comment on the
            ConditionSpec type."
        ::= { mtCntRuleEntry 35 }

    mtCntRuleMtTotalCounter OBJECT-TYPE
        SYNTAX  Counter
        ACCESS  read-write
        STATUS  mandatory
        DESCRIPTION
            "Counter specifying the total number of times an MT/SM was issued
            by the TPR. This counter is incremented whenever:
            - the TPR issues a MT/SM on behalf of an application that is
              directly connected to the TPR
            - the TPR receives all MT/SM's from an SMSC and directs the MT/SM
              to its destination."
        ::= { mtCntRuleEntry 60 }

    mtCntRuleMtSuccessfulCounter OBJECT-TYPE
        SYNTAX  Counter
        ACCESS  read-write
        STATUS  mandatory
        DESCRIPTION
            "Counter specifying the number of times an MT/SM was successfully
            delivered."
        ::= { mtCntRuleEntry 61 }

    mtCntRuleMtTimeoutCounter OBJECT-TYPE
        SYNTAX  Counter
        ACCESS  read-write
        STATUS  mandatory
        DESCRIPTION
            "Counter specifying the number of times that delivering an MT/SM
            resulted in a timeout."
        ::= { mtCntRuleEntry 62 }

    mtCntRuleMtAbsSubErrorCounter OBJECT-TYPE
        SYNTAX  Counter
        ACCESS  read-write
        STATUS  mandatory
        DESCRIPTION
            "Counter specifying the number of times that delivering an MT/SM
            resulted in an Absent-Subscriber error."
        ::= { mtCntRuleEntry 63 }

    mtCntRuleMtSysFailErrorCounter OBJECT-TYPE
        SYNTAX  Counter
        ACCESS  read-write
        STATUS  mandatory
        DESCRIPTION
            "Counter specifying the number of times that delivering an MT/SM
            resulted in an System-Failure error."
        ::= { mtCntRuleEntry 64 }

    mtCntRuleMtDataMisErrorCounter OBJECT-TYPE
        SYNTAX  Counter
        ACCESS  read-write
        STATUS  mandatory
        DESCRIPTION
            "Counter specifying the number of times that delivering an MT/SM
            resulted in an Data-Missing error."
        ::= { mtCntRuleEntry 65 }

    mtCntRuleMtUnexpDataValErrorCounter OBJECT-TYPE
        SYNTAX  Counter
        ACCESS  read-write
        STATUS  mandatory
        DESCRIPTION
            "Counter specifying the number of times that delivering an MT/SM
            resulted in an Unexpected-Data-Value error."
        ::= { mtCntRuleEntry 66 }

    mtCntRuleMtFacNotSuppErrorCounter OBJECT-TYPE
        SYNTAX  Counter
        ACCESS  read-write
        STATUS  mandatory
        DESCRIPTION
            "Counter specifying the number of times that delivering an MT/SM
            resulted in an Facility-Not-Supported error."
        ::= { mtCntRuleEntry 67 }

    mtCntRuleMtUnidenSubErrorCounter OBJECT-TYPE
        SYNTAX  Counter

        ACCESS  read-write
        STATUS  mandatory
        DESCRIPTION
            "Counter specifying the number of times that delivering an MT/SM
            resulted in an Unidentified-Subscriber error."
        ::= { mtCntRuleEntry 68 }

    mtCntRuleMtIllSubErrorCounter OBJECT-TYPE
        SYNTAX  Counter
        ACCESS  read-write
        STATUS  mandatory

        DESCRIPTION
            "Counter specifying the number of times that delivering an MT/SM
            resulted in an Illegal-Subscriber error."
        ::= { mtCntRuleEntry 69 }

    mtCntRuleMtIllEquipErrorCounter OBJECT-TYPE
        SYNTAX  Counter
        ACCESS  read-write
        STATUS  mandatory
        DESCRIPTION
            "Counter specifying the number of times that delivering an MT/SM
            resulted in an Illegal-Equipment error."
        ::= { mtCntRuleEntry 70 }

    mtCntRuleMtSubBusyForMtSmErrorCounter OBJECT-TYPE
        SYNTAX  Counter
        ACCESS  read-write
        STATUS  mandatory
        DESCRIPTION
            "Counter specifying the number of times that delivering an MT/SM
            resulted in an Subscriber-Busy-For-MT-SMS error."
        ::= { mtCntRuleEntry 71 }

    mtCntRuleMtInvSmeAddrErrorCounter OBJECT-TYPE
        SYNTAX  Counter
        ACCESS  read-write
        STATUS  mandatory
        DESCRIPTION
            "Counter specifying the number of times that delivering an MT/SM
            resulted in a SM-Delivery-Failure error with failure cause equal
            to Invalid-SME-Address."
        ::= { mtCntRuleEntry 72 }

    mtCntRuleMtEquipProtErrorCounter OBJECT-TYPE
        SYNTAX  Counter
        ACCESS  read-write
        STATUS  mandatory
        DESCRIPTION
            "Counter specifying the number of times that delivering an MT/SM
            resulted in a SM-Delivery-Failure error with failure cause equal
            to Equipment-Protocol-Error."
        ::= { mtCntRuleEntry 73 }

    mtCntRuleMtEquipNotSmEquipErrorCounter OBJECT-TYPE

        SYNTAX  Counter
        ACCESS  read-write
        STATUS  mandatory
        DESCRIPTION
            "Counter specifying the number of times that delivering an MT/SM
            resulted in a SM-Delivery-Failure error with failure cause equal
            to Equipment-Not-SM-equipped."
        ::= { mtCntRuleEntry 74 }

    mtCntRuleMtMemCapExcErrorCounter OBJECT-TYPE
        SYNTAX  Counter
        ACCESS  read-write
        STATUS  mandatory
        DESCRIPTION
            "Counter specifying the number of times that delivering an MT/SM
            resulted in a SM-Delivery-Failure error with failure cause equal
            to Memory-Capacity-Exceeded."
        ::= { mtCntRuleEntry 75 }

    mtCntRuleMtOtherErrorsCounter OBJECT-TYPE
        SYNTAX  Counter
        ACCESS  read-write
        STATUS  mandatory
        DESCRIPTION
            "Counter specifying the number of times that delivering an MT/SM
            resulted in another MAP error (or possibly a failure cause) than
            specified for the other MT counters."
        ::= { mtCntRuleEntry 76 }

    mtCntRuleMtTcapAbortedCounter OBJECT-TYPE
        SYNTAX  Counter
        ACCESS  read-write
        STATUS  mandatory
        DESCRIPTION
            "Counter specifying the number of times that delivering an MT/SM
            resulted in the MSC/SGSN rejecting the MT/SM by sending a TC-ABORT
            on TCAP level."
        ::= { mtCntRuleEntry 77 }

    mtCntRuleMtSccpAbortedCounter OBJECT-TYPE

        SYNTAX  Counter
        ACCESS  read-write
        STATUS  mandatory
        DESCRIPTION
            "Counter specifying the number of times that delivering an MT/SM
            resulted in the MSC/SGSN rejecting the MT/SM by sending a UDTS on
            SCCP level."
        ::= { mtCntRuleEntry 78 }

    mtCntRuleMtFallbackToVersion2Counter OBJECT-TYPE
        SYNTAX  Counter
        ACCESS  read-write
        STATUS  mandatory
        DESCRIPTION
            "Counter specifying the number of times that delivering an MT/SM
            resulted in the MSC/SGSN requesting to fallback to MAP version 2."
        ::= { mtCntRuleEntry 79 }

    mtCntRuleMtFallbackToVersion1Counter OBJECT-TYPE
        SYNTAX  Counter
        ACCESS  read-write
        STATUS  mandatory
        DESCRIPTION
            "Counter specifying the number of times that delivering an MT/SM
            resulted in the MSC/SGSN requesting to fallback to MAP version 1."
        ::= { mtCntRuleEntry 80 }

    mtCntRuleMtAlternatePathUsedCounter OBJECT-TYPE
        SYNTAX  Counter
        ACCESS  read-write
        STATUS  mandatory
        DESCRIPTION
            "Counter specifying the number of times that for delivering an
            MT/SM both paths (through MSC and through SGSN) were available
            and that delivery on the primary path failed (and the alternate
            path was thus used)."
        ::= { mtCntRuleEntry 81 }

    mtCntRuleMtAlternatePathNotUsedCounter OBJECT-TYPE
        SYNTAX  Counter
        ACCESS  read-write
        STATUS  mandatory
        DESCRIPTION
            "Counter specifying the number of times that for delivering an
            MT/SM both paths (through MSC and through SGSN) were available
            and that delivery on the primary path succeeded (and the
            alternate path was thus not used)."
        ::= { mtCntRuleEntry 82 }

    mtCntRuleSriSmTotalCounter OBJECT-TYPE
        SYNTAX  Counter
        ACCESS  read-write
        STATUS  mandatory
        DESCRIPTION
            "Counter specifying the total number of times a Send-Routing-Info-
            For-SM operation was issued
            by the TPR. This counter is incremented whenever:
            - the TPR issues a Send-Routing-Info-For-SM operation as part of
              the delivery of a MT/SM that was sent by an application that is
              directly connected to the TPR
            - the TPR receives all Send-Routing-Info-For-SM operations from
              an SMSC and directs the opeation to its destination."
        ::= { mtCntRuleEntry 83 }

    mtCntRuleSriSmSuccessCounter OBJECT-TYPE
        SYNTAX  Counter
        ACCESS  read-write
        STATUS  mandatory
        DESCRIPTION
            "Counter specifying the number of times a Send-Routing-Info-For-
            SM operation was successfully issued."
        ::= { mtCntRuleEntry 84 }

    mtCntRuleSriSmTimeoutCounter OBJECT-TYPE
        SYNTAX  Counter
        ACCESS  read-write
        STATUS  mandatory
        DESCRIPTION
            "Counter specifying the number of times that issueing a
            Send-Routing- Info-For-SM operation resulted in a timeout."
        ::= { mtCntRuleEntry 85 }

    mtCntRuleSriSmSysFailErrorCounter OBJECT-TYPE
        SYNTAX  Counter
        ACCESS  read-write
        STATUS  mandatory
        DESCRIPTION
            "Counter specifying the number of times that issueing a
            Send-Routing- Info-For-SM operation resulted in a System-Failure
            error."
        ::= { mtCntRuleEntry 86 }

    mtCntRuleSriSmDataMisErrorCounter OBJECT-TYPE
        SYNTAX  Counter
        ACCESS  read-write
        STATUS  mandatory
        DESCRIPTION
            "Counter specifying the number of times that issueing a
            Send-Routing- Info-For-SM operation resulted in a Data-Missing
            error."
        ::= { mtCntRuleEntry 87 }

    mtCntRuleSriSmUnexpDataValErrorCounter OBJECT-TYPE
        SYNTAX  Counter
        ACCESS  read-write
        STATUS  mandatory
        DESCRIPTION
            "Counter specifying the number of times that issueing a
            Send-Routing- Info-For-SM operation resulted in a
            Unexpected-Data-Value error."
        ::= { mtCntRuleEntry 88 }

    mtCntRuleSriSmFacNotSuppErrorCounter OBJECT-TYPE
        SYNTAX  Counter
        ACCESS  read-write
        STATUS  mandatory
        DESCRIPTION
            "Counter specifying the number of times that issueing a
            Send-Routing- Info-For-SM operation resulted in a
            Facility-Not-Supported error."
        ::= { mtCntRuleEntry 89 }

    mtCntRuleSriSmUnkSubErrorCounter OBJECT-TYPE
        SYNTAX  Counter
        ACCESS  read-write
        STATUS  mandatory
        DESCRIPTION
            "Counter specifying the number of times that issueing a
            Send-Routing- Info-For-SM operation resulted in a
            Unknown-Subscriber error."
        ::= { mtCntRuleEntry 90 }

    mtCntRuleSriSmAbsSubErrorCounter OBJECT-TYPE
        SYNTAX  Counter
        ACCESS  read-write
        STATUS  mandatory
        DESCRIPTION
            "Counter specifying the number of times that issueing a
            Send-Routing- Info-For-SM operation resulted in a
            Absent-Subscriber error."
        ::= { mtCntRuleEntry 91 }

    mtCntRuleSriSmCallBarredErrorCounter OBJECT-TYPE
        SYNTAX  Counter
        ACCESS  read-write

        STATUS  mandatory
        DESCRIPTION
            "Counter specifying the number of times that issueing a
            Send-Routing- Info-For-SM operation resulted in a Call-Barred
            error."
        ::= { mtCntRuleEntry 92 }

    mtCntRuleSriSmTeleServNotProvErrorCounter OBJECT-TYPE
        SYNTAX  Counter
        ACCESS  read-write
        STATUS  mandatory
        DESCRIPTION
            "Counter specifying the number of times that issueing a
            Send-Routing- Info-For-SM operation resulted in a
            Teleservice-Not-Provisioned error."
        ::= { mtCntRuleEntry 93 }

    mtCntRuleSriSmOtherErrorsCounter OBJECT-TYPE
        SYNTAX  Counter
        ACCESS  read-write
        STATUS  mandatory
        DESCRIPTION
            "Counter specifying the number of times that issueing a
            Send-Routing- Info-For-SM operation resulted in another error
            than specified for the other Send-Routing-Info-For-SM counters."
        ::= { mtCntRuleEntry 94 }

    mtCntRuleSriSmTcapAbortedCounter OBJECT-TYPE
        SYNTAX  Counter
        ACCESS  read-write
        STATUS  mandatory
        DESCRIPTION
            "Counter specifying the number of times that issueing a
            Send-Routing- Info-For-SM operation resulted in the HLR rejecting
            the operation by sending a TC-ABORT on TCAP level."
        ::= { mtCntRuleEntry 95 }

    mtCntRuleSriSmSccpAbortedCounter OBJECT-TYPE
        SYNTAX  Counter
        ACCESS  read-write
        STATUS  mandatory
        DESCRIPTION
            "Counter specifying the number of times that issueing a
            Send-Routing- Info-For-SM operation resulted in the HLR rejecting
            the operation by sending a UDTS on SCCP level."
        ::= { mtCntRuleEntry 96 }

    mtCntRuleSriSmFallbackToVersion2Counter OBJECT-TYPE
        SYNTAX  Counter
        ACCESS  read-write
        STATUS  mandatory
        DESCRIPTION
            "Counter specifying the number of times that issueing a
            Send-Routing- Info-For-SM operation resulted in the HLR
            requesting to fallback to MAP version 2."
        ::= { mtCntRuleEntry 97 }

    mtCntRuleSriSmFallbackToVersion1Counter OBJECT-TYPE
        SYNTAX  Counter
        ACCESS  read-write
        STATUS  mandatory
        DESCRIPTION
            "Counter specifying the number of times that issueing a
            Send-Routing- Info-For-SM operation resulted in the HLR
            requesting to fallback to MAP version 1."
        ::= { mtCntRuleEntry 98 }

    mtCntRuleRepStsTotalCounter OBJECT-TYPE
        SYNTAX  Counter
        ACCESS  read-write
        STATUS  mandatory
        DESCRIPTION
            "Counter specifying the total number of times a Report-SM-
            Delivery-Status operation was issued
            by the TPR. This counter is incremented whenever:
            - the TPR issues a Report-SM-Delivery-Status operation as part of
              the delivery of a MT/SM that was sent by an application that is
              directly connected to the TPR
            - the TPR receives all Report-SM-Delivery-Status operations from
              an SMSC and directs the opeation to its destination."
        ::= { mtCntRuleEntry 99 }

    mtCntRuleRepStsSuccessCounter OBJECT-TYPE
        SYNTAX  Counter
        ACCESS  read-write
        STATUS  mandatory
        DESCRIPTION
            "Counter specifying the number of times a Report-SM-Delivery-
            Status operation was successfully issued."
        ::= { mtCntRuleEntry 100 }

    mtCntRuleRepStsTimeoutCounter OBJECT-TYPE
        SYNTAX  Counter
        ACCESS  read-write
        STATUS  mandatory
        DESCRIPTION
            "Counter specifying the number of times that issueing a Report-SM-
            Delivery-Status operation resulted in a timeout."
        ::= { mtCntRuleEntry 101 }

    mtCntRuleRepStsSysFailErrorCounter OBJECT-TYPE
        SYNTAX  Counter
        ACCESS  read-write
        STATUS  mandatory
        DESCRIPTION
            "Counter specifying the number of times that issueing a Report-SM-
            Delivery-Status operation resulted in a System-Failure error."
        ::= { mtCntRuleEntry 102 }

    mtCntRuleRepStsDataMisErrorCounter OBJECT-TYPE
        SYNTAX  Counter
        ACCESS  read-write
        STATUS  mandatory
        DESCRIPTION
            "Counter specifying the number of times that issueing a Report-SM-
            Delivery-Status operation resulted in a Data-Missing error."
        ::= { mtCntRuleEntry 103 }

    mtCntRuleRepStsUnexpDataValErrorCounter OBJECT-TYPE
        SYNTAX  Counter
        ACCESS  read-write
        STATUS  mandatory
        DESCRIPTION
            "Counter specifying the number of times that issueing a Report-SM-
            Delivery-Status operation resulted in a Unexpected-Data-Value
            error."
        ::= { mtCntRuleEntry 104 }

    mtCntRuleRepStsUnkSubErrorCounter OBJECT-TYPE
        SYNTAX  Counter
        ACCESS  read-write
        STATUS  mandatory
        DESCRIPTION
           "Counter specifying the number of times that issueing a Report-SM-
            Delivery-Status operation resulted in a Unknown-Subscriber
            error."
        ::= { mtCntRuleEntry 105 }

    mtCntRuleRepStsMsgWaitListFullErrorCounter OBJECT-TYPE
        SYNTAX  Counter
        ACCESS  read-write
        STATUS  mandatory
        DESCRIPTION
           "Counter specifying the number of times that issueing a Report-SM-
            Delivery-Status operation resulted in a Message-Waiting-List-Full
            error."
        ::= { mtCntRuleEntry 106 }

    mtCntRuleRepStsOtherErrorsCounter OBJECT-TYPE
        SYNTAX  Counter
        ACCESS  read-write
        STATUS  mandatory
        DESCRIPTION
            "Counter specifying the number of times that issueing a
            Report-SM- Delivery-Status operation resulted in in another error
            than specified for the other Report-SM-Delivery-Status counters."
        ::= { mtCntRuleEntry 107 }

    mtCntRuleRepStsTcapAbortedCounter OBJECT-TYPE
        SYNTAX  Counter
        ACCESS  read-write
        STATUS  mandatory
        DESCRIPTION
            "Counter specifying the number of times that issueing a Report-SM-
            Delivery-Status operation resulted in the HLR rejecting the
            operation by sending a TC-ABORT on TCAP level."
        ::= { mtCntRuleEntry 108 }

    mtCntRuleRepStsSccpAbortedCounter OBJECT-TYPE
        SYNTAX  Counter
        ACCESS  read-write
        STATUS  mandatory
        DESCRIPTION
            "Counter specifying the number of times that issueing a Report-SM-
            Delivery-Status operation resulted in the HLR rejecting the
            operation by sending a UDTS on SCCP level."
        ::= { mtCntRuleEntry 109 }

    mtCntRuleRepStsFallbackToVersion2Counter OBJECT-TYPE
        SYNTAX  Counter
        ACCESS  read-write
        STATUS  mandatory
        DESCRIPTION
            "Counter specifying the number of times that issueing a Report-SM-
            Delivery-Status operation resulted in the HLR requesting to
            fallback to MAP version 2."
        ::= { mtCntRuleEntry 110 }

    mtCntRuleRepStsFallbackToVersion1Counter OBJECT-TYPE
        SYNTAX  Counter
        ACCESS  read-write
        STATUS  mandatory
        DESCRIPTION
            "Counter specifying the number of times that issueing a Report-SM-
            Delivery-Status operation resulted in the HLR requesting to
            fallback to MAP version 1."
        ::= { mtCntRuleEntry 111 }

    countryTable OBJECT-TYPE
        SYNTAX  SEQUENCE OF CountryEntry
        ACCESS  not-accessible
        STATUS  mandatory
        DESCRIPTION
            "A table defining the properties of each country."
        ::= { sms 31 }

    countryEntry OBJECT-TYPE
        SYNTAX  CountryEntry
        ACCESS  not-accessible
        STATUS  mandatory
        DESCRIPTION
            "Table entry defining a single country."
        INDEX   { countryIndex }
        ::= { countryTable 1 }

    CountryEntry ::=
        SEQUENCE {
            countryIndex                          CountryTableIndex,
            countryAdminState                     AdminState,
            countryCountry                        Country,
            countryCountryCode                    E164Address,
            countryMobileCountryCode              MobileCountryCodes,
            countryMoTotalCounter                 Counter,
            countryMoSuccessfulCounter            Counter,
            countryMoTimeoutCounter               Counter,
            countryMoDroppedCounter               Counter,
            countryMoDiscardWithNakCounter        Counter,
            countryMoRejectedByTprCounter         Counter,
            countryMoRejectedByAppCounter         Counter,
            countryMoUnknownResultCounter         Counter,
            countryMoSysFailErrorCounter          Counter,
            countryMoDataMisErrorCounter          Counter,
            countryMoUnexpDataValErrorCounter     Counter,
            countryMoFacNotSuppErrorCounter       Counter,
            countryMoUnkScErrorCounter            Counter,
            countryMoScCongErrorCounter           Counter,
            countryMoInvSmeAddrErrorCounter       Counter,
            countryMoSubNotScSubErrorCounter      Counter,
            countryMoOtherErrorsCounter           Counter,
            countryMoTcapAbortedCounter           Counter,
            countryMoSccpAbortedCounter           Counter,
            countryMtTotalCounter                 Counter,
            countryMtSuccessfulCounter            Counter,
            countryMtTimeoutCounter               Counter,
            countryMtAbsSubErrorCounter           Counter,
            countryMtSysFailErrorCounter          Counter,
            countryMtDataMisErrorCounter          Counter,
            countryMtUnexpDataValErrorCounter     Counter,
            countryMtFacNotSuppErrorCounter       Counter,
            countryMtUnidenSubErrorCounter        Counter,
            countryMtIllSubErrorCounter           Counter,
            countryMtIllEquipErrorCounter         Counter,
            countryMtSubBusyForMtSmErrorCounter   Counter,
            countryMtInvSmeAddrErrorCounter       Counter,
            countryMtEquipProtErrorCounter        Counter,
            countryMtEquipNotSmEquipErrorCounter  Counter,
            countryMtMemCapExcErrorCounter        Counter,
            countryMtOtherErrorsCounter           Counter,
            countryMtTcapAbortedCounter           Counter,
            countryMtSccpAbortedCounter           Counter,
            countryMtFallbackToVersion2Counter    Counter,
            countryMtFallbackToVersion1Counter    Counter,
            countryMtAlternatePathUsedCounter     Counter,
            countryMtAlternatePathNotUsedCounter  Counter,
            countrySriSmTotalCounter              Counter,
            countrySriSmSuccessCounter            Counter,
            countrySriSmTimeoutCounter            Counter,
            countrySriSmSysFailErrorCounter       Counter,
            countrySriSmDataMisErrorCounter       Counter,
            countrySriSmUnexpDataValErrorCounter  Counter,
            countrySriSmFacNotSuppErrorCounter    Counter,
            countrySriSmUnkSubErrorCounter        Counter,
            countrySriSmAbsSubErrorCounter        Counter,
            countrySriSmCallBarredErrorCounter    Counter,
            countrySriSmTeleServNotProvErrorCounter Counter,
            countrySriSmOtherErrorsCounter        Counter,
            countrySriSmTcapAbortedCounter        Counter,
            countrySriSmSccpAbortedCounter        Counter,
            countrySriSmFallbackToVersion2Counter Counter,
            countrySriSmFallbackToVersion1Counter Counter,
            countryRepStsTotalCounter             Counter,
            countryRepStsSuccessCounter           Counter,
            countryRepStsTimeoutCounter           Counter,
            countryRepStsSysFailErrorCounter      Counter,
            countryRepStsDataMisErrorCounter      Counter,
            countryRepStsUnexpDataValErrorCounter Counter,
            countryRepStsUnkSubErrorCounter       Counter,
            countryRepStsMsgWaitListFullErrorCounter Counter,
            countryRepStsOtherErrorsCounter       Counter,
            countryRepStsTcapAbortedCounter       Counter,
            countryRepStsSccpAbortedCounter       Counter,
            countryRepStsFallbackToVersion2Counter Counter,
            countryRepStsFallbackToVersion1Counter Counter,
            countryRecvSriSmRespPassedCounter     Counter,
            countryRecvSriSmRespBlockedWithPermanentErrorCounter Counter,
            countryRecvSriSmRespBlockedWithTemporaryErrorCounter Counter,
            countryRecvSriSmRespBlockedWithNoResponseCounter Counter,
            countryRecvSriSmRespReleasedCounter   Counter,
            countryRecvSriSmPassedCounter         Counter,
            countryRecvSriSmBlockedWithPermanentErrorCounter Counter,
            countryRecvSriSmBlockedWithTemporaryErrorCounter Counter,
            countryRecvSriSmBlockedWithNoResponseCounter Counter,
            countryRecvSriSmReleasedCounter       Counter,
            countryRecvMtPassedCounter            Counter,
            countryRecvMtBlockedWithPermanentErrorCounter Counter,
            countryRecvMtBlockedWithTemporaryErrorCounter Counter,
            countryRecvMtBlockedWithNoResponseCounter Counter,
            countryRecvMtBlockedWithAckCounter    Counter,
            countryRecvMtReleasedCounter          Counter,
            countryRecvSriSmInvalidSccpSmscAddressCounter Counter,
            countryRecvSriSmInvalidMapSmscAddressCounter Counter,
            countryRecvSriSmInvalidRecipientAddressCounter Counter,
            countryRecvSriSmInvalidOriginatorAddressCounter Counter,
            countryRecvSriSmUnknownSccpSmscAddressCounter Counter,
            countryRecvSriSmUnknownMapSmscAddressCounter Counter,
            countryRecvSriSmConflictingSmscAddressCounter Counter,
            countryRecvSriSmMatchingMtRoutingRuleCounter Counter,
            countryRecvSriSmMatchingMtExtConditionRuleCounter Counter,
            countryRecvSriSmRespMatchingMtRoutingRuleCounter Counter,
            countryRecvSriSmRespMatchingMtExtConditionRuleCounter Counter,
            countryRecvMtInvalidSccpSmscAddressCounter Counter,
            countryRecvMtInvalidMapSmscAddressCounter Counter,
            countryRecvMtInvalidOriginatorAddressCounter Counter,
            countryRecvMtInvalidImsiCounter       Counter,
            countryRecvMtInvalidMscOrSgsnAddressCounter Counter,
            countryRecvMtUnknownSccpSmscAddressCounter Counter,
            countryRecvMtUnknownMapSmscAddressCounter Counter,
            countryRecvMtConflictingSmscAddressCounter Counter,
            countryRecvMtSpoofedSccpSmscAddressCounter Counter,
            countryRecvMtSpoofedMapSmscAddressCounter Counter,
            countryRecvMtWithoutPrecedingSriSmCounter Counter,
            countryRecvMtForgedMscOrSgsnAddressCounter Counter,
            countryRecvMtForgedImsiCounter        Counter,
            countryRecvMtForgedLmsiCounter        Counter,
            countryRecvMtMatchingMtRoutingRuleCounter Counter,
            countryRecvMtMatchingMtExtConditionRuleCounter Counter,
            countryRecvMtMatchingWhiteListedImsiCounter Counter,
            countryRecvMoSpoofedOriginatorAddressCounter Counter,
            countryRecvRogueTcapContinueCounter Counter,
            countryRecvRogueTcapEndCounter Counter,
            countryCdpaBasedMoForwardingTotalCounter Counter,
            countryCdpaBasedMoForwardingSuccessCounter Counter,
            countryCdpaBasedMoForwardingTimeoutCounter Counter,
            countryCdpaBasedMoForwardingSccpAbortCounter Counter,
            countryCdpaBasedMoForwardingTcapAbortCounter Counter,
            countryCdpaBasedMoForwardingUnknownResultCounter Counter,
            countryCdpaBasedMoForwardingSysFailErrorCounter Counter,
            countryCdpaBasedMoForwardingDataMisErrorCounter Counter,
            countryCdpaBasedMoForwardingUnexpDataValErrorCounter Counter,
            countryCdpaBasedMoForwardingFacNotSuppErrorCounter Counter,
            countryCdpaBasedMoForwardingUnkScErrorCounter Counter,
            countryCdpaBasedMoForwardingScCongErrorCounter Counter,
            countryCdpaBasedMoForwardingInvSmeAddrErrorCounter Counter,
            countryCdpaBasedMoForwardingSubNotScSubErrorCounter Counter,
            countryCdpaBasedMoForwardingOtherErrorsCounter Counter
        }

    countryIndex OBJECT-TYPE
        SYNTAX  CountryTableIndex
        ACCESS  read-write
        STATUS  mandatory
        DESCRIPTION
            "Index of entry in country table."
        ::= { countryEntry 1 }

    countryAdminState OBJECT-TYPE
        SYNTAX  AdminState
        ACCESS  read-write
        STATUS  mandatory
        DESCRIPTION
            "Administrative state of the country.

            Transition from 'inactive' state to 'active' state is only
            possible when:
            1) ISO3166 country code, E164 country code and mobile country code
               have been supplied;
            2) ISO3166 country code, E164 country code and mobile country code
               is not already in use by another country.

            Transition from 'active' state to 'inactive' state is only
            possible if:
            1) none of the 'active' rule records is referring to the country
               with a condition of type COUNTRY;
            2) all networks of the country are inactive.

            For details, refer to the comment on the AdminState type."
        ::= { countryEntry 2 }

    countryCountry OBJECT-TYPE
        SYNTAX  Country
        ACCESS  read-write
        STATUS  mandatory
        DESCRIPTION
            "Two letter code of country
            For details, refer to the comment on the Country type."
        ::= { countryEntry 3 }

    countryCountryCode OBJECT-TYPE
        SYNTAX  E164Address
        ACCESS  read-write
        STATUS  mandatory
        DESCRIPTION
            "E164 country code for the mobile network

            31 for the Netherlands
            32 for Belgium
            33 for France
            44 for United Kingdom
            49 for Germany

            Refer to http://www.lincmad.com/countrycodes.html for more country
            codes."
        ::= { countryEntry 4 }

    countryMobileCountryCode OBJECT-TYPE
        SYNTAX  MobileCountryCodes
        ACCESS  read-write
        STATUS  mandatory
        DESCRIPTION
            "Comma-seperated list with mobile country codes that are used for
            the country.

            For details, refer to comment on MobileCountryCodes type."
        ::= { countryEntry 5 }

    countryMoTotalCounter OBJECT-TYPE
        SYNTAX  Counter
        ACCESS  read-write
        STATUS  mandatory
        DESCRIPTION
            "Counter specifying the total number of times an MO/SM was
            received."
        ::= { countryEntry 11 }

    countryMoSuccessfulCounter OBJECT-TYPE
        SYNTAX  Counter
        ACCESS  read-write
        STATUS  mandatory
        DESCRIPTION
            "Counter specifying the number of times an MO/SM was successfully
             routed to its destination. The following events result in
             incrementing of this counter:
             - receiving a MO/SM matching a rule with action equal to
               discardWithAck
             - receiving an ACK from an application as result of an MO/SM
               being routed to the application
             - receiving an ACK from an SMSC as result of an MO/SM being
               routed to the SMSC."
        ::= { countryEntry 12 }

    countryMoTimeoutCounter OBJECT-TYPE
        SYNTAX  Counter
        ACCESS  read-write
        STATUS  mandatory
        DESCRIPTION
            "Counter specifying the number of times that routing an MO/SM to
            its destination resulted in a timeout. The following events
            result in incrementing of this counter:
             - not receiving a response from an application on an MO/SM
               being routed to the application within the maximum response

               time
             - receiving an ACK from an SMSC as result of an MO/SM being
               routed to an SMSC within the maximum response time."
        ::= { countryEntry 13 }

    countryMoDroppedCounter OBJECT-TYPE
        SYNTAX  Counter
        ACCESS  read-write
        STATUS  mandatory
        DESCRIPTION
            "Counter specifying the number of times that an MO/SM has not
            been routed to its destination due to decimation (this is only
            applicable when routing to an application)."
        ::= { countryEntry 14 }

    countryMoDiscardWithNakCounter OBJECT-TYPE
        SYNTAX  Counter
        ACCESS  read-write
        STATUS  mandatory
        DESCRIPTION
            "Counter specifying the number of times that TPR has rejected an
            MO/SM as result of a routing rule with action equal to
            discardWithNak or because none of the routing rules match."
        ::= { countryEntry 15 }

    countryMoRejectedByTprCounter OBJECT-TYPE
        SYNTAX  Counter
        ACCESS  read-write
        STATUS  mandatory
        DESCRIPTION
            "Counter specifying the number of times that TPR has rejected an
            MO/SM as result of incorrect syntax of the MO/SM."
        ::= { countryEntry 16 }

    countryMoRejectedByAppCounter OBJECT-TYPE
        SYNTAX  Counter
        ACCESS  read-write
        STATUS  mandatory
        DESCRIPTION
            "Counter specifying the number of times that routing to an
            application resulted in the application rejecting the MO/SM by
            sending a NAK."
        ::= { countryEntry 17 }

    countryMoUnknownResultCounter OBJECT-TYPE
        SYNTAX  Counter
        ACCESS  read-write
        STATUS  mandatory
        DESCRIPTION
            "Counter specifying the number of times that the result of routing
            an MO/SM to its destination could not be retrieved (this is only
            applicable when using optimal routing towards an SMSC)."
        ::= { countryEntry 18 }

    countryMoSysFailErrorCounter OBJECT-TYPE
        SYNTAX  Counter
        ACCESS  read-write
        STATUS  mandatory
        DESCRIPTION
            "Counter specifying the number of times that routing to an SMSC
            resulted in the SMSC rejecting the MO/SM with a System-Failure
            error on MAP level."
        ::= { countryEntry 19 }

    countryMoDataMisErrorCounter OBJECT-TYPE
        SYNTAX  Counter
        ACCESS  read-write
        STATUS  mandatory
        DESCRIPTION
            "Counter specifying the number of times that routing to an SMSC
            resulted in the SMSC rejecting the MO/SM with a Data-Missing
            error on MAP level."
        ::= { countryEntry 20 }

    countryMoUnexpDataValErrorCounter OBJECT-TYPE
        SYNTAX  Counter
        ACCESS  read-write
        STATUS  mandatory
        DESCRIPTION
            "Counter specifying the number of times that routing to an SMSC
            resulted in the SMSC rejecting the MO/SM with a Unexpected-Data-
            Value error on MAP level."
        ::= { countryEntry 21 }

    countryMoFacNotSuppErrorCounter OBJECT-TYPE
        SYNTAX  Counter
        ACCESS  read-write
        STATUS  mandatory
        DESCRIPTION
            "Counter specifying the number of times that routing to an SMSC
            resulted in the SMSC rejecting the MO/SM with a Facility-Not-
            Supported error on MAP level."
        ::= { countryEntry 22 }

    countryMoUnkScErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Unknown-
            Service-Centre."
        ::= { countryEntry 23 }

    countryMoScCongErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to SC-
            Congestion."
        ::= { countryEntry 24 }

    countryMoInvSmeAddrErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Invalid-
            SME-Address."
        ::= { countryEntry 25 }

    countryMoSubNotScSubErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to
            Subscriber-Not-SC-Subscriber."
        ::= { countryEntry 26 }

    countryMoOtherErrorsCounter OBJECT-TYPE
        SYNTAX  Counter
        ACCESS  read-write
        STATUS  mandatory
        DESCRIPTION
            "Counter specifying the number of times that routing to an SMSC
            resulted in the SMSC rejecting the MO/SM with another MAP error
            (or possibly a failure cause) than specified for the
            other MO counters."
        ::= { countryEntry 27 }

    countryMoTcapAbortedCounter OBJECT-TYPE
        SYNTAX  Counter
        ACCESS  read-write
        STATUS  mandatory
        DESCRIPTION
            "Counter specifying the number of times that routing to an SMSC
            resulted in the SMSC rejecting the MO/SM by sending a TC-ABORT
            on TCAP level."
        ::= { countryEntry 28 }

    countryMoSccpAbortedCounter OBJECT-TYPE
        SYNTAX  Counter
        ACCESS  read-write
        STATUS  mandatory
        DESCRIPTION
            "Counter specifying the number of times that routing to an SMSC
            resulted in the SMSC rejecting the MO/SM by sending a UDTS on
            SCCP level."
        ::= { countryEntry 29 }

    countryMtTotalCounter OBJECT-TYPE
        SYNTAX  Counter
        ACCESS  read-write
        STATUS  mandatory
        DESCRIPTION
            "Counter specifying the total number of times an MT/SM was issued
            by the TPR. This counter is incremented whenever:
            - the TPR issues a MT/SM on behalf of an application that is
              directly connected to the TPR
            - the TPR receives all MT/SM's from an SMSC and directs the MT/SM
              to its destination."
        ::= { countryEntry 30 }

    countryMtSuccessfulCounter OBJECT-TYPE
        SYNTAX  Counter
        ACCESS  read-write
        STATUS  mandatory
        DESCRIPTION
            "Counter specifying the number of times an MT/SM was successfully
            delivered."
        ::= { countryEntry 31 }

    countryMtTimeoutCounter OBJECT-TYPE
        SYNTAX  Counter
        ACCESS  read-write
        STATUS  mandatory
        DESCRIPTION
            "Counter specifying the number of times that delivering an MT/SM
            resulted in a timeout."
        ::= { countryEntry 32 }

    countryMtAbsSubErrorCounter OBJECT-TYPE
        SYNTAX  Counter
        ACCESS  read-write
        STATUS  mandatory
        DESCRIPTION
            "Counter specifying the number of times that delivering an MT/SM
            resulted in an Absent-Subscriber error."
        ::= { countryEntry 33 }

    countryMtSysFailErrorCounter OBJECT-TYPE
        SYNTAX  Counter
        ACCESS  read-write
        STATUS  mandatory
        DESCRIPTION
            "Counter specifying the number of times that delivering an MT/SM
            resulted in an System-Failure error."
        ::= { countryEntry 34 }

    countryMtDataMisErrorCounter OBJECT-TYPE
        SYNTAX  Counter
        ACCESS  read-write
        STATUS  mandatory
        DESCRIPTION
            "Counter specifying the number of times that delivering an MT/SM
            resulted in an Data-Missing error."
        ::= { countryEntry 35 }

    countryMtUnexpDataValErrorCounter OBJECT-TYPE
        SYNTAX  Counter
        ACCESS  read-write
        STATUS  mandatory
        DESCRIPTION
            "Counter specifying the number of times that delivering an MT/SM
            resulted in an Unexpected-Data-Value error."
        ::= { countryEntry 36 }

    countryMtFacNotSuppErrorCounter OBJECT-TYPE
        SYNTAX  Counter
        ACCESS  read-write
        STATUS  mandatory
        DESCRIPTION
            "Counter specifying the number of times that delivering an MT/SM
            resulted in an Facility-Not-Supported error."
        ::= { countryEntry 37 }

    countryMtUnidenSubErrorCounter OBJECT-TYPE
        SYNTAX  Counter
        ACCESS  read-write
        STATUS  mandatory
        DESCRIPTION
            "Counter specifying the number of times that delivering an MT/SM
            resulted in an Unidentified-Subscriber error."
        ::= { countryEntry 38 }

    countryMtIllSubErrorCounter OBJECT-TYPE
        SYNTAX  Counter
        ACCESS  read-write
        STATUS  mandatory
        DESCRIPTION
            "Counter specifying the number of times that delivering an MT/SM
            resulted in an Illegal-Subscriber error."
        ::= { countryEntry 39 }

    countryMtIllEquipErrorCounter OBJECT-TYPE
        SYNTAX  Counter
        ACCESS  read-write
        STATUS  mandatory
        DESCRIPTION
            "Counter specifying the number of times that delivering an MT/SM
            resulted in an Illegal-Equipment error."
        ::= { countryEntry 40 }

    countryMtSubBusyForMtSmErrorCounter OBJECT-TYPE
        SYNTAX  Counter
        ACCESS  read-write
        STATUS  mandatory
        DESCRIPTION
            "Counter specifying the number of times that delivering an MT/SM
            resulted in an Subscriber-Busy-For-MT-SMS error."
        ::= { countryEntry 41 }

    countryMtInvSmeAddrErrorCounter OBJECT-TYPE
        SYNTAX  Counter
        ACCESS  read-write
        STATUS  mandatory
        DESCRIPTION
            "Counter specifying the number of times that delivering an MT/SM
            resulted in a SM-Delivery-Failure error with failure cause equal
            to Invalid-SME-Address."
        ::= { countryEntry 42 }

    countryMtEquipProtErrorCounter OBJECT-TYPE
        SYNTAX  Counter
        ACCESS  read-write
        STATUS  mandatory
        DESCRIPTION
            "Counter specifying the number of times that delivering an MT/SM
            resulted in a SM-Delivery-Failure error with failure cause equal
            to Equipment-Protocol-Error."
        ::= { countryEntry 43 }

    countryMtEquipNotSmEquipErrorCounter OBJECT-TYPE
        SYNTAX  Counter
        ACCESS  read-write
        STATUS  mandatory
        DESCRIPTION
            "Counter specifying the number of times that delivering an MT/SM
            resulted in a SM-Delivery-Failure error with failure cause equal
            to Equipment-Not-SM-equipped."
        ::= { countryEntry 44 }

    countryMtMemCapExcErrorCounter OBJECT-TYPE
        SYNTAX  Counter
        ACCESS  read-write
        STATUS  mandatory
        DESCRIPTION
            "Counter specifying the number of times that delivering an MT/SM
            resulted in a SM-Delivery-Failure error with failure cause equal
            to Memory-Capacity-Exceeded."
        ::= { countryEntry 45 }

    countryMtOtherErrorsCounter OBJECT-TYPE
        SYNTAX  Counter
        ACCESS  read-write
        STATUS  mandatory
        DESCRIPTION
            "Counter specifying the number of times that delivering an MT/SM
            resulted in another MAP error (or possibly a failure cause) than
            specified for the other MT counters."
        ::= { countryEntry 46 }

    countryMtTcapAbortedCounter OBJECT-TYPE
        SYNTAX  Counter
        ACCESS  read-write
        STATUS  mandatory
        DESCRIPTION

            "Counter specifying the number of times that delivering an MT/SM
            resulted in the MSC/SGSN rejecting the MT/SM by sending a TC-ABORT
            on TCAP level."
        ::= { countryEntry 47 }

    countryMtSccpAbortedCounter OBJECT-TYPE

        SYNTAX  Counter
        ACCESS  read-write
        STATUS  mandatory
        DESCRIPTION
            "Counter specifying the number of times that delivering an MT/SM
            resulted in the MSC/SGSN rejecting the MT/SM by sending a UDTS on
            SCCP level."
        ::= { countryEntry 48 }

    countryMtFallbackToVersion2Counter OBJECT-TYPE
        SYNTAX  Counter
        ACCESS  read-write
        STATUS  mandatory
        DESCRIPTION
            "Counter specifying the number of times that delivering an MT/SM
            resulted in the MSC/SGSN requesting to fallback to MAP version 2."
        ::= { countryEntry 49 }

    countryMtFallbackToVersion1Counter OBJECT-TYPE
        SYNTAX  Counter
        ACCESS  read-write
        STATUS  mandatory
        DESCRIPTION
            "Counter specifying the number of times that delivering an MT/SM
            resulted in the MSC/SGSN requesting to fallback to MAP version 1."
        ::= { countryEntry 50 }

    countryMtAlternatePathUsedCounter OBJECT-TYPE
        SYNTAX  Counter
        ACCESS  read-write
        STATUS  mandatory
        DESCRIPTION
            "Counter specifying the number of times that for delivering an
            MT/SM both paths (through MSC and through SGSN) were available
            and that delivery on the primary path failed (and the alternate
            path was thus used)."
        ::= { countryEntry 51 }

    countryMtAlternatePathNotUsedCounter OBJECT-TYPE
        SYNTAX  Counter
        ACCESS  read-write
        STATUS  mandatory
        DESCRIPTION
            "Counter specifying the number of times that for delivering an
            MT/SM both paths (through MSC and through SGSN) were available
            and that delivery on the primary path succeeded (and the
            alternate path was thus not used)."
        ::= { countryEntry 52 }

    countrySriSmTotalCounter OBJECT-TYPE
        SYNTAX  Counter
        ACCESS  read-write
        STATUS  mandatory
        DESCRIPTION
            "Counter specifying the total number of times a Send-Routing-Info-
            For-SM operation was issued
            by the TPR. This counter is incremented whenever:
            - the TPR issues a Send-Routing-Info-For-SM operation as part of
              the delivery of a MT/SM that was sent by an application that is
              directly connected to the TPR
            - the TPR receives all Send-Routing-Info-For-SM operations from
              an SMSC and directs the opeation to its destination."
        ::= { countryEntry 53 }

    countrySriSmSuccessCounter OBJECT-TYPE
        SYNTAX  Counter
        ACCESS  read-write
        STATUS  mandatory
        DESCRIPTION
            "Counter specifying the number of times a Send-Routing-Info-For-
            SM operation was successfully issued."
        ::= { countryEntry 54 }

    countrySriSmTimeoutCounter OBJECT-TYPE
        SYNTAX  Counter
        ACCESS  read-write
        STATUS  mandatory
        DESCRIPTION
            "Counter specifying the number of times that issueing a
            Send-Routing- Info-For-SM operation resulted in a timeout."
        ::= { countryEntry 55 }

    countrySriSmSysFailErrorCounter OBJECT-TYPE
        SYNTAX  Counter
        ACCESS  read-write
        STATUS  mandatory
        DESCRIPTION
            "Counter specifying the number of times that issueing a
            Send-Routing- Info-For-SM operation resulted in a System-Failure
            error."
        ::= { countryEntry 56 }

    countrySriSmDataMisErrorCounter OBJECT-TYPE
        SYNTAX  Counter
        ACCESS  read-write
        STATUS  mandatory
        DESCRIPTION
            "Counter specifying the number of times that issueing a
            Send-Routing- Info-For-SM operation resulted in a Data-Missing
            error."
        ::= { countryEntry 57 }

    countrySriSmUnexpDataValErrorCounter OBJECT-TYPE
        SYNTAX  Counter
        ACCESS  read-write
        STATUS  mandatory
        DESCRIPTION
            "Counter specifying the number of times that issueing a
            Send-Routing- Info-For-SM operation resulted in a
            Unexpected-Data-Value error."
        ::= { countryEntry 58 }

    countrySriSmFacNotSuppErrorCounter OBJECT-TYPE
        SYNTAX  Counter
        ACCESS  read-write
        STATUS  mandatory
        DESCRIPTION
            "Counter specifying the number of times that issueing a
            Send-Routing- Info-For-SM operation resulted in a
            Facility-Not-Supported error."
        ::= { countryEntry 59 }

    countrySriSmUnkSubErrorCounter OBJECT-TYPE
        SYNTAX  Counter
        ACCESS  read-write
        STATUS  mandatory
        DESCRIPTION
            "Counter specifying the number of times that issueing a
            Send-Routing- Info-For-SM operation resulted in a
            Unknown-Subscriber error."
        ::= { countryEntry 60 }

    countrySriSmAbsSubErrorCounter OBJECT-TYPE
        SYNTAX  Counter
        ACCESS  read-write
        STATUS  mandatory
        DESCRIPTION
            "Counter specifying the number of times that issueing a
            Send-Routing- Info-For-SM operation resulted in a
            Absent-Subscriber error."
        ::= { countryEntry 61 }

    countrySriSmCallBarredErrorCounter OBJECT-TYPE
        SYNTAX  Counter
        ACCESS  read-write
        STATUS  mandatory
        DESCRIPTION
            "Counter specifying the number of times that issueing a
            Send-Routing- Info-For-SM operation resulted in a Call-Barred
            error."
        ::= { countryEntry 62 }

    countrySriSmTeleServNotProvErrorCounter OBJECT-TYPE
        SYNTAX  Counter
        ACCESS  read-write
        STATUS  mandatory
        DESCRIPTION
            "Counter specifying the number of times that issueing a
            Send-Routing- Info-For-SM operation resulted in a
            Teleservice-Not-Provisioned error."
        ::= { countryEntry 63 }

    countrySriSmOtherErrorsCounter OBJECT-TYPE
        SYNTAX  Counter
        ACCESS  read-write
        STATUS  mandatory
        DESCRIPTION
            "Counter specifying the number of times that issueing a
            Send-Routing- Info-For-SM operation resulted in another error
            than specified for the other Send-Routing-Info-For-SM counters."
        ::= { countryEntry 64 }

    countrySriSmTcapAbortedCounter OBJECT-TYPE
        SYNTAX  Counter
        ACCESS  read-write
        STATUS  mandatory
        DESCRIPTION
            "Counter specifying the number of times that issueing a
            Send-Routing- Info-For-SM operation resulted in the HLR rejecting
            the operation by sending a TC-ABORT on TCAP level."
        ::= { countryEntry 65 }

    countrySriSmSccpAbortedCounter OBJECT-TYPE
        SYNTAX  Counter
        ACCESS  read-write
        STATUS  mandatory
        DESCRIPTION
            "Counter specifying the number of times that issueing a
            Send-Routing- Info-For-SM operation resulted in the HLR rejecting
            the operation by sending a UDTS on SCCP level."
        ::= { countryEntry 66 }

    countrySriSmFallbackToVersion2Counter OBJECT-TYPE
        SYNTAX  Counter
        ACCESS  read-write
        STATUS  mandatory
        DESCRIPTION
            "Counter specifying the number of times that issueing a
            Send-Routing- Info-For-SM operation resulted in the HLR
            requesting to fallback to MAP version 2."
        ::= { countryEntry 67 }

    countrySriSmFallbackToVersion1Counter OBJECT-TYPE

        SYNTAX  Counter
        ACCESS  read-write
        STATUS  mandatory
        DESCRIPTION
            "Counter specifying the number of times that issueing a
            Send-Routing- Info-For-SM operation resulted in the HLR
            requesting to fallback to MAP version 1."
        ::= { countryEntry 68 }

    countryRepStsTotalCounter OBJECT-TYPE
        SYNTAX  Counter
        ACCESS  read-write
        STATUS  mandatory
        DESCRIPTION
            "Counter specifying the total number of times a Report-SM-
            Delivery-Status operation was issued
            by the TPR. This counter is incremented whenever:
            - the TPR issues a Report-SM-Delivery-Status operation as part of
              the delivery of a MT/SM that was sent by an application that is
              directly connected to the TPR
            - the TPR receives all Report-SM-Delivery-Status operations from
              an SMSC and directs the opeation to its destination."
        ::= { countryEntry 69 }

    countryRepStsSuccessCounter OBJECT-TYPE
        SYNTAX  Counter
        ACCESS  read-write
        STATUS  mandatory
        DESCRIPTION
            "Counter specifying the number of times a Report-SM-Delivery-
            Status operation was successfully issued."
        ::= { countryEntry 70 }

    countryRepStsTimeoutCounter OBJECT-TYPE
        SYNTAX  Counter
        ACCESS  read-write
        STATUS  mandatory
        DESCRIPTION
            "Counter specifying the number of times that issueing a Report-SM-
            Delivery-Status operation resulted in a timeout."
        ::= { countryEntry 71 }

    countryRepStsSysFailErrorCounter OBJECT-TYPE
        SYNTAX  Counter
        ACCESS  read-write
        STATUS  mandatory
        DESCRIPTION
            "Counter specifying the number of times that issueing a Report-SM-
            Delivery-Status operation resulted in a System-Failure error."
        ::= { countryEntry 72 }

    countryRepStsDataMisErrorCounter OBJECT-TYPE
        SYNTAX  Counter
        ACCESS  read-write
        STATUS  mandatory
        DESCRIPTION
            "Counter specifying the number of times that issueing a Report-SM-
            Delivery-Status operation resulted in a Data-Missing error."
        ::= { countryEntry 73 }

    countryRepStsUnexpDataValErrorCounter OBJECT-TYPE
        SYNTAX  Counter
        ACCESS  read-write
        STATUS  mandatory
        DESCRIPTION
            "Counter specifying the number of times that issueing a Report-SM-
            Delivery-Status operation resulted in a Unexpected-Data-Value
            error."
        ::= { countryEntry 74 }


    countryRepStsUnkSubErrorCounter OBJECT-TYPE
        SYNTAX  Counter
        ACCESS  read-write
        STATUS  mandatory

        DESCRIPTION
           "Counter specifying the number of times that issueing a Report-SM-
            Delivery-Status operation resulted in a Unknown-Subscriber
            error."
        ::= { countryEntry 75 }

    countryRepStsMsgWaitListFullErrorCounter OBJECT-TYPE
        SYNTAX  Counter
        ACCESS  read-write
        STATUS  mandatory
        DESCRIPTION
           "Counter specifying the number of times that issueing a Report-SM-
            Delivery-Status operation resulted in a Message-Waiting-List-Full
            error."
        ::= { countryEntry 76 }

    countryRepStsOtherErrorsCounter OBJECT-TYPE
        SYNTAX  Counter
        ACCESS  read-write
        STATUS  mandatory
        DESCRIPTION
            "Counter specifying the number of times that issueing a
            Report-SM- Delivery-Status operation resulted in in another error
            than specified for the other Report-SM-Delivery-Status counters."
        ::= { countryEntry 77 }

    countryRepStsTcapAbortedCounter OBJECT-TYPE
        SYNTAX  Counter
        ACCESS  read-write
        STATUS  mandatory
        DESCRIPTION
            "Counter specifying the number of times that issueing a Report-SM-
            Delivery-Status operation resulted in the HLR rejecting the
            operation by sending a TC-ABORT on TCAP level."
        ::= { countryEntry 78 }

    countryRepStsSccpAbortedCounter OBJECT-TYPE
        SYNTAX  Counter
        ACCESS  read-write
        STATUS  mandatory
        DESCRIPTION
            "Counter specifying the number of times that issueing a Report-SM-
            Delivery-Status operation resulted in the HLR rejecting the
            operation by sending a UDTS on SCCP level."
        ::= { countryEntry 79 }

    countryRepStsFallbackToVersion2Counter OBJECT-TYPE
        SYNTAX  Counter
        ACCESS  read-write
        STATUS  mandatory
        DESCRIPTION
            "Counter specifying the number of times that issueing a Report-SM-
            Delivery-Status operation resulted in the HLR requesting to
            fallback to MAP version 2."
        ::= { countryEntry 80 }

    countryRepStsFallbackToVersion1Counter OBJECT-TYPE
        SYNTAX  Counter
        ACCESS  read-write
        STATUS  mandatory
        DESCRIPTION
            "Counter specifying the number of times that issueing a Report-SM-
            Delivery-Status operation resulted in the HLR requesting to
            fallback to MAP version 1."
        ::= { countryEntry 81 }

    countryRecvSriSmRespPassedCounter OBJECT-TYPE
        SYNTAX  Counter
        ACCESS  read-write
        STATUS  mandatory
        DESCRIPTION
            "Counter specifying the number of times that TextPass received an
             response for an inbound Send-Routing-Info-For-SM operation and 
             relayed it to the invoking SMSC."
        ::= { countryEntry 91 }

    countryRecvSriSmRespBlockedWithPermanentErrorCounter OBJECT-TYPE
        SYNTAX  Counter
        ACCESS  read-write
        STATUS  mandatory
        DESCRIPTION
            "Counter specifying the number of times that TextPass rejected a
             response to an inbound Send-Routing-Info-For-SM operation and 
             returned a permanent error to the invoking SMSC."
        ::= { countryEntry 92 }

    countryRecvSriSmRespBlockedWithTemporaryErrorCounter OBJECT-TYPE
        SYNTAX  Counter
        ACCESS  read-write
        STATUS  mandatory
        DESCRIPTION
            "Counter specifying the number of times that TextPass rejected a 
             response to an inbound Send-Routing-Info-For-SM operation and 
             returned a temporary error to the invoking SMSC."
        ::= { countryEntry 93 }

    countryRecvSriSmRespBlockedWithNoResponseCounter OBJECT-TYPE
        SYNTAX  Counter
        ACCESS  read-write
        STATUS  mandatory
        DESCRIPTION
            "Counter specifying the number of times that TextPass rejected a
             response to an inbound Send-Routing-Info-For-SM operation and 
             did not return anything to the invoking SMSC."
        ::= { countryEntry 94 }

    countryRecvSriSmRespReleasedCounter OBJECT-TYPE
        SYNTAX  Counter
        ACCESS  read-write
        STATUS  mandatory
        DESCRIPTION
            "Counter specifying the number of times that TextPass released a
             response to an inbound Send-Routing-Info-For-SM operation."
        ::= { countryEntry 96 }

    countryRecvSriSmPassedCounter OBJECT-TYPE
        SYNTAX  Counter
        ACCESS  read-write
        STATUS  mandatory
        DESCRIPTION
            "Counter specifying the number of times that TextPass accepted an
             inbound Send-Routing-Info-For-SM operation and relayed it to an
             HLR on behalf of the invoking SMSC."
        ::= { countryEntry 101 }

    countryRecvSriSmBlockedWithPermanentErrorCounter OBJECT-TYPE
        SYNTAX  Counter
        ACCESS  read-write
        STATUS  mandatory
        DESCRIPTION
            "Counter specifying the number of times that TextPass rejected an
            inbound Send-Routing-Info-For-SM operation and returned a
            permanent error to the invoking SMSC."
        ::= { countryEntry 102 }

    countryRecvSriSmBlockedWithTemporaryErrorCounter OBJECT-TYPE
        SYNTAX  Counter
        ACCESS  read-write
        STATUS  mandatory
        DESCRIPTION
            "Counter specifying the number of times that TextPass rejected an
            inbound Send-Routing-Info-For-SM operation and returned a
            temporary error to the invoking SMSC."
        ::= { countryEntry 103 }

    countryRecvSriSmBlockedWithNoResponseCounter OBJECT-TYPE
        SYNTAX  Counter
        ACCESS  read-write
        STATUS  mandatory
        DESCRIPTION
            "Counter specifying the number of times that TextPass rejected an
             inbound Send-Routing-Info-For-SM operation and did not return
             anything to the invoking SMSC."
        ::= { countryEntry 104 }

    countryRecvSriSmReleasedCounter OBJECT-TYPE
        SYNTAX  Counter
        ACCESS  read-write
        STATUS  mandatory
        DESCRIPTION
            "Counter specifying the number of times that TextPass released
             an inbound Send-Routing-Info-For-SM operation."
        ::= { countryEntry 106 }

    countryRecvMtPassedCounter OBJECT-TYPE
        SYNTAX  Counter
        ACCESS  read-write
        STATUS  mandatory
        DESCRIPTION
            "Counter specifying the number of times that TextPass accepted an
             inbound MT-Forward-SM operation and relayed it to an MSC/SGSN on
             behalf of the invoking SMSC."
        ::= { countryEntry 111 }

    countryRecvMtBlockedWithPermanentErrorCounter OBJECT-TYPE
        SYNTAX  Counter
        ACCESS  read-write
        STATUS  mandatory
        DESCRIPTION
            "Counter specifying the number of times that TextPass rejected an
             inbound MT-Forward-SM operation and returned a permanent error to
             the invoking SMSC."
        ::= { countryEntry 112 }

    countryRecvMtBlockedWithTemporaryErrorCounter OBJECT-TYPE
        SYNTAX  Counter
        ACCESS  read-write
        STATUS  mandatory
        DESCRIPTION
            "Counter specifying the number of times that TextPass rejected an
             inbound MT-Forward-SM operation and returned a temporary error to
             the invoking SMSC."
        ::= { countryEntry 113 }

    countryRecvMtBlockedWithNoResponseCounter OBJECT-TYPE
        SYNTAX  Counter
        ACCESS  read-write
        STATUS  mandatory
        DESCRIPTION
            "Counter specifying the number of times that TextPass rejected an
            inbound MT-Forward-SM operation and did not return anything to
            the invoking SMSC."
        ::= { countryEntry 114 }

    countryRecvMtBlockedWithAckCounter OBJECT-TYPE
        SYNTAX  Counter
        ACCESS  read-write
        STATUS  mandatory
        DESCRIPTION
            "Counter specifying the number of times that TextPass rejected an
             inbound MT-Forward-SM operation, but did a positive response to
             the invoking SMSC."
        ::= { countryEntry 115 }

    countryRecvMtReleasedCounter OBJECT-TYPE
        SYNTAX  Counter
        ACCESS  read-write
        STATUS  mandatory
        DESCRIPTION
            "Counter specifying the number of times that TextPass released
             an inbound MT-Forward-For-SM operation."
        ::= { countryEntry 116 }

    countryRecvSriSmInvalidSccpSmscAddressCounter OBJECT-TYPE
        SYNTAX  Counter
        ACCESS  read-write
        STATUS  mandatory
        DESCRIPTION
            "Counter specifying the number of times that TextPass rejected an
             inbound Send-Routing-Info-For-SM operation due to an invalid SMSC
             address at SCCP layer."
        ::= { countryEntry 121 }


    countryRecvSriSmInvalidMapSmscAddressCounter OBJECT-TYPE
        SYNTAX  Counter
        ACCESS  read-write
        STATUS  mandatory
        DESCRIPTION
            "Counter specifying the number of times that TextPass rejected an
             inbound Send-Routing-Info-For-SM operation due to an invalid SMSC
             address at MAP layer."
        ::= { countryEntry 122 }

    countryRecvSriSmInvalidRecipientAddressCounter OBJECT-TYPE
        SYNTAX  Counter
        ACCESS  read-write
        STATUS  mandatory
        DESCRIPTION
            "Counter specifying the number of times that TextPass rejected an
             inbound Send-Routing-Info-For-SM operation due to an invalid
             recipient address."
        ::= { countryEntry 123 }

    countryRecvSriSmInvalidOriginatorAddressCounter OBJECT-TYPE
        SYNTAX  Counter
        ACCESS  read-write
        STATUS  mandatory
        DESCRIPTION
            "Counter specifying the number of times that TextPass rejected an
             inbound Send-Routing-Info-For-SM operation due to an invalid
             originator address."
        ::= { countryEntry 124 }

    countryRecvSriSmUnknownSccpSmscAddressCounter OBJECT-TYPE
        SYNTAX  Counter
        ACCESS  read-write
        STATUS  mandatory
        DESCRIPTION
            "Counter specifying the number of times that TextPass rejected an
            inbound Send-Routing-Info-For-SM operation due to an SMSC address
            at SCCP layer that could not be associated with any of the
            defined mobile network entities."
        ::= { countryEntry 125 }

    countryRecvSriSmUnknownMapSmscAddressCounter OBJECT-TYPE
        SYNTAX  Counter
        ACCESS  read-write
        STATUS  mandatory
        DESCRIPTION
            "Counter specifying the number of times that TextPass rejected an
             inbound Send-Routing-Info-For-SM operation due to an SMSC address
             at MAP layer that could not be associated with any of the defined
             mobile network entities."
        ::= { countryEntry 126 }

    countryRecvSriSmConflictingSmscAddressCounter OBJECT-TYPE
        SYNTAX  Counter
        ACCESS  read-write
        STATUS  mandatory
        DESCRIPTION
            "Counter specifying the number of times that TextPass rejected an
            inbound Send-Routing-Info-For-SM operation due to conflicting
            SMSC addresses at SCCP layer and MAP layer. These addresses
            conflict when they are from:
             - different countries (determined on the basis of the country
               code)
             - different mobile networks (determined by associating the
               addresses with a mobile network)."
        ::= { countryEntry 127 }

    countryRecvSriSmMatchingMtRoutingRuleCounter OBJECT-TYPE
        SYNTAX  Counter
        ACCESS  read-write
        STATUS  mandatory
        DESCRIPTION
            "Counter specifying the number of times that TextPass rejected an
             inbound Send-Routing-Info-For-SM operation due to a matching MT
             routing rule."
        ::= { countryEntry 128 }

    countryRecvSriSmMatchingMtExtConditionRuleCounter OBJECT-TYPE
        SYNTAX  Counter
        ACCESS  read-write
        STATUS  mandatory
        DESCRIPTION
            "Counter specifying the number of times that TextPass rejected an
             inbound Send-Routing-Info-For-SM operation due to a matching MT
             external condition rule."
        ::= { countryEntry 129 }

    countryRecvSriSmRespMatchingMtRoutingRuleCounter OBJECT-TYPE
        SYNTAX  Counter
        ACCESS  read-write
        STATUS  mandatory
        DESCRIPTION
            "Counter specifying the number of times that TextPass rejected an
             inbound Send-Routing-Info-For-SM operation due to a matching MT
             routing rule."
        ::= { countryEntry 130 }

    countryRecvSriSmRespMatchingMtExtConditionRuleCounter OBJECT-TYPE
        SYNTAX  Counter
        ACCESS  read-write
        STATUS  mandatory
        DESCRIPTION
            "Counter specifying the number of times that TextPass rejected an
             inbound Send-Routing-Info-For-SM operation due to a matching MT
             external condition rule."
        ::= { countryEntry 131 }

    countryRecvMtInvalidSccpSmscAddressCounter OBJECT-TYPE
        SYNTAX  Counter
        ACCESS  read-write
        STATUS  mandatory
        DESCRIPTION
            "Counter specifying the number of times that TextPass rejected an
             inbound MT-Forward-SM operation due to an invalid SMSC address at
             SCCP layer."
        ::= { countryEntry 141 }

    countryRecvMtInvalidMapSmscAddressCounter OBJECT-TYPE
        SYNTAX  Counter
        ACCESS  read-write
        STATUS  mandatory
        DESCRIPTION
            "Counter specifying the number of times that TextPass rejected an
             inbound MT-Forward-SM operation due to an invalid SMSC address at
             MAP layer."
        ::= { countryEntry 142 }

    countryRecvMtInvalidOriginatorAddressCounter OBJECT-TYPE
        SYNTAX  Counter
        ACCESS  read-write
        STATUS  mandatory
        DESCRIPTION
            "Counter specifying the number of times that TextPass rejected an
             inbound MT-Forward-SM operation due to an invalid originator
             address."
        ::= { countryEntry 143 }

    countryRecvMtInvalidImsiCounter OBJECT-TYPE
        SYNTAX  Counter
        ACCESS  read-write
        STATUS  mandatory
        DESCRIPTION
            "Counter specifying the number of times that TextPass rejected an
             inbound MT-Forward-SM operation due to an invalid IMSI."
        ::= { countryEntry 144 }

    countryRecvMtInvalidMscOrSgsnAddressCounter OBJECT-TYPE
        SYNTAX  Counter
        ACCESS  read-write
        STATUS  mandatory
        DESCRIPTION
            "Counter specifying the number of times that TextPass rejected an
             inbound MT-Forward-SM operation due to an invalid MSC address or
             SGSN address."
        ::= { countryEntry 145 }

    countryRecvMtUnknownSccpSmscAddressCounter OBJECT-TYPE
        SYNTAX  Counter
        ACCESS  read-write
        STATUS  mandatory
        DESCRIPTION
            "Counter specifying the number of times that TextPass rejected an
             inbound MT-Forward-SM operation due to an SMSC address at SCCP
             layer that could not be associated with any of the defined mobile
             network entities."
        ::= { countryEntry 146 }

    countryRecvMtUnknownMapSmscAddressCounter OBJECT-TYPE
        SYNTAX  Counter
        ACCESS  read-write
        STATUS  mandatory
        DESCRIPTION
            "Counter specifying the number of times that TextPass rejected an
             inbound MT-Forward-SM operation due to an SMSC address at MAP
             layer that could not be associated with any of the defined mobile
             network entities."
        ::= { countryEntry 147 }

    countryRecvMtConflictingSmscAddressCounter OBJECT-TYPE
        SYNTAX  Counter
        ACCESS  read-write
        STATUS  mandatory
        DESCRIPTION
            "Counter specifying the number of times that TextPass rejected an
             inbound MT-Forward-SM operation due to:
             - conflicting SMSC addresses at SCCP layer and MAP layer
             - different SMSC addresses at SCCP layer used amongst the various
               TCAP messages of a segmented TCAP dialogue
             SMSC addresses at SCCP layer and MAP layer conflict when they are
             from:
               - different countries (determined on the basis of the country
                 code), or
               - different mobile networks (determined by associating the
                 addresses with a mobile network)."
        ::= { countryEntry 148 }

    countryRecvMtSpoofedSccpSmscAddressCounter OBJECT-TYPE
        SYNTAX  Counter
        ACCESS  read-write
        STATUS  mandatory
        DESCRIPTION
            "Counter specifying the number of times that TextPass rejected an
            inbound MT-Forward-SM operation due to spoofing of the SMSC
            address at SCCP level, i.e. using an SMSC address at SCCP level
            for MT-Forward-SM that conflicts with address used in relating
            Send- Routing-Info-For-SM operation. A conflict exist when the
            addresses are from:
               - different countries (determined on the basis of the country
                 code), or
               - different mobile networks (determined by associating the
                 addresses with a mobile network)."
        ::= { countryEntry 149 }

    countryRecvMtSpoofedMapSmscAddressCounter OBJECT-TYPE
        SYNTAX  Counter
        ACCESS  read-write
        STATUS  mandatory
        DESCRIPTION
            "Counter specifying the number of times that TextPass rejected an
            inbound MT-Forward-SM operation due to spoofing of the SMSC
            address at MAP level, i.e. using an SMSC address at MAP level for
            MT-Forward-SM that conflicts with address used in relating Send-
            Routing-Info-For-SM operation. A conflict exist when the
            addresses are from:
               - different countries (determined on the basis of the country
                 code), or
               - different mobile networks (determined by associating the
                 addresses with a mobile network)."
        ::= { countryEntry 150 }

    countryRecvMtWithoutPrecedingSriSmCounter OBJECT-TYPE
        SYNTAX  Counter
        ACCESS  read-write
        STATUS  mandatory
        DESCRIPTION
            "Counter specifying the number of times that TextPass rejected an
             inbound MT-Forward-SM operation pertaining to a subscriber of the
             operator's network that could not be related with a previously
             received Send-Routing-Info-For-SM operation."
        ::= { countryEntry 151 }

    countryRecvMtForgedMscOrSgsnAddressCounter OBJECT-TYPE
        SYNTAX  Counter
        ACCESS  read-write
        STATUS  mandatory
        DESCRIPTION
            "Counter specifying the number of times that TextPass rejected an
             inbound MT-Forward-SM operation due to a forged MSC address or
             SGSN address."
        ::= { countryEntry 152 }

    countryRecvMtForgedImsiCounter OBJECT-TYPE
        SYNTAX  Counter
        ACCESS  read-write
        STATUS  mandatory
        DESCRIPTION
            "Counter specifying the number of times that TextPass rejected an
             inbound MT-Forward-SM operation due to a forged IMSI."
        ::= { countryEntry 153 }

    countryRecvMtForgedLmsiCounter OBJECT-TYPE
        SYNTAX  Counter
        ACCESS  read-write
        STATUS  mandatory
        DESCRIPTION
            "Counter specifying the number of times that TextPass rejected an
             inbound MT-Forward-SM operation due to a forged LMSI."
        ::= { countryEntry 154 }

    countryRecvMtMatchingMtRoutingRuleCounter OBJECT-TYPE
        SYNTAX  Counter
        ACCESS  read-write
        STATUS  mandatory
        DESCRIPTION
            "Counter specifying the number of times that TextPass rejected an
            inbound MT-Forward-SM operation due to a matching MT routing
            rule."
        ::= { countryEntry 155 }

    countryRecvMtMatchingMtExtConditionRuleCounter OBJECT-TYPE
        SYNTAX  Counter
        ACCESS  read-write
        STATUS  mandatory
        DESCRIPTION
            "Counter specifying the number of times that TextPass rejected an
             inbound MT-Forward-SM  operation due to a matching MT external
             condition rule."
        ::= { countryEntry 156 }

    countryRecvMtMatchingWhiteListedImsiCounter OBJECT-TYPE
        SYNTAX  Counter
        ACCESS  read-write
        STATUS  mandatory
        DESCRIPTION
            "Counter specifying the number of times that TextPass received an
             inbound MT-Forward-SM  operation that matches a whitelisted
             prefix from fwPropNoSpoofCheckWhiteListedRecipientImsi."
        ::= { countryEntry 157 }

    countryRecvMoSpoofedOriginatorAddressCounter OBJECT-TYPE
        SYNTAX  Counter
        ACCESS  read-write
        STATUS  mandatory
        DESCRIPTION
            "Counter specifying the number of times that TextPass rejected an
             inbound MO-Forward-SM operation due to due to spoofing of the
             originator address."
        ::= { countryEntry 191 }

    countryRecvRogueTcapContinueCounter OBJECT-TYPE
        SYNTAX  Counter
        ACCESS  read-write
        STATUS  mandatory
        DESCRIPTION
            "Counter specifying the number of times that TextPass received an
             TCAP Continue message that had no corresponding previous dialog
             and contained components other than Invoke."
        ::= { countryEntry 192 }

    countryRecvRogueTcapEndCounter OBJECT-TYPE
        SYNTAX  Counter
        ACCESS  read-write
        STATUS  mandatory
        DESCRIPTION
            "Counter specifying the number of times that TextPass received an
             TCAP End message that had no corresponding previous dialog."
        ::= { countryEntry 193 }

    countryCdpaBasedMoForwardingTotalCounter OBJECT-TYPE
        SYNTAX  Counter
        ACCESS  read-write
        STATUS  mandatory
        DESCRIPTION
            "Counter specifying the number of times a cdpa-based
            MO forwarding attempt was made."
        ::= { countryEntry 201 }

    countryCdpaBasedMoForwardingSuccessCounter OBJECT-TYPE
        SYNTAX  Counter
        ACCESS  read-write
        STATUS  mandatory
        DESCRIPTION
            "Counter specifying the number of times a cdpa-based
            MO forwarding attempt was successful."
        ::= { countryEntry 202 }

    countryCdpaBasedMoForwardingTimeoutCounter OBJECT-TYPE
        SYNTAX  Counter
        ACCESS  read-write
        STATUS  mandatory
        DESCRIPTION
            "Counter specifying the number of times a cdpa-based
            MO forwarding attempt timed out."
        ::= { countryEntry 203 }

    countryCdpaBasedMoForwardingSccpAbortCounter OBJECT-TYPE
        SYNTAX  Counter
        ACCESS  read-write
        STATUS  mandatory
        DESCRIPTION
            "Counter specifying the number of times a cdpa-based
            MO forwarding attempt resulted in an SCCP abort."
        ::= { countryEntry 204 }

    countryCdpaBasedMoForwardingTcapAbortCounter OBJECT-TYPE
        SYNTAX  Counter
        ACCESS  read-write
        STATUS  mandatory
        DESCRIPTION
            "Counter specifying the number of times a cdpa-based
            MO forwarding attempt resulted in a TCAP abort."
        ::= { countryEntry 205 }

    countryCdpaBasedMoForwardingUnknownResultCounter OBJECT-TYPE
        SYNTAX  Counter
        ACCESS  read-write
        STATUS  mandatory
        DESCRIPTION
            "Counter specifying the number of times a cdpa-based
            MO forwarding attempt was made using transparent routing,
            in which case the forwarding result is unknown."
        ::= { countryEntry 206 }

    countryCdpaBasedMoForwardingSysFailErrorCounter OBJECT-TYPE
        SYNTAX  Counter
        ACCESS  read-write
        STATUS  mandatory
        DESCRIPTION
            "Counter specifying the number of times a cdpa-based
            MO forwarding attempt resulted in the SMSC returning a
            systemFailure error."
        ::= { countryEntry 207 }

    countryCdpaBasedMoForwardingDataMisErrorCounter OBJECT-TYPE
        SYNTAX  Counter
        ACCESS  read-write
        STATUS  mandatory
        DESCRIPTION
            "Counter specifying the number of times a cdpa-based
            MO forwarding attempt resulted in the SMSC returning a
            dataMissing error."
        ::= { countryEntry 208 }

    countryCdpaBasedMoForwardingUnexpDataValErrorCounter OBJECT-TYPE
        SYNTAX  Counter
        ACCESS  read-write
        STATUS  mandatory
        DESCRIPTION
            "Counter specifying the number of times a cdpa-based
            MO forwarding attempt resulted in the SMSC returning a
            unexpectedDataValue error."
        ::= { countryEntry 209 }

    countryCdpaBasedMoForwardingFacNotSuppErrorCounter OBJECT-TYPE
        SYNTAX  Counter
        ACCESS  read-write
        STATUS  mandatory
        DESCRIPTION
            "Counter specifying the number of times a cdpa-based
            MO forwarding attempt resulted in the SMSC returning a
            facilityNotSupported error."
        ::= { countryEntry 210 }

    countryCdpaBasedMoForwardingUnkScErrorCounter OBJECT-TYPE
        SYNTAX  Counter
        ACCESS  read-write
        STATUS  mandatory
        DESCRIPTION
            "Counter specifying the number of times a cdpa-based
            MO forwarding attempt resulted in the SMSC returning a
            unknownServiceCentre error."
        ::= { countryEntry 211 }

    countryCdpaBasedMoForwardingScCongErrorCounter OBJECT-TYPE
        SYNTAX  Counter
        ACCESS  read-write
        STATUS  mandatory
        DESCRIPTION
            "Counter specifying the number of times a cdpa-based
            MO forwarding attempt resulted in the SMSC returning a
            serviceCentreCongested error."
        ::= { countryEntry 212 }

    countryCdpaBasedMoForwardingInvSmeAddrErrorCounter OBJECT-TYPE
        SYNTAX  Counter
        ACCESS  read-write
        STATUS  mandatory
        DESCRIPTION
            "Counter specifying the number of times a cdpa-based
            MO forwarding attempt resulted in the SMSC returning a
            invalidSmeAddress error."
        ::= { countryEntry 213 }

    countryCdpaBasedMoForwardingSubNotScSubErrorCounter OBJECT-TYPE
        SYNTAX  Counter
        ACCESS  read-write
        STATUS  mandatory
        DESCRIPTION
            "Counter specifying the number of times a cdpa-based
            MO forwarding attempt resulted in the SMSC returning a
            subscriberNotScSubscriber error."
        ::= { countryEntry 214 }

    countryCdpaBasedMoForwardingOtherErrorsCounter OBJECT-TYPE
        SYNTAX  Counter
        ACCESS  read-write
        STATUS  mandatory
        DESCRIPTION
            "Counter specifying the number of times a cdpa-based
            MO forwarding attempt resulted in an error other than the
            errors specified above."
        ::= { countryEntry 215 }


    mobNetworkTable OBJECT-TYPE
        SYNTAX  SEQUENCE OF MobNetworkEntry
        ACCESS  not-accessible
        STATUS  mandatory
        DESCRIPTION
            "A table defining the properties of each mobile network."
        ::= { sms 32 }

    mobNetworkEntry OBJECT-TYPE
        SYNTAX  MobNetworkEntry
        ACCESS  not-accessible
        STATUS  mandatory
        DESCRIPTION
            "Table entry defining a single mobile network."
        INDEX   { mobNetworkIndex }
        ::= { mobNetworkTable 1 }

    MobNetworkEntry ::=
        SEQUENCE {
            mobNetworkIndex                       MobNetworkTableIndex,
            mobNetworkAdminState                  AdminState,
            mobNetworkCountry                     Country,
            mobNetworkOperator                    NameString,
            mobNetworkMobileNetworkCode           MobileNetworkCodes,
            mobNetworkMapPhase                    MapPhase,
            mobNetworkTtForPrimarySriSm           TranslationType,
            mobNetworkEnableFallbackSriSm         Boolean,
            mobNetworkTtForFallbackSriSm          TranslationType,
            mobNetworkMnpPrefix                   HexAddressString,
            mobNetworkMoTotalCounter              Counter,
            mobNetworkMoSuccessfulCounter         Counter,
            mobNetworkMoTimeoutCounter            Counter,
            mobNetworkMoDroppedCounter            Counter,
            mobNetworkMoDiscardWithNakCounter     Counter,
            mobNetworkMoRejectedByTprCounter      Counter,
            mobNetworkMoRejectedByAppCounter      Counter,
            mobNetworkMoUnknownResultCounter      Counter,
            mobNetworkMoSysFailErrorCounter       Counter,
            mobNetworkMoDataMisErrorCounter       Counter,
            mobNetworkMoUnexpDataValErrorCounter  Counter,
            mobNetworkMoFacNotSuppErrorCounter    Counter,
            mobNetworkMoUnkScErrorCounter         Counter,
            mobNetworkMoScCongErrorCounter        Counter,
            mobNetworkMoInvSmeAddrErrorCounter    Counter,
            mobNetworkMoSubNotScSubErrorCounter   Counter,
            mobNetworkMoOtherErrorsCounter        Counter,
            mobNetworkMoTcapAbortedCounter        Counter,
            mobNetworkMoSccpAbortedCounter        Counter,            
            mobNetworkMtTotalCounter              Counter,
            mobNetworkMtSuccessfulCounter         Counter,
            mobNetworkMtTimeoutCounter            Counter,
            mobNetworkMtAbsSubErrorCounter        Counter,
            mobNetworkMtSysFailErrorCounter       Counter,
            mobNetworkMtDataMisErrorCounter       Counter,
            mobNetworkMtUnexpDataValErrorCounter  Counter,
            mobNetworkMtFacNotSuppErrorCounter    Counter,
            mobNetworkMtUnidenSubErrorCounter     Counter,
            mobNetworkMtIllSubErrorCounter        Counter,
            mobNetworkMtIllEquipErrorCounter      Counter,
            mobNetworkMtSubBusyForMtSmErrorCounter Counter,
            mobNetworkMtInvSmeAddrErrorCounter    Counter,
            mobNetworkMtEquipProtErrorCounter     Counter,
            mobNetworkMtEquipNotSmEquipErrorCounter Counter,
            mobNetworkMtMemCapExcErrorCounter     Counter,
            mobNetworkMtOtherErrorsCounter        Counter,
            mobNetworkMtTcapAbortedCounter        Counter,
            mobNetworkMtSccpAbortedCounter        Counter,
            mobNetworkMtFallbackToVersion2Counter Counter,
            mobNetworkMtFallbackToVersion1Counter Counter,
            mobNetworkMtAlternatePathUsedCounter  Counter,
            mobNetworkMtAlternatePathNotUsedCounter Counter,
            mobNetworkSriSmTotalCounter           Counter,
            mobNetworkSriSmSuccessCounter         Counter,
            mobNetworkSriSmTimeoutCounter         Counter,
            mobNetworkSriSmSysFailErrorCounter    Counter,
            mobNetworkSriSmDataMisErrorCounter    Counter,
            mobNetworkSriSmUnexpDataValErrorCounter Counter,
            mobNetworkSriSmFacNotSuppErrorCounter Counter,
            mobNetworkSriSmUnkSubErrorCounter     Counter,
            mobNetworkSriSmAbsSubErrorCounter     Counter,
            mobNetworkSriSmCallBarredErrorCounter Counter,
            mobNetworkSriSmTeleServNotProvErrorCounter Counter,
            mobNetworkSriSmOtherErrorsCounter     Counter,
            mobNetworkSriSmTcapAbortedCounter     Counter,
            mobNetworkSriSmSccpAbortedCounter     Counter,
            mobNetworkSriSmFallbackToVersion2Counter Counter,
            mobNetworkSriSmFallbackToVersion1Counter Counter,
            mobNetworkRepStsTotalCounter          Counter,
            mobNetworkRepStsSuccessCounter        Counter,
            mobNetworkRepStsTimeoutCounter        Counter,
            mobNetworkRepStsSysFailErrorCounter   Counter,
            mobNetworkRepStsDataMisErrorCounter   Counter,
            mobNetworkRepStsUnexpDataValErrorCounter Counter,
            mobNetworkRepStsUnkSubErrorCounter    Counter,
            mobNetworkRepStsMsgWaitListFullErrorCounter Counter,
            mobNetworkRepStsOtherErrorsCounter    Counter,
            mobNetworkRepStsTcapAbortedCounter    Counter,
            mobNetworkRepStsSccpAbortedCounter    Counter,
            mobNetworkRepStsFallbackToVersion2Counter Counter,
            mobNetworkRepStsFallbackToVersion1Counter Counter,
            mobNetworkRecvSriSmRespPassedCounter  Counter,
            mobNetworkRecvSriSmRespBlockedWithPermanentErrorCounter Counter,
            mobNetworkRecvSriSmRespBlockedWithTemporaryErrorCounter Counter,
            mobNetworkRecvSriSmRespBlockedWithNoResponseCounter Counter,
            mobNetworkRecvSriSmRespReleasedCounter Counter,
            mobNetworkRecvSriSmPassedCounter      Counter,
            mobNetworkRecvSriSmBlockedWithPermanentErrorCounter Counter,
            mobNetworkRecvSriSmBlockedWithTemporaryErrorCounter Counter,
            mobNetworkRecvSriSmBlockedWithNoResponseCounter Counter,
            mobNetworkRecvSriSmReleasedCounter    Counter,
            mobNetworkRecvMtPassedCounter         Counter,
            mobNetworkRecvMtBlockedWithPermanentErrorCounter Counter,
            mobNetworkRecvMtBlockedWithTemporaryErrorCounter Counter,
            mobNetworkRecvMtBlockedWithNoResponseCounter Counter,
            mobNetworkRecvMtBlockedWithAckCounter Counter,
            mobNetworkRecvMtReleasedCounter       Counter,
            mobNetworkRecvSriSmInvalidSccpSmscAddressCounter Counter,
            mobNetworkRecvSriSmInvalidMapSmscAddressCounter Counter,
            mobNetworkRecvSriSmInvalidRecipientAddressCounter Counter,
            mobNetworkRecvSriSmInvalidOriginatorAddressCounter Counter,
            mobNetworkRecvSriSmUnknownSccpSmscAddressCounter Counter,
            mobNetworkRecvSriSmUnknownMapSmscAddressCounter Counter,
            mobNetworkRecvSriSmConflictingSmscAddressCounter Counter,
            mobNetworkRecvSriSmMatchingMtRoutingRuleCounter Counter,
            mobNetworkRecvSriSmMatchingMtExtConditionRuleCounter Counter,
            mobNetworkRecvSriSmRespMatchingMtRoutingRuleCounter Counter,
            mobNetworkRecvSriSmRespMatchingMtExtConditionRuleCounter Counter,
            mobNetworkRecvMtInvalidSccpSmscAddressCounter Counter,
            mobNetworkRecvMtInvalidMapSmscAddressCounter Counter,
            mobNetworkRecvMtInvalidOriginatorAddressCounter Counter,
            mobNetworkRecvMtInvalidImsiCounter    Counter,
            mobNetworkRecvMtInvalidMscOrSgsnAddressCounter Counter,
            mobNetworkRecvMtUnknownSccpSmscAddressCounter Counter,
            mobNetworkRecvMtUnknownMapSmscAddressCounter Counter,
            mobNetworkRecvMtConflictingSmscAddressCounter Counter,
            mobNetworkRecvMtSpoofedSccpSmscAddressCounter Counter,
            mobNetworkRecvMtSpoofedMapSmscAddressCounter Counter,
            mobNetworkRecvMtWithoutPrecedingSriSmCounter Counter,
            mobNetworkRecvMtForgedMscOrSgsnAddressCounter Counter,
            mobNetworkRecvMtForgedImsiCounter     Counter,
            mobNetworkRecvMtForgedLmsiCounter     Counter,
            mobNetworkRecvMtMatchingMtRoutingRuleCounter Counter,
            mobNetworkRecvMtMatchingMtExtConditionRuleCounter Counter,
            mobNetworkRecvMtMatchingWhiteListedImsiCounter Counter,
            mobNetworkRecvMoSpoofedOriginatorAddressCounter Counter,
            mobNetworkRecvRogueTcapContinueCounter Counter,
            mobNetworkRecvRogueTcapEndCounter     Counter,
            mobNetworkMobileCountryCode           MobileCountryCode,
            mobNetworkEnableNetworkSpecificMoSpoofingCheck       Boolean,
            mobNetworkMoSpoofingDigits            GtDigitCount,
            mobNetworkCdpaBasedMoForwardingTotalCounter Counter,
            mobNetworkCdpaBasedMoForwardingSuccessCounter Counter,
            mobNetworkCdpaBasedMoForwardingTimeoutCounter Counter,
            mobNetworkCdpaBasedMoForwardingSccpAbortCounter Counter,
            mobNetworkCdpaBasedMoForwardingTcapAbortCounter Counter,
            mobNetworkCdpaBasedMoForwardingUnknownResultCounter Counter,
            mobNetworkCdpaBasedMoForwardingSysFailErrorCounter Counter,
            mobNetworkCdpaBasedMoForwardingDataMisErrorCounter Counter,
            mobNetworkCdpaBasedMoForwardingUnexpDataValErrorCounter Counter,
            mobNetworkCdpaBasedMoForwardingFacNotSuppErrorCounter Counter,
            mobNetworkCdpaBasedMoForwardingUnkScErrorCounter Counter,
            mobNetworkCdpaBasedMoForwardingScCongErrorCounter Counter,
            mobNetworkCdpaBasedMoForwardingInvSmeAddrErrorCounter Counter,
            mobNetworkCdpaBasedMoForwardingSubNotScSubErrorCounter Counter,
            mobNetworkCdpaBasedMoForwardingOtherErrorsCounter Counter
        }

    mobNetworkIndex OBJECT-TYPE
        SYNTAX  MobNetworkTableIndex
        ACCESS  read-write
        STATUS  mandatory
        DESCRIPTION
            "Index of entry in mobile network table."
        ::= { mobNetworkEntry 1 }

    mobNetworkAdminState OBJECT-TYPE
        SYNTAX  AdminState
        ACCESS  read-write
        STATUS  mandatory
        DESCRIPTION
            "Administrative state of the mobile network.

            Transition from 'inactive' state to 'active' state is only
            possible when:
            1) ISO3166 country code, mobile network code and name have been
               supplied;
            2) the country identified with the IS03166 country code is active;
            3) mobile network code or name is not already in use by another
               network of the same country;
            4) number ranges of network start with e164 country code of
               relating country;
            5) number ranges of network do not overlap with number ranges of
               any other network of the same country.
            6) each number range of network does not overlap with another
               number range of network.

            Transition from 'active' state to 'inactive' state is only
            possible if:
            1) none of the 'active' rule record is referring to the network
               with a condition of type NETWORK.

            For details, refer to the comment on the AdminState type."
        ::= { mobNetworkEntry 2 }

    mobNetworkCountry OBJECT-TYPE
        SYNTAX  Country
        ACCESS  read-write
        STATUS  mandatory
        DESCRIPTION
            "Two letter code of country of the mobile network

            For details, refer to the comment on the Country type."
        ::= { mobNetworkEntry 3 }

    mobNetworkOperator OBJECT-TYPE
        SYNTAX  NameString
        ACCESS  read-write
        STATUS  mandatory
        DESCRIPTION
            "Name of operator of the mobile network, e.g. KPN, Vodafone, O2,
            Ben, Dutchtone."
        ::= { mobNetworkEntry 4 }

    mobNetworkMobileNetworkCode OBJECT-TYPE
        SYNTAX  MobileNetworkCodes
        ACCESS  read-write
        STATUS  mandatory
        DESCRIPTION
            "Mobile network codes for the mobile network

            For details, refer to comment on MobileNetworkCode type."
        ::= { mobNetworkEntry 5 }

    mobNetworkMapPhase OBJECT-TYPE
        SYNTAX  MapPhase
        ACCESS  read-write
        STATUS  mandatory
        DESCRIPTION
            "MAP phase to be used when interacting with mobile network."
        ::= { mobNetworkEntry 6 }

    mobNetworkTtForPrimarySriSm OBJECT-TYPE
        SYNTAX  TranslationType
        ACCESS  read-write
        STATUS  mandatory
        DESCRIPTION
            "Translation Type (TT) value to be used in SCCP Called Party
            Address of the first SendRoutingInfoForSm operation to retrieve
            the recipient IMSI. The default for ITU-T is 0, whilst 14 is used
            as a default for ANSI."        
        ::= { mobNetworkEntry 7 }

    mobNetworkEnableFallbackSriSm OBJECT-TYPE
        SYNTAX  Boolean
        ACCESS  read-write
        STATUS  mandatory
        DESCRIPTION
            "Indicator specifying that a second SendRoutingInfoForSm
            operation will be issued for the recipient when the HLR receiving
            the first SendRoutingInfoForSm operation has indicated that it
            does not have the subscriber information of the recipient.
            Default is 'false'."
        ::= { mobNetworkEntry 8 }

    mobNetworkTtForFallbackSriSm OBJECT-TYPE
        SYNTAX  TranslationType
        ACCESS  read-write
        STATUS  mandatory
        DESCRIPTION
            "Translation Type (TT) value to be used in SCCP Called Party
            Address of the second SendRoutingInfoForSm operation to retrieve
            the recipient IMSI. A second SendRoutingInfoForSm operation is
            only used when the HLR receiving the first SendRoutingInfoForSm
            operation has indicated that it does not have the subscriber
            information of the recipient.
            The default for ITU-T is 0, whilst 14 is used as a default for 
            ANSI.
            Note that this object is only relevant when the object 
            mobNetworkEnableFallbackSriSm is equal to 'true'."        
        ::= { mobNetworkEntry 9 }

    mobNetworkMnpPrefix OBJECT-TYPE
        SYNTAX  HexAddressString
        ACCESS  read-write
        STATUS  mandatory
        DESCRIPTION
            "MNP prefix that should be used in SCCP Called Party Address for
            HLR-terminated operations when recipient IMSI is known. When the
            MNP prefix is applied, the GT is a concatenation of the MNP
            prefix and the national significant part of the MSISDN. The NAI
            in the GT is set to 'national' and the TT to 0. 
            By default, the MNP prefix is a zero-length string. The
            zero-length string implies that the MNP prefix is disabled. When
            MNP prefix is disabled, the HLR is addressed the normal way."        
        ::= { mobNetworkEntry 10 }

    mobNetworkMoTotalCounter OBJECT-TYPE
        SYNTAX  Counter
        ACCESS  read-write
        STATUS  mandatory
        DESCRIPTION
            "Counter specifying the total number of times an MO/SM was
            received."
        ::= { mobNetworkEntry 11 }

    mobNetworkMoSuccessfulCounter OBJECT-TYPE
        SYNTAX  Counter
        ACCESS  read-write
        STATUS  mandatory
        DESCRIPTION
            "Counter specifying the number of times an MO/SM was successfully
             routed to its destination. The following events result in
             incrementing of this counter:
             - receiving a MO/SM matching a rule with action equal to
               discardWithAck
             - receiving an ACK from an application as result of an MO/SM
               being routed to the application
             - receiving an ACK from an SMSC as result of an MO/SM being
               routed to the SMSC."
        ::= { mobNetworkEntry 12 }

    mobNetworkMoTimeoutCounter OBJECT-TYPE
        SYNTAX  Counter
        ACCESS  read-write
        STATUS  mandatory
        DESCRIPTION
            "Counter specifying the number of times that routing an MO/SM to
            its destination resulted in a timeout. The following events
            result in incrementing of this counter:
             - not receiving a response from an application on an MO/SM
               being routed to the application within the maximum response
               time
             - receiving an ACK from an SMSC as result of an MO/SM being
               routed to an SMSC within the maximum response time."
        ::= { mobNetworkEntry 13 }

    mobNetworkMoDroppedCounter OBJECT-TYPE
        SYNTAX  Counter
        ACCESS  read-write
        STATUS  mandatory
        DESCRIPTION
            "Counter specifying the number of times that an MO/SM has not
            been routed to its destination due to decimation (this is only
            applicable when routing to an application)."
        ::= { mobNetworkEntry 14 }

    mobNetworkMoDiscardWithNakCounter OBJECT-TYPE
        SYNTAX  Counter
        ACCESS  read-write
        STATUS  mandatory
        DESCRIPTION
            "Counter specifying the number of times that TPR has rejected an
            MO/SM as result of a routing rule with action equal to
            discardWithNak or because none of the routing rules match."
        ::= { mobNetworkEntry 15 }

    mobNetworkMoRejectedByTprCounter OBJECT-TYPE
        SYNTAX  Counter
        ACCESS  read-write
        STATUS  mandatory
        DESCRIPTION
            "Counter specifying the number of times that TPR has rejected an
            MO/SM as result of incorrect syntax of the MO/SM."
        ::= { mobNetworkEntry 16 }

    mobNetworkMoRejectedByAppCounter OBJECT-TYPE
        SYNTAX  Counter
        ACCESS  read-write
        STATUS  mandatory
        DESCRIPTION
            "Counter specifying the number of times that routing to an
            application resulted in the application rejecting the MO/SM by
            sending a NAK."
        ::= { mobNetworkEntry 17 }

    mobNetworkMoUnknownResultCounter OBJECT-TYPE
        SYNTAX  Counter
        ACCESS  read-write
        STATUS  mandatory
        DESCRIPTION
            "Counter specifying the number of times that the result of routing
            an MO/SM to its destination could not be retrieved (this is only
            applicable when using optimal routing towards an SMSC)."
        ::= { mobNetworkEntry 18 }

    mobNetworkMoSysFailErrorCounter OBJECT-TYPE
        SYNTAX  Counter
        ACCESS  read-write
        STATUS  mandatory
        DESCRIPTION
            "Counter specifying the number of times that routing to an SMSC
            resulted in the SMSC rejecting the MO/SM with a System-Failure
            error on MAP level."
        ::= { mobNetworkEntry 19 }

    mobNetworkMoDataMisErrorCounter OBJECT-TYPE
        SYNTAX  Counter
        ACCESS  read-write
        STATUS  mandatory
        DESCRIPTION
            "Counter specifying the number of times that routing to an SMSC
            resulted in the SMSC rejecting the MO/SM with a Data-Missing
            error on MAP level."
        ::= { mobNetworkEntry 20 }

    mobNetworkMoUnexpDataValErrorCounter OBJECT-TYPE
        SYNTAX  Counter
        ACCESS  read-write
        STATUS  mandatory
        DESCRIPTION
            "Counter specifying the number of times that routing to an SMSC
            resulted in the SMSC rejecting the MO/SM with a Unexpected-Data-
            Value error on MAP level."
        ::= { mobNetworkEntry 21 }

    mobNetworkMoFacNotSuppErrorCounter OBJECT-TYPE
        SYNTAX  Counter
        ACCESS  read-write
        STATUS  mandatory
        DESCRIPTION
            "Counter specifying the number of times that routing to an SMSC
            resulted in the SMSC rejecting the MO/SM with a Facility-Not-
            Supported error on MAP level."
        ::= { mobNetworkEntry 22 }

    mobNetworkMoUnkScErrorCounter OBJECT-TYPE

        SYNTAX  Counter
        ACCESS  read-write
        STATUS  mandatory
        DESCRIPTION
            "Counter specifying the number of times that routing to an SMSC
            resulted in the SMSC rejecting the MO/SM with a SM-Delivery-
            Failure error on MAP level with failure cause equal to Unknown-
            Service-Centre."
        ::= { mobNetworkEntry 23 }

    mobNetworkMoScCongErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to SC-
            Congestion."
        ::= { mobNetworkEntry 24 }

    mobNetworkMoInvSmeAddrErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Invalid-
            SME-Address."
        ::= { mobNetworkEntry 25 }

    mobNetworkMoSubNotScSubErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to
            Subscriber-Not-SC-Subscriber."
        ::= { mobNetworkEntry 26 }

    mobNetworkMoOtherErrorsCounter OBJECT-TYPE
        SYNTAX  Counter
        ACCESS  read-write
        STATUS  mandatory
        DESCRIPTION
            "Counter specifying the number of times that routing to an SMSC
            resulted in the SMSC rejecting the MO/SM with another MAP error
            (or possibly a failure cause) than specified for the
            other MO counters."
        ::= { mobNetworkEntry 27 }

    mobNetworkMoTcapAbortedCounter OBJECT-TYPE
        SYNTAX  Counter
        ACCESS  read-write
        STATUS  mandatory
        DESCRIPTION
            "Counter specifying the number of times that routing to an SMSC
            resulted in the SMSC rejecting the MO/SM by sending a TC-ABORT
            on TCAP level."
        ::= { mobNetworkEntry 28 }

    mobNetworkMoSccpAbortedCounter OBJECT-TYPE
        SYNTAX  Counter
        ACCESS  read-write
        STATUS  mandatory
        DESCRIPTION
            "Counter specifying the number of times that routing to an SMSC
            resulted in the SMSC rejecting the MO/SM by sending a UDTS on
            SCCP level."
        ::= { mobNetworkEntry 29 }

    mobNetworkMtTotalCounter OBJECT-TYPE
        SYNTAX  Counter
        ACCESS  read-write
        STATUS  mandatory
        DESCRIPTION
            "Counter specifying the total number of times an MT/SM was issued
            by the TPR. This counter is incremented whenever:
            - the TPR issues a MT/SM on behalf of an application that is
              directly connected to the TPR
            - the TPR receives all MT/SM's from an SMSC and directs the MT/SM
              to its destination."
        ::= { mobNetworkEntry 30 }

    mobNetworkMtSuccessfulCounter OBJECT-TYPE
        SYNTAX  Counter
        ACCESS  read-write
        STATUS  mandatory
        DESCRIPTION
            "Counter specifying the number of times an MT/SM was successfully
            delivered."
        ::= { mobNetworkEntry 31 }

    mobNetworkMtTimeoutCounter OBJECT-TYPE
        SYNTAX  Counter
        ACCESS  read-write
        STATUS  mandatory
        DESCRIPTION
            "Counter specifying the number of times that delivering an MT/SM
            resulted in a timeout."

        ::= { mobNetworkEntry 32 }

    mobNetworkMtAbsSubErrorCounter OBJECT-TYPE
        SYNTAX  Counter
        ACCESS  read-write
        STATUS  mandatory
        DESCRIPTION
            "Counter specifying the number of times that delivering an MT/SM
            resulted in an Absent-Subscriber error."
        ::= { mobNetworkEntry 33 }

    mobNetworkMtSysFailErrorCounter OBJECT-TYPE
        SYNTAX  Counter
        ACCESS  read-write
        STATUS  mandatory
        DESCRIPTION
            "Counter specifying the number of times that delivering an MT/SM
            resulted in an System-Failure error."
        ::= { mobNetworkEntry 34 }

    mobNetworkMtDataMisErrorCounter OBJECT-TYPE
        SYNTAX  Counter
        ACCESS  read-write
        STATUS  mandatory
        DESCRIPTION
            "Counter specifying the number of times that delivering an MT/SM
            resulted in an Data-Missing error."
        ::= { mobNetworkEntry 35 }

    mobNetworkMtUnexpDataValErrorCounter OBJECT-TYPE
        SYNTAX  Counter
        ACCESS  read-write
        STATUS  mandatory
        DESCRIPTION
            "Counter specifying the number of times that delivering an MT/SM
            resulted in an Unexpected-Data-Value error."
        ::= { mobNetworkEntry 36 }

    mobNetworkMtFacNotSuppErrorCounter OBJECT-TYPE
        SYNTAX  Counter
        ACCESS  read-write
        STATUS  mandatory
        DESCRIPTION
            "Counter specifying the number of times that delivering an MT/SM
            resulted in an Facility-Not-Supported error."
        ::= { mobNetworkEntry 37 }

    mobNetworkMtUnidenSubErrorCounter OBJECT-TYPE
        SYNTAX  Counter
        ACCESS  read-write
        STATUS  mandatory
        DESCRIPTION
            "Counter specifying the number of times that delivering an MT/SM
            resulted in an Unidentified-Subscriber error."
        ::= { mobNetworkEntry 38 }

    mobNetworkMtIllSubErrorCounter OBJECT-TYPE
        SYNTAX  Counter
        ACCESS  read-write
        STATUS  mandatory
        DESCRIPTION
            "Counter specifying the number of times that delivering an MT/SM
            resulted in an Illegal-Subscriber error."
        ::= { mobNetworkEntry 39 }

    mobNetworkMtIllEquipErrorCounter OBJECT-TYPE
        SYNTAX  Counter
        ACCESS  read-write
        STATUS  mandatory
        DESCRIPTION
            "Counter specifying the number of times that delivering an MT/SM
            resulted in an Illegal-Equipment error."
        ::= { mobNetworkEntry 40 }

    mobNetworkMtSubBusyForMtSmErrorCounter OBJECT-TYPE
        SYNTAX  Counter
        ACCESS  read-write
        STATUS  mandatory
        DESCRIPTION
            "Counter specifying the number of times that delivering an MT/SM
            resulted in an Subscriber-Busy-For-MT-SMS error."
        ::= { mobNetworkEntry 41 }

    mobNetworkMtInvSmeAddrErrorCounter OBJECT-TYPE
        SYNTAX  Counter

        ACCESS  read-write
        STATUS  mandatory
        DESCRIPTION
            "Counter specifying the number of times that delivering an MT/SM
            resulted in a SM-Delivery-Failure error with failure cause equal
            to Invalid-SME-Address."
        ::= { mobNetworkEntry 42 }

    mobNetworkMtEquipProtErrorCounter OBJECT-TYPE
        SYNTAX  Counter
        ACCESS  read-write
        STATUS  mandatory
        DESCRIPTION
            "Counter specifying the number of times that delivering an MT/SM
            resulted in a SM-Delivery-Failure error with failure cause equal
            to Equipment-Protocol-Error."
        ::= { mobNetworkEntry 43 }

    mobNetworkMtEquipNotSmEquipErrorCounter OBJECT-TYPE
        SYNTAX  Counter
        ACCESS  read-write
        STATUS  mandatory
        DESCRIPTION
            "Counter specifying the number of times that delivering an MT/SM
            resulted in a SM-Delivery-Failure error with failure cause equal
            to Equipment-Not-SM-equipped."
        ::= { mobNetworkEntry 44 }

    mobNetworkMtMemCapExcErrorCounter OBJECT-TYPE
        SYNTAX  Counter
        ACCESS  read-write
        STATUS  mandatory
        DESCRIPTION
            "Counter specifying the number of times that delivering an MT/SM
            resulted in a SM-Delivery-Failure error with failure cause equal
            to Memory-Capacity-Exceeded."
        ::= { mobNetworkEntry 45 }

    mobNetworkMtOtherErrorsCounter OBJECT-TYPE
        SYNTAX  Counter
        ACCESS  read-write
        STATUS  mandatory
        DESCRIPTION
            "Counter specifying the number of times that delivering an MT/SM
            resulted in another MAP error (or possibly a failure cause) than
            specified for the other MT counters."
        ::= { mobNetworkEntry 46 }

    mobNetworkMtTcapAbortedCounter OBJECT-TYPE
        SYNTAX  Counter
        ACCESS  read-write
        STATUS  mandatory
        DESCRIPTION
            "Counter specifying the number of times that delivering an MT/SM
            resulted in the MSC/SGSN rejecting the MT/SM by sending a TC-ABORT
            on TCAP level."
        ::= { mobNetworkEntry 47 }

    mobNetworkMtSccpAbortedCounter OBJECT-TYPE
        SYNTAX  Counter
        ACCESS  read-write
        STATUS  mandatory
        DESCRIPTION
            "Counter specifying the number of times that delivering an MT/SM
            resulted in the MSC/SGSN rejecting the MT/SM by sending a UDTS on
            SCCP level."
        ::= { mobNetworkEntry 48 }

    mobNetworkMtFallbackToVersion2Counter OBJECT-TYPE
        SYNTAX  Counter
        ACCESS  read-write
        STATUS  mandatory
        DESCRIPTION
            "Counter specifying the number of times that delivering an MT/SM
            resulted in the MSC/SGSN requesting to fallback to MAP version 2."
        ::= { mobNetworkEntry 49 }

    mobNetworkMtFallbackToVersion1Counter OBJECT-TYPE
        SYNTAX  Counter
        ACCESS  read-write
        STATUS  mandatory
        DESCRIPTION
            "Counter specifying the number of times that delivering an MT/SM
            resulted in the MSC/SGSN requesting to fallback to MAP version 1."
        ::= { mobNetworkEntry 50 }

    mobNetworkMtAlternatePathUsedCounter OBJECT-TYPE
        SYNTAX  Counter
        ACCESS  read-write
        STATUS  mandatory
        DESCRIPTION
            "Counter specifying the number of times that for delivering an
            MT/SM both paths (through MSC and through SGSN) were available
            and that delivery on the primary path failed (and the alternate
            path was thus used)."
        ::= { mobNetworkEntry 51 }

    mobNetworkMtAlternatePathNotUsedCounter OBJECT-TYPE
        SYNTAX  Counter
        ACCESS  read-write
        STATUS  mandatory
        DESCRIPTION
            "Counter specifying the number of times that for delivering an
            MT/SM both paths (through MSC and through SGSN) were available
            and that delivery on the primary path succeeded (and the
            alternate path was thus not used)."
        ::= { mobNetworkEntry 52 }

    mobNetworkSriSmTotalCounter OBJECT-TYPE
        SYNTAX  Counter
        ACCESS  read-write
        STATUS  mandatory
        DESCRIPTION
            "Counter specifying the total number of times a Send-Routing-Info-
            For-SM operation was issued
            by the TPR. This counter is incremented whenever:
            - the TPR issues a Send-Routing-Info-For-SM operation as part of
              the delivery of a MT/SM that was sent by an application that is
              directly connected to the TPR
            - the TPR receives all Send-Routing-Info-For-SM operations from
              an SMSC and directs the opeation to its destination."
        ::= { mobNetworkEntry 53 }


    mobNetworkSriSmSuccessCounter OBJECT-TYPE
        SYNTAX  Counter
        ACCESS  read-write
        STATUS  mandatory
        DESCRIPTION
            "Counter specifying the number of times a Send-Routing-Info-For-
            SM operation was successfully issued."
        ::= { mobNetworkEntry 54 }

    mobNetworkSriSmTimeoutCounter OBJECT-TYPE
        SYNTAX  Counter
        ACCESS  read-write
        STATUS  mandatory
        DESCRIPTION
            "Counter specifying the number of times that issueing a
            Send-Routing- Info-For-SM operation resulted in a timeout."
        ::= { mobNetworkEntry 55 }

    mobNetworkSriSmSysFailErrorCounter OBJECT-TYPE
        SYNTAX  Counter
        ACCESS  read-write
        STATUS  mandatory
        DESCRIPTION
            "Counter specifying the number of times that issueing a
            Send-Routing- Info-For-SM operation resulted in a System-Failure
            error."
        ::= { mobNetworkEntry 56 }

    mobNetworkSriSmDataMisErrorCounter OBJECT-TYPE
        SYNTAX  Counter
        ACCESS  read-write
        STATUS  mandatory
        DESCRIPTION
            "Counter specifying the number of times that issueing a
            Send-Routing- Info-For-SM operation resulted in a Data-Missing
            error."
        ::= { mobNetworkEntry 57 }

    mobNetworkSriSmUnexpDataValErrorCounter OBJECT-TYPE
        SYNTAX  Counter
        ACCESS  read-write
        STATUS  mandatory
        DESCRIPTION
            "Counter specifying the number of times that issueing a
            Send-Routing- Info-For-SM operation resulted in a
            Unexpected-Data-Value error."
        ::= { mobNetworkEntry 58 }


    mobNetworkSriSmFacNotSuppErrorCounter OBJECT-TYPE
        SYNTAX  Counter
        ACCESS  read-write
        STATUS  mandatory
        DESCRIPTION
            "Counter specifying the number of times that issueing a
            Send-Routing- Info-For-SM operation resulted in a
            Facility-Not-Supported error."
        ::= { mobNetworkEntry 59 }

    mobNetworkSriSmUnkSubErrorCounter OBJECT-TYPE
        SYNTAX  Counter
        ACCESS  read-write
        STATUS  mandatory
        DESCRIPTION
            "Counter specifying the number of times that issueing a
            Send-Routing- Info-For-SM operation resulted in a
            Unknown-Subscriber error."
        ::= { mobNetworkEntry 60 }

    mobNetworkSriSmAbsSubErrorCounter OBJECT-TYPE
        SYNTAX  Counter
        ACCESS  read-write
        STATUS  mandatory
        DESCRIPTION
            "Counter specifying the number of times that issueing a
            Send-Routing- Info-For-SM operation resulted in a
            Absent-Subscriber error."
        ::= { mobNetworkEntry 61 }

    mobNetworkSriSmCallBarredErrorCounter OBJECT-TYPE
        SYNTAX  Counter
        ACCESS  read-write
        STATUS  mandatory
        DESCRIPTION
            "Counter specifying the number of times that issueing a
            Send-Routing- Info-For-SM operation resulted in a Call-Barred
            error."
        ::= { mobNetworkEntry 62 }

    mobNetworkSriSmTeleServNotProvErrorCounter OBJECT-TYPE
        SYNTAX  Counter
        ACCESS  read-write
        STATUS  mandatory
        DESCRIPTION
            "Counter specifying the number of times that issueing a
            Send-Routing- Info-For-SM operation resulted in a
            Teleservice-Not-Provisioned error."
        ::= { mobNetworkEntry 63 }

    mobNetworkSriSmOtherErrorsCounter OBJECT-TYPE
        SYNTAX  Counter
        ACCESS  read-write
        STATUS  mandatory
        DESCRIPTION
            "Counter specifying the number of times that issueing a
            Send-Routing- Info-For-SM operation resulted in another error
            than specified for the other Send-Routing-Info-For-SM counters."
        ::= { mobNetworkEntry 64 }

    mobNetworkSriSmTcapAbortedCounter OBJECT-TYPE
        SYNTAX  Counter
        ACCESS  read-write
        STATUS  mandatory
        DESCRIPTION
            "Counter specifying the number of times that issueing a
            Send-Routing- Info-For-SM operation resulted in the HLR rejecting
            the operation by sending a TC-ABORT on TCAP level."
        ::= { mobNetworkEntry 65 }

    mobNetworkSriSmSccpAbortedCounter OBJECT-TYPE
        SYNTAX  Counter
        ACCESS  read-write
        STATUS  mandatory
        DESCRIPTION
            "Counter specifying the number of times that issueing a
            Send-Routing- Info-For-SM operation resulted in the HLR rejecting
            the operation by sending a UDTS on SCCP level."
        ::= { mobNetworkEntry 66 }

    mobNetworkSriSmFallbackToVersion2Counter OBJECT-TYPE
        SYNTAX  Counter
        ACCESS  read-write
        STATUS  mandatory
        DESCRIPTION
            "Counter specifying the number of times that issueing a
            Send-Routing- Info-For-SM operation resulted in the HLR
            requesting to fallback to MAP version 2."
        ::= { mobNetworkEntry 67 }

    mobNetworkSriSmFallbackToVersion1Counter OBJECT-TYPE
        SYNTAX  Counter
        ACCESS  read-write
        STATUS  mandatory
        DESCRIPTION
            "Counter specifying the number of times that issueing a
            Send-Routing- Info-For-SM operation resulted in the HLR
            requesting to fallback to MAP version 1."
        ::= { mobNetworkEntry 68 }

    mobNetworkRepStsTotalCounter OBJECT-TYPE
        SYNTAX  Counter
        ACCESS  read-write
        STATUS  mandatory
        DESCRIPTION
            "Counter specifying the total number of times a Report-SM-
            Delivery-Status operation was issued
            by the TPR. This counter is incremented whenever:
            - the TPR issues a Report-SM-Delivery-Status operation as part of
              the delivery of a MT/SM that was sent by an application that is
              directly connected to the TPR
            - the TPR receives all Report-SM-Delivery-Status operations from
              an SMSC and directs the opeation to its destination."
        ::= { mobNetworkEntry 69 }

    mobNetworkRepStsSuccessCounter OBJECT-TYPE
        SYNTAX  Counter
        ACCESS  read-write
        STATUS  mandatory
        DESCRIPTION
            "Counter specifying the number of times a Report-SM-Delivery-
            Status operation was successfully issued."
        ::= { mobNetworkEntry 70 }

    mobNetworkRepStsTimeoutCounter OBJECT-TYPE
        SYNTAX  Counter
        ACCESS  read-write
        STATUS  mandatory
        DESCRIPTION
            "Counter specifying the number of times that issueing a Report-SM-
            Delivery-Status operation resulted in a timeout."
        ::= { mobNetworkEntry 71 }

    mobNetworkRepStsSysFailErrorCounter OBJECT-TYPE
        SYNTAX  Counter
        ACCESS  read-write
        STATUS  mandatory
        DESCRIPTION
            "Counter specifying the number of times that issueing a Report-SM-
            Delivery-Status operation resulted in a System-Failure error."
        ::= { mobNetworkEntry 72 }


    mobNetworkRepStsDataMisErrorCounter OBJECT-TYPE
        SYNTAX  Counter
        ACCESS  read-write
        STATUS  mandatory
        DESCRIPTION
            "Counter specifying the number of times that issueing a Report-SM-
            Delivery-Status operation resulted in a Data-Missing error."
        ::= { mobNetworkEntry 73 }

    mobNetworkRepStsUnexpDataValErrorCounter OBJECT-TYPE
        SYNTAX  Counter
        ACCESS  read-write
        STATUS  mandatory
        DESCRIPTION
            "Counter specifying the number of times that issueing a Report-SM-
            Delivery-Status operation resulted in a Unexpected-Data-Value
            error."
        ::= { mobNetworkEntry 74 }

    mobNetworkRepStsUnkSubErrorCounter OBJECT-TYPE
        SYNTAX  Counter
        ACCESS  read-write
        STATUS  mandatory
        DESCRIPTION
           "Counter specifying the number of times that issueing a Report-SM-
            Delivery-Status operation resulted in a Unknown-Subscriber
            error."
        ::= { mobNetworkEntry 75 }

    mobNetworkRepStsMsgWaitListFullErrorCounter OBJECT-TYPE
        SYNTAX  Counter
        ACCESS  read-write
        STATUS  mandatory
        DESCRIPTION
           "Counter specifying the number of times that issueing a Report-SM-
            Delivery-Status operation resulted in a Message-Waiting-List-Full
            error."
        ::= { mobNetworkEntry 76 }

    mobNetworkRepStsOtherErrorsCounter OBJECT-TYPE
        SYNTAX  Counter
        ACCESS  read-write
        STATUS  mandatory
        DESCRIPTION
            "Counter specifying the number of times that issueing a
            Report-SM- Delivery-Status operation resulted in in another error
            than specified for the other Report-SM-Delivery-Status counters."
        ::= { mobNetworkEntry 77 }

    mobNetworkRepStsTcapAbortedCounter OBJECT-TYPE
        SYNTAX  Counter
        ACCESS  read-write
        STATUS  mandatory
        DESCRIPTION
            "Counter specifying the number of times that issueing a Report-SM-
            Delivery-Status operation resulted in the HLR rejecting the
            operation by sending a TC-ABORT on TCAP level."
        ::= { mobNetworkEntry 78 }

    mobNetworkRepStsSccpAbortedCounter OBJECT-TYPE
        SYNTAX  Counter
        ACCESS  read-write
        STATUS  mandatory
        DESCRIPTION
            "Counter specifying the number of times that issueing a Report-SM-
            Delivery-Status operation resulted in the HLR rejecting the
            operation by sending a UDTS on SCCP level."
        ::= { mobNetworkEntry 79 }

    mobNetworkRepStsFallbackToVersion2Counter OBJECT-TYPE
        SYNTAX  Counter
        ACCESS  read-write
        STATUS  mandatory
        DESCRIPTION
            "Counter specifying the number of times that issueing a Report-SM-
            Delivery-Status operation resulted in the HLR requesting to
            fallback to MAP version 2."
        ::= { mobNetworkEntry 80 }

    mobNetworkRepStsFallbackToVersion1Counter OBJECT-TYPE
        SYNTAX  Counter
        ACCESS  read-write
        STATUS  mandatory
        DESCRIPTION
            "Counter specifying the number of times that issueing a Report-SM-
            Delivery-Status operation resulted in the HLR requesting to
            fallback to MAP version 1."
        ::= { mobNetworkEntry 81 }

    mobNetworkRecvSriSmRespPassedCounter OBJECT-TYPE
        SYNTAX  Counter
        ACCESS  read-write
        STATUS  mandatory
        DESCRIPTION
            "Counter specifying the number of times that TextPass received an
             response for an inbound Send-Routing-Info-For-SM operation and 
             relayed it to the invoking SMSC."
        ::= { mobNetworkEntry 91 }

    mobNetworkRecvSriSmRespBlockedWithPermanentErrorCounter OBJECT-TYPE
        SYNTAX  Counter
        ACCESS  read-write
        STATUS  mandatory
        DESCRIPTION
            "Counter specifying the number of times that TextPass rejected a
             response to an inbound Send-Routing-Info-For-SM operation and 
             returned a permanent error to the invoking SMSC."
        ::= { mobNetworkEntry 92 }

    mobNetworkRecvSriSmRespBlockedWithTemporaryErrorCounter OBJECT-TYPE
        SYNTAX  Counter
        ACCESS  read-write
        STATUS  mandatory
        DESCRIPTION
            "Counter specifying the number of times that TextPass rejected a 
             response to an inbound Send-Routing-Info-For-SM operation and 
             returned a temporary error to the invoking SMSC."
        ::= { mobNetworkEntry 93 }

    mobNetworkRecvSriSmRespBlockedWithNoResponseCounter OBJECT-TYPE
        SYNTAX  Counter
        ACCESS  read-write
        STATUS  mandatory
        DESCRIPTION
            "Counter specifying the number of times that TextPass rejected a
             response to an inbound Send-Routing-Info-For-SM operation and 
             did not return anything to the invoking SMSC."
        ::= { mobNetworkEntry 94 }

    mobNetworkRecvSriSmRespReleasedCounter OBJECT-TYPE
        SYNTAX  Counter
        ACCESS  read-write
        STATUS  mandatory
        DESCRIPTION
            "Counter specifying the number of times that TextPass released a
             response to an inbound Send-Routing-Info-For-SM operation."
        ::= { mobNetworkEntry 96 }

    mobNetworkRecvSriSmPassedCounter OBJECT-TYPE
        SYNTAX  Counter
        ACCESS  read-write
        STATUS  mandatory
        DESCRIPTION
            "Counter specifying the number of times that TextPass accepted an
             inbound Send-Routing-Info-For-SM operation and relayed it to an
             HLR on behalf of the invoking SMSC."
        ::= { mobNetworkEntry 101 }

    mobNetworkRecvSriSmBlockedWithPermanentErrorCounter OBJECT-TYPE
        SYNTAX  Counter
        ACCESS  read-write
        STATUS  mandatory
        DESCRIPTION
            "Counter specifying the number of times that TextPass rejected an
            inbound Send-Routing-Info-For-SM operation and returned a
            permanent error to the invoking SMSC."
        ::= { mobNetworkEntry 102 }


    mobNetworkRecvSriSmBlockedWithTemporaryErrorCounter OBJECT-TYPE
        SYNTAX  Counter
        ACCESS  read-write
        STATUS  mandatory
        DESCRIPTION
            "Counter specifying the number of times that TextPass rejected an
            inbound Send-Routing-Info-For-SM operation and returned a
            temporary error to the invoking SMSC."
        ::= { mobNetworkEntry 103 }

    mobNetworkRecvSriSmBlockedWithNoResponseCounter OBJECT-TYPE
        SYNTAX  Counter
        ACCESS  read-write
        STATUS  mandatory
        DESCRIPTION
            "Counter specifying the number of times that TextPass rejected an
             inbound Send-Routing-Info-For-SM operation and did not return
             anything to the invoking SMSC."
        ::= { mobNetworkEntry 104 }

    mobNetworkRecvSriSmReleasedCounter OBJECT-TYPE
        SYNTAX  Counter
        ACCESS  read-write
        STATUS  mandatory
        DESCRIPTION
            "Counter specifying the number of times that TextPass released
             an inbound Send-Routing-Info-For-SM operation."
        ::= { mobNetworkEntry 106 }

    mobNetworkRecvMtPassedCounter OBJECT-TYPE
        SYNTAX  Counter
        ACCESS  read-write
        STATUS  mandatory
        DESCRIPTION
            "Counter specifying the number of times that TextPass accepted an
             inbound MT-Forward-SM operation and relayed it to an MSC/SGSN on
             behalf of the invoking SMSC."
        ::= { mobNetworkEntry 111 }

    mobNetworkRecvMtBlockedWithPermanentErrorCounter OBJECT-TYPE
        SYNTAX  Counter
        ACCESS  read-write
        STATUS  mandatory
        DESCRIPTION
            "Counter specifying the number of times that TextPass rejected an
             inbound MT-Forward-SM operation and returned a permanent error to
             the invoking SMSC."
        ::= { mobNetworkEntry 112 }

    mobNetworkRecvMtBlockedWithTemporaryErrorCounter OBJECT-TYPE
        SYNTAX  Counter
        ACCESS  read-write
        STATUS  mandatory
        DESCRIPTION
            "Counter specifying the number of times that TextPass rejected an
             inbound MT-Forward-SM operation and returned a temporary error to
             the invoking SMSC."
        ::= { mobNetworkEntry 113 }

    mobNetworkRecvMtBlockedWithNoResponseCounter OBJECT-TYPE
        SYNTAX  Counter
        ACCESS  read-write
        STATUS  mandatory
        DESCRIPTION
            "Counter specifying the number of times that TextPass rejected an
            inbound MT-Forward-SM operation and did not return anything to
            the invoking SMSC."
        ::= { mobNetworkEntry 114 }

    mobNetworkRecvMtBlockedWithAckCounter OBJECT-TYPE
        SYNTAX  Counter
        ACCESS  read-write
        STATUS  mandatory
        DESCRIPTION
            "Counter specifying the number of times that TextPass rejected an
             inbound MT-Forward-SM operation, but did a positive response to
             the invoking SMSC."
        ::= { mobNetworkEntry 115 }

    mobNetworkRecvMtReleasedCounter OBJECT-TYPE
        SYNTAX  Counter
        ACCESS  read-write
        STATUS  mandatory
        DESCRIPTION
            "Counter specifying the number of times that TextPass released
             an inbound MT-Forward-For-SM operation."
        ::= { mobNetworkEntry 116 }

    mobNetworkRecvSriSmInvalidSccpSmscAddressCounter OBJECT-TYPE
        SYNTAX  Counter
        ACCESS  read-write
        STATUS  mandatory
        DESCRIPTION
            "Counter specifying the number of times that TextPass rejected an
             inbound Send-Routing-Info-For-SM operation due to an invalid SMSC
             address at SCCP layer."
        ::= { mobNetworkEntry 121 }

    mobNetworkRecvSriSmInvalidMapSmscAddressCounter OBJECT-TYPE
        SYNTAX  Counter
        ACCESS  read-write
        STATUS  mandatory
        DESCRIPTION
            "Counter specifying the number of times that TextPass rejected an
             inbound Send-Routing-Info-For-SM operation due to an invalid SMSC
             address at MAP layer."
        ::= { mobNetworkEntry 122 }

    mobNetworkRecvSriSmInvalidRecipientAddressCounter OBJECT-TYPE
        SYNTAX  Counter
        ACCESS  read-write
        STATUS  mandatory
        DESCRIPTION
            "Counter specifying the number of times that TextPass rejected an
             inbound Send-Routing-Info-For-SM operation due to an invalid
             recipient address."
        ::= { mobNetworkEntry 123 }

    mobNetworkRecvSriSmInvalidOriginatorAddressCounter OBJECT-TYPE
        SYNTAX  Counter
        ACCESS  read-write
        STATUS  mandatory
        DESCRIPTION
            "Counter specifying the number of times that TextPass rejected an
             inbound Send-Routing-Info-For-SM operation due to an invalid
             originator address."
        ::= { mobNetworkEntry 124 }

    mobNetworkRecvSriSmUnknownSccpSmscAddressCounter OBJECT-TYPE
        SYNTAX  Counter
        ACCESS  read-write

        STATUS  mandatory
        DESCRIPTION
            "Counter specifying the number of times that TextPass rejected an
            inbound Send-Routing-Info-For-SM operation due to an SMSC address
            at SCCP layer that could not be associated with any of the
            defined mobile network entities."
        ::= { mobNetworkEntry 125 }

    mobNetworkRecvSriSmUnknownMapSmscAddressCounter OBJECT-TYPE
        SYNTAX  Counter
        ACCESS  read-write
        STATUS  mandatory
        DESCRIPTION
            "Counter specifying the number of times that TextPass rejected an
             inbound Send-Routing-Info-For-SM operation due to an SMSC address
             at MAP layer that could not be associated with any of the defined
             mobile network entities."
        ::= { mobNetworkEntry 126 }

    mobNetworkRecvSriSmConflictingSmscAddressCounter OBJECT-TYPE
        SYNTAX  Counter
        ACCESS  read-write
        STATUS  mandatory
        DESCRIPTION
            "Counter specifying the number of times that TextPass rejected an
            inbound Send-Routing-Info-For-SM operation due to conflicting
            SMSC addresses at SCCP layer and MAP layer. These addresses
            conflict when they are from:
             - different countries (determined on the basis of the country
               code)
             - different mobile networks (determined by associating the
               addresses with a mobile network)."
        ::= { mobNetworkEntry 127 }

    mobNetworkRecvSriSmMatchingMtRoutingRuleCounter OBJECT-TYPE
        SYNTAX  Counter
        ACCESS  read-write
        STATUS  mandatory
        DESCRIPTION
            "Counter specifying the number of times that TextPass rejected an
             inbound Send-Routing-Info-For-SM operation due to a matching MT
             routing rule."
        ::= { mobNetworkEntry 128 }

    mobNetworkRecvSriSmMatchingMtExtConditionRuleCounter OBJECT-TYPE
        SYNTAX  Counter
        ACCESS  read-write
        STATUS  mandatory
        DESCRIPTION
            "Counter specifying the number of times that TextPass rejected an
             inbound Send-Routing-Info-For-SM operation due to a matching MT
             external condition rule."
        ::= { mobNetworkEntry 129 }

    mobNetworkRecvSriSmRespMatchingMtRoutingRuleCounter OBJECT-TYPE
        SYNTAX  Counter
        ACCESS  read-write
        STATUS  mandatory
        DESCRIPTION
            "Counter specifying the number of times that TextPass rejected an
             inbound Send-Routing-Info-For-SM operation due to a matching MT
             routing rule."
        ::= { mobNetworkEntry 130 }

    mobNetworkRecvSriSmRespMatchingMtExtConditionRuleCounter OBJECT-TYPE
        SYNTAX  Counter
        ACCESS  read-write
        STATUS  mandatory
        DESCRIPTION
            "Counter specifying the number of times that TextPass rejected an
             inbound Send-Routing-Info-For-SM operation due to a matching MT
             external condition rule."
        ::= { mobNetworkEntry 131 }

    mobNetworkRecvMtInvalidSccpSmscAddressCounter OBJECT-TYPE
        SYNTAX  Counter
        ACCESS  read-write
        STATUS  mandatory
        DESCRIPTION
            "Counter specifying the number of times that TextPass rejected an
             inbound MT-Forward-SM operation due to an invalid SMSC address at
             SCCP layer."
        ::= { mobNetworkEntry 141 }

    mobNetworkRecvMtInvalidMapSmscAddressCounter OBJECT-TYPE
        SYNTAX  Counter
        ACCESS  read-write
        STATUS  mandatory
        DESCRIPTION
            "Counter specifying the number of times that TextPass rejected an
             inbound MT-Forward-SM operation due to an invalid SMSC address at
             MAP layer."
        ::= { mobNetworkEntry 142 }

    mobNetworkRecvMtInvalidOriginatorAddressCounter OBJECT-TYPE
        SYNTAX  Counter
        ACCESS  read-write
        STATUS  mandatory
        DESCRIPTION
            "Counter specifying the number of times that TextPass rejected an
             inbound MT-Forward-SM operation due to an invalid originator
             address."
        ::= { mobNetworkEntry 143 }

    mobNetworkRecvMtInvalidImsiCounter OBJECT-TYPE
        SYNTAX  Counter
        ACCESS  read-write
        STATUS  mandatory

        DESCRIPTION
            "Counter specifying the number of times that TextPass rejected an
             inbound MT-Forward-SM operation due to an invalid IMSI."
        ::= { mobNetworkEntry 144 }

    mobNetworkRecvMtInvalidMscOrSgsnAddressCounter OBJECT-TYPE
        SYNTAX  Counter
        ACCESS  read-write
        STATUS  mandatory
        DESCRIPTION
            "Counter specifying the number of times that TextPass rejected an
             inbound MT-Forward-SM operation due to an invalid MSC address or
             SGSN address."
        ::= { mobNetworkEntry 145 }

    mobNetworkRecvMtUnknownSccpSmscAddressCounter OBJECT-TYPE
        SYNTAX  Counter
        ACCESS  read-write
        STATUS  mandatory
        DESCRIPTION
            "Counter specifying the number of times that TextPass rejected an
             inbound MT-Forward-SM operation due to an SMSC address at SCCP
             layer that could not be associated with any of the defined mobile
             network entities."
        ::= { mobNetworkEntry 146 }

    mobNetworkRecvMtUnknownMapSmscAddressCounter OBJECT-TYPE
        SYNTAX  Counter
        ACCESS  read-write
        STATUS  mandatory
        DESCRIPTION
            "Counter specifying the number of times that TextPass rejected an
             inbound MT-Forward-SM operation due to an SMSC address at MAP
             layer that could not be associated with any of the defined mobile
             network entities."
        ::= { mobNetworkEntry 147 }

    mobNetworkRecvMtConflictingSmscAddressCounter OBJECT-TYPE
        SYNTAX  Counter
        ACCESS  read-write
        STATUS  mandatory
        DESCRIPTION
            "Counter specifying the number of times that TextPass rejected an
             inbound MT-Forward-SM operation due to:
             - conflicting SMSC addresses at SCCP layer and MAP layer
             - different SMSC addresses at SCCP layer used amongst the various

               TCAP messages of a segmented TCAP dialogue
             SMSC addresses at SCCP layer and MAP layer conflict when they are
             from:
               - different countries (determined on the basis of the country
                 code), or
               - different mobile networks (determined by associating the
                 addresses with a mobile network)."
        ::= { mobNetworkEntry 148 }

    mobNetworkRecvMtSpoofedSccpSmscAddressCounter OBJECT-TYPE
        SYNTAX  Counter
        ACCESS  read-write
        STATUS  mandatory
        DESCRIPTION
            "Counter specifying the number of times that TextPass rejected an
            inbound MT-Forward-SM operation due to spoofing of the SMSC
            address at SCCP level, i.e. using an SMSC address at SCCP level
            for MT-Forward-SM that conflicts with address used in relating
            Send- Routing-Info-For-SM operation. A conflict exist when the
            addresses are from:
               - different countries (determined on the basis of the country
                 code), or
               - different mobile networks (determined by associating the
                 addresses with a mobile network)."
        ::= { mobNetworkEntry 149 }

    mobNetworkRecvMtSpoofedMapSmscAddressCounter OBJECT-TYPE
        SYNTAX  Counter
        ACCESS  read-write
        STATUS  mandatory
        DESCRIPTION
            "Counter specifying the number of times that TextPass rejected an
            inbound MT-Forward-SM operation due to spoofing of the SMSC
            address at MAP level, i.e. using an SMSC address at MAP level for
            MT-Forward-SM that conflicts with address used in relating Send-
            Routing-Info-For-SM operation. A conflict exist when the
            addresses are from:
               - different countries (determined on the basis of the country
                 code), or
               - different mobile networks (determined by associating the
                 addresses with a mobile network)."
        ::= { mobNetworkEntry 150 }

    mobNetworkRecvMtWithoutPrecedingSriSmCounter OBJECT-TYPE
        SYNTAX  Counter
        ACCESS  read-write
        STATUS  mandatory
        DESCRIPTION
            "Counter specifying the number of times that TextPass rejected an
             inbound MT-Forward-SM operation pertaining to a subscriber of the
             operator's network that could not be related with a previously
             received Send-Routing-Info-For-SM operation."
        ::= { mobNetworkEntry 151 }

    mobNetworkRecvMtForgedMscOrSgsnAddressCounter OBJECT-TYPE
        SYNTAX  Counter
        ACCESS  read-write
        STATUS  mandatory
        DESCRIPTION
            "Counter specifying the number of times that TextPass rejected an
             inbound MT-Forward-SM operation due to a forged MSC address or
             SGSN address."
        ::= { mobNetworkEntry 152 }

    mobNetworkRecvMtForgedImsiCounter OBJECT-TYPE
        SYNTAX  Counter
        ACCESS  read-write
        STATUS  mandatory
        DESCRIPTION
            "Counter specifying the number of times that TextPass rejected an
             inbound MT-Forward-SM operation due to a forged IMSI."
        ::= { mobNetworkEntry 153 }

    mobNetworkRecvMtForgedLmsiCounter OBJECT-TYPE
        SYNTAX  Counter

        ACCESS  read-write
        STATUS  mandatory
        DESCRIPTION
            "Counter specifying the number of times that TextPass rejected an
             inbound MT-Forward-SM operation due to a forged LMSI."
        ::= { mobNetworkEntry 154 }

    mobNetworkRecvMtMatchingMtRoutingRuleCounter OBJECT-TYPE
        SYNTAX  Counter
        ACCESS  read-write
        STATUS  mandatory
        DESCRIPTION
            "Counter specifying the number of times that TextPass rejected an
            inbound MT-Forward-SM operation due to a matching MT routing
            rule."
        ::= { mobNetworkEntry 155 }

    mobNetworkRecvMtMatchingMtExtConditionRuleCounter OBJECT-TYPE
        SYNTAX  Counter
        ACCESS  read-write
        STATUS  mandatory
        DESCRIPTION
            "Counter specifying the number of times that TextPass rejected an
             inbound MT-Forward-SM  operation due to a matching MT external
             condition rule."
        ::= { mobNetworkEntry 156 }

    mobNetworkRecvMtMatchingWhiteListedImsiCounter OBJECT-TYPE
        SYNTAX  Counter
        ACCESS  read-write
        STATUS  mandatory
        DESCRIPTION
            "Counter specifying the number of times that TextPass received an
             inbound MT-Forward-SM  operation that matches a whitelisted
             prefix from fwPropNoSpoofCheckWhiteListedRecipientImsi."
        ::= { mobNetworkEntry 157 }

    mobNetworkRecvMoSpoofedOriginatorAddressCounter OBJECT-TYPE
        SYNTAX  Counter
        ACCESS  read-write
        STATUS  mandatory
        DESCRIPTION
            "Counter specifying the number of times that TextPass rejected an
             inbound MO-Forward-SM operation due to due to spoofing of the
             originator address."
        ::= { mobNetworkEntry 191 }

    mobNetworkRecvRogueTcapContinueCounter OBJECT-TYPE
        SYNTAX  Counter
        ACCESS  read-write
        STATUS  mandatory
        DESCRIPTION
            "Counter specifying the number of times that TextPass received an
             TCAP Continue message that had no corresponding previous dialog
             and contained components other than Invoke."
        ::= { mobNetworkEntry 192 }

    mobNetworkRecvRogueTcapEndCounter OBJECT-TYPE
        SYNTAX  Counter
        ACCESS  read-write
        STATUS  mandatory
        DESCRIPTION
            "Counter specifying the number of times that TextPass received an
             TCAP End message that had no corresponding previous dialog."
        ::= { mobNetworkEntry 193 }

    mobNetworkMobileCountryCode OBJECT-TYPE
        SYNTAX  MobileCountryCode
        ACCESS  read-write
        STATUS  mandatory
        DESCRIPTION
            "Mobile country code that is used for the mobile network.
            
            If the countryMobileCountryCode attribute specifies just one
            mobile country code, then this attribute is optional. Otherwise,
            when the countryMobileCountryCode attribute defines multiple
            mobile country codes, the attribute is mandatory.

            The value for this attribute should be equal to one of the mobile 
            country codes that is specified for the countryMobileCountryCode 
            attribute. 
            
            For details, refer to comment on MobileCountryCode type."
        ::= { mobNetworkEntry 201 }

    mobNetworkEnableNetworkSpecificMoSpoofingCheck OBJECT-TYPE
        SYNTAX  Boolean
        ACCESS  read-write
        STATUS  mandatory
        DESCRIPTION
            "Indicator specifying that an MO spoofing check has be performed
            on this network, where the number of digits checked equals the
            value placed into mobNetworkMoSpoofingDigits.
            Default is 'false'."
        ::= { mobNetworkEntry 202 }

    mobNetworkMoSpoofingDigits OBJECT-TYPE
        SYNTAX      GtDigitCount
        ACCESS      read-write
        STATUS      mandatory
        DESCRIPTION 
            "Number of digits from the beginning of the MSC GT used for the 
            MO spoofing check. Any further digits may differ, and no spoofing 
            is detected. Default is 4."
        ::= { mobNetworkEntry 203 }

    mobNetworkCdpaBasedMoForwardingTotalCounter OBJECT-TYPE
        SYNTAX  Counter
        ACCESS  read-write
        STATUS  mandatory
        DESCRIPTION
            "Counter specifying the number of times a cdpa-based
            MO forwarding attempt was made."
        ::= { mobNetworkEntry 211 }

    mobNetworkCdpaBasedMoForwardingSuccessCounter OBJECT-TYPE
        SYNTAX  Counter
        ACCESS  read-write
        STATUS  mandatory
        DESCRIPTION
            "Counter specifying the number of times a cdpa-based
            MO forwarding attempt was successful."
        ::= { mobNetworkEntry 212 }

    mobNetworkCdpaBasedMoForwardingTimeoutCounter OBJECT-TYPE
        SYNTAX  Counter
        ACCESS  read-write
        STATUS  mandatory
        DESCRIPTION
            "Counter specifying the number of times a cdpa-based
            MO forwarding attempt timed out."
        ::= { mobNetworkEntry 213 }

    mobNetworkCdpaBasedMoForwardingSccpAbortCounter OBJECT-TYPE
        SYNTAX  Counter
        ACCESS  read-write
        STATUS  mandatory
        DESCRIPTION
            "Counter specifying the number of times a cdpa-based
            MO forwarding attempt resulted in an SCCP abort."
        ::= { mobNetworkEntry 214 }

    mobNetworkCdpaBasedMoForwardingTcapAbortCounter OBJECT-TYPE
        SYNTAX  Counter
        ACCESS  read-write
        STATUS  mandatory
        DESCRIPTION
            "Counter specifying the number of times a cdpa-based
            MO forwarding attempt resulted in a TCAP abort."
        ::= { mobNetworkEntry 215 }

    mobNetworkCdpaBasedMoForwardingUnknownResultCounter OBJECT-TYPE
        SYNTAX  Counter
        ACCESS  read-write
        STATUS  mandatory
        DESCRIPTION
            "Counter specifying the number of times a cdpa-based
            MO forwarding attempt was made using transparent routing,
            in which case the forwarding result is unknown."
        ::= { mobNetworkEntry 216 }

    mobNetworkCdpaBasedMoForwardingSysFailErrorCounter OBJECT-TYPE
        SYNTAX  Counter
        ACCESS  read-write
        STATUS  mandatory
        DESCRIPTION
            "Counter specifying the number of times a cdpa-based
            MO forwarding attempt resulted in the SMSC returning a
            systemFailure error."
        ::= { mobNetworkEntry 217 }

    mobNetworkCdpaBasedMoForwardingDataMisErrorCounter OBJECT-TYPE
        SYNTAX  Counter
        ACCESS  read-write
        STATUS  mandatory
        DESCRIPTION
            "Counter specifying the number of times a cdpa-based
            MO forwarding attempt resulted in the SMSC returning a
            dataMissing error."
        ::= { mobNetworkEntry 218 }

    mobNetworkCdpaBasedMoForwardingUnexpDataValErrorCounter OBJECT-TYPE
        SYNTAX  Counter
        ACCESS  read-write
        STATUS  mandatory
        DESCRIPTION
            "Counter specifying the number of times a cdpa-based
            MO forwarding attempt resulted in the SMSC returning a
            unexpectedDataValue error."
        ::= { mobNetworkEntry 219 }

    mobNetworkCdpaBasedMoForwardingFacNotSuppErrorCounter OBJECT-TYPE
        SYNTAX  Counter
        ACCESS  read-write
        STATUS  mandatory
        DESCRIPTION
            "Counter specifying the number of times a cdpa-based
            MO forwarding attempt resulted in the SMSC returning a
            facilityNotSupported error."
        ::= { mobNetworkEntry 220 }

    mobNetworkCdpaBasedMoForwardingUnkScErrorCounter OBJECT-TYPE
        SYNTAX  Counter
        ACCESS  read-write
        STATUS  mandatory
        DESCRIPTION
            "Counter specifying the number of times a cdpa-based
            MO forwarding attempt resulted in the SMSC returning a
            unknownServiceCentre error."
        ::= { mobNetworkEntry 221 }

    mobNetworkCdpaBasedMoForwardingScCongErrorCounter OBJECT-TYPE
        SYNTAX  Counter
        ACCESS  read-write
        STATUS  mandatory
        DESCRIPTION
            "Counter specifying the number of times a cdpa-based
            MO forwarding attempt resulted in the SMSC returning a
            serviceCentreCongested error."
        ::= { mobNetworkEntry 222 }

    mobNetworkCdpaBasedMoForwardingInvSmeAddrErrorCounter OBJECT-TYPE
        SYNTAX  Counter
        ACCESS  read-write
        STATUS  mandatory
        DESCRIPTION
            "Counter specifying the number of times a cdpa-based
            MO forwarding attempt resulted in the SMSC returning a
            invalidSmeAddress error."
        ::= { mobNetworkEntry 223 }

    mobNetworkCdpaBasedMoForwardingSubNotScSubErrorCounter OBJECT-TYPE
        SYNTAX  Counter
        ACCESS  read-write
        STATUS  mandatory
        DESCRIPTION
            "Counter specifying the number of times a cdpa-based
            MO forwarding attempt resulted in the SMSC returning a
            subscriberNotScSubscriber error."
        ::= { mobNetworkEntry 224 }

    mobNetworkCdpaBasedMoForwardingOtherErrorsCounter OBJECT-TYPE
        SYNTAX  Counter
        ACCESS  read-write
        STATUS  mandatory
        DESCRIPTION
            "Counter specifying the number of times a cdpa-based
            MO forwarding attempt resulted in an error other than the
            errors specified above."
        ::= { mobNetworkEntry 225 }


    mobNetworkNumberRangeTable OBJECT-TYPE
        SYNTAX  SEQUENCE OF MobNetworkNumberRangeEntry
        ACCESS  not-accessible
        STATUS  mandatory
        DESCRIPTION
            "A table defining the number ranges of a mobile network."
        ::= { sms 33 }

    mobNetworkNumberRangeEntry OBJECT-TYPE
        SYNTAX  MobNetworkNumberRangeEntry
        ACCESS  not-accessible
        STATUS  mandatory
        DESCRIPTION
            "Table entry defining a single number range of a mobile network."
        INDEX   { mobNetworkNumberRangeIndex1, mobNetworkNumberRangeIndex2 }
        ::= { mobNetworkNumberRangeTable 1 }

    MobNetworkNumberRangeEntry ::=
        SEQUENCE {
            mobNetworkNumberRangeIndex1           MobNetworkTableIndex,
            mobNetworkNumberRangeIndex2           MobNetworkNumberRangeTableIndex,
            mobNetworkNumberRange                 GsmAddressRange
        }

    mobNetworkNumberRangeIndex1 OBJECT-TYPE
        SYNTAX  MobNetworkTableIndex
        ACCESS  read-write
        STATUS  mandatory
        DESCRIPTION
            "Index of entry in table containing number ranges for a mobile
            network. This index is actually a reference to the related mobile
            network. Its value is equal to the index of the mobNetworkTable
            entry that specifies the mobile network."
        ::= { mobNetworkNumberRangeEntry 1 }

    mobNetworkNumberRangeIndex2 OBJECT-TYPE
        SYNTAX  MobNetworkNumberRangeTableIndex
        ACCESS  read-write
        STATUS  mandatory
        DESCRIPTION
            "Index of entry in table containing number ranges for a mobile
            network. This index identifies one specific number range."
        ::= { mobNetworkNumberRangeEntry 2 }

    mobNetworkNumberRange OBJECT-TYPE
        SYNTAX  GsmAddressRange
        ACCESS  read-write
        STATUS  mandatory
        DESCRIPTION
           "A number range specification."
        ::= { mobNetworkNumberRangeEntry 11 }

    countryAreaCodeTable OBJECT-TYPE
        SYNTAX  SEQUENCE OF CountryAreaCodeEntry
        ACCESS  not-accessible
        STATUS  mandatory
        DESCRIPTION
            "A table with each row associating a combination of a country 
            code and an area code with a country. This table is required when 
            defining multiple countries with the same E164 country code. This 
            table should have at least one row for each country that shares 
            the same country code with another country. If this is not done,
            the concerning country cannot be activated.
            
            An example of a country code that is shared by multiple countries 
            is 1. It is used by USA, Canada and some of the Caribbean 
            islands. 
            
            The RTR uses this table to retrieve the country that is 
            associated with an address starting with a country code which is 
            shared by multiple countries."
        ::= { sms 34 }

    countryAreaCodeEntry OBJECT-TYPE
        SYNTAX  CountryAreaCodeEntry
        ACCESS  not-accessible
        STATUS  mandatory
        DESCRIPTION
            "Table entry associating a combination of a country 
            code and an area code with a country."
        INDEX   { countryAreaCodeIndex1, countryAreaCodeIndex2 }
        ::= { countryAreaCodeTable 1 }

    CountryAreaCodeEntry ::=
        SEQUENCE {
            countryAreaCodeIndex1                         CountryAreaCodeTableIndex1,
            countryAreaCodeIndex2                         CountryAreaCodeTableIndex2,
            countryAreaCodeAdminState                     AdminState,
            countryAreaCodeCountry                        Country,
            countryAreaCodeCountryCode                    E164Address,
            countryAreaCodeAreaCode                       E164Address
        }

    countryAreaCodeIndex1 OBJECT-TYPE
        SYNTAX  CountryAreaCodeTableIndex1
        ACCESS  read-write
        STATUS  mandatory
        DESCRIPTION
            "First index of entry in country area code table."
        ::= { countryAreaCodeEntry 1 }

    countryAreaCodeIndex2 OBJECT-TYPE
        SYNTAX  CountryAreaCodeTableIndex2
        ACCESS  read-write
        STATUS  mandatory
        DESCRIPTION
            "Second index of entry in country area code table."
        ::= { countryAreaCodeEntry 2 }

    countryAreaCodeAdminState OBJECT-TYPE
        SYNTAX  AdminState
        ACCESS  read-write
        STATUS  mandatory
        DESCRIPTION
            "Administrative state of the country area code.

            Transition from 'inactive' state to 'active' state is only
            possible when:
            1) ISO3166 country code, E164 country code and E164 area code 
               have been supplied;
            2) E164 country code and E164 area code is not already in use 
               by another row.
            3) E164 area code does not overlap with another row with the 
               same E164 country code. 

            Transition from 'active' state to 'inactive' state is only
            possible if it does not break the rule that a country with
            a common country code should have at least one row in this 
            table.

            For details, refer to the comment on the AdminState type."
        ::= { countryAreaCodeEntry 3 }

    countryAreaCodeCountry OBJECT-TYPE
        SYNTAX  Country
        ACCESS  read-write
        STATUS  mandatory
        DESCRIPTION
            "Two letter code of country for the country area code
            For details, refer to the comment on the Country type."
        ::= { countryAreaCodeEntry 4 }

    countryAreaCodeCountryCode OBJECT-TYPE
        SYNTAX  E164Address
        ACCESS  read-write
        STATUS  mandatory
        DESCRIPTION
            "E164 country code for the country area code

            1 for US and Canada

            Refer to http://www.lincmad.com/countrycodes.html for more country
            codes.
            
            The maximum length for country code is 4. Furthermore, the length 
            of country code concatenated with area code should not exceed 6."
        ::= { countryAreaCodeEntry 5 }

    countryAreaCodeAreaCode OBJECT-TYPE
        SYNTAX  E164Address
        ACCESS  read-write
        STATUS  mandatory
        DESCRIPTION
            "E164 area code for the country area code.
            
            The length of country code concatenated with area code should not 
            exceed 6."
        ::= { countryAreaCodeEntry 6 }

    -- Applications

    appCountryStatsTable OBJECT-TYPE
        SYNTAX  SEQUENCE OF AppCountryStatsEntry
        ACCESS  not-accessible
        STATUS  mandatory
        DESCRIPTION
            "A table containing AO/MT statistics per country and per
            application."
        ::= { sms 42 }

    appCountryStatsEntry OBJECT-TYPE
        SYNTAX  AppCountryStatsEntry
        ACCESS  not-accessible
        STATUS  mandatory
        DESCRIPTION
            "Table entry containing AO/MT statistics for one specific country
            and specific application."
        INDEX   { appCountryStatsIndex1, appCountryStatsIndex2 }
        ::= { appCountryStatsTable 1 }

    AppCountryStatsEntry ::=
        SEQUENCE {
            appCountryStatsIndex1                CountryTableIndex,
            appCountryStatsIndex2                ApplicationTableIndex,
            appCountryStatsMoTotalCounter        Counter,
            appCountryStatsMoSuccessfulCounter   Counter,
            appCountryStatsMoTimeoutCounter      Counter,
            appCountryStatsMoDroppedCounter      Counter,
            appCountryStatsMoDiscardWithNakCounter Counter,
            appCountryStatsMoRejectedByTprCounter Counter,
            appCountryStatsMoRejectedByAppCounter Counter,
            appCountryStatsMoUnknownResultCounter Counter,
            appCountryStatsMoSysFailErrorCounter Counter,
            appCountryStatsMoDataMisErrorCounter Counter,
            appCountryStatsMoUnexpDataValErrorCounter Counter,
            appCountryStatsMoFacNotSuppErrorCounter Counter,
            appCountryStatsMoUnkScErrorCounter   Counter,
            appCountryStatsMoScCongErrorCounter  Counter,
            appCountryStatsMoInvSmeAddrErrorCounter Counter,
            appCountryStatsMoSubNotScSubErrorCounter Counter,
            appCountryStatsMoOtherErrorsCounter  Counter,
            appCountryStatsMoTcapAbortedCounter  Counter,
            appCountryStatsMoSccpAbortedCounter  Counter,
            appCountryStatsMtTotalCounter        Counter,
            appCountryStatsMtSuccessfulCounter   Counter,
            appCountryStatsMtTimeoutCounter      Counter,
            appCountryStatsMtAbsSubErrorCounter  Counter,
            appCountryStatsMtSysFailErrorCounter Counter,
            appCountryStatsMtDataMisErrorCounter Counter,
            appCountryStatsMtUnexpDataValErrorCounter Counter,
            appCountryStatsMtFacNotSuppErrorCounter Counter,
            appCountryStatsMtUnidenSubErrorCounter Counter,
            appCountryStatsMtIllSubErrorCounter  Counter,
            appCountryStatsMtIllEquipErrorCounter Counter,
            appCountryStatsMtSubBusyForMtSmErrorCounter Counter,
            appCountryStatsMtInvSmeAddrErrorCounter Counter,
            appCountryStatsMtEquipProtErrorCounter Counter,
            appCountryStatsMtEquipNotSmEquipErrorCounter Counter,
            appCountryStatsMtMemCapExcErrorCounter Counter,
            appCountryStatsMtOtherErrorsCounter  Counter,
            appCountryStatsMtTcapAbortedCounter  Counter,
            appCountryStatsMtSccpAbortedCounter  Counter,
            appCountryStatsMtFallbackToVersion2Counter Counter,
            appCountryStatsMtFallbackToVersion1Counter Counter,
            appCountryStatsMtAlternatePathUsedCounter Counter,
            appCountryStatsMtAlternatePathNotUsedCounter Counter,
            appCountryStatsSriSmTotalCounter     Counter,
            appCountryStatsSriSmSuccessCounter   Counter,
            appCountryStatsSriSmTimeoutCounter   Counter,
            appCountryStatsSriSmSysFailErrorCounter Counter,
            appCountryStatsSriSmDataMisErrorCounter Counter,
            appCountryStatsSriSmUnexpDataValErrorCounter Counter,
            appCountryStatsSriSmFacNotSuppErrorCounter Counter,
            appCountryStatsSriSmUnkSubErrorCounter Counter,
            appCountryStatsSriSmAbsSubErrorCounter Counter,
            appCountryStatsSriSmCallBarredErrorCounter Counter,
            appCountryStatsSriSmTeleServNotProvErrorCounter Counter,
            appCountryStatsSriSmOtherErrorsCounter Counter,
            appCountryStatsSriSmTcapAbortedCounter Counter,
            appCountryStatsSriSmSccpAbortedCounter Counter,
            appCountryStatsSriSmFallbackToVersion2Counter Counter,
            appCountryStatsSriSmFallbackToVersion1Counter Counter,
            appCountryStatsRepStsTotalCounter    Counter,
            appCountryStatsRepStsSuccessCounter  Counter,
            appCountryStatsRepStsTimeoutCounter  Counter,
            appCountryStatsRepStsSysFailErrorCounter Counter,
            appCountryStatsRepStsDataMisErrorCounter Counter,
            appCountryStatsRepStsUnexpDataValErrorCounter Counter,
            appCountryStatsRepStsUnkSubErrorCounter Counter,
            appCountryStatsRepStsMsgWaitListFullErrorCounter Counter,
            appCountryStatsRepStsOtherErrorsCounter Counter,
            appCountryStatsRepStsTcapAbortedCounter Counter,
            appCountryStatsRepStsSccpAbortedCounter Counter,
            appCountryStatsRepStsFallbackToVersion2Counter Counter,
            appCountryStatsRepStsFallbackToVersion1Counter Counter,
            appCountryStatsCntInsideAoTotal           Counter,
            appCountryStatsCntInsideAoSuccess         Counter,
            appCountryStatsCntInsideAoSourceError     Counter,
            appCountryStatsCntInsideAoRoutingError    Counter,
            appCountryStatsCntInsideAoDestinationTemporaryError Counter,
            appCountryStatsCntInsideAoDestinationPermanentRecipientError Counter,
            appCountryStatsCntInsideAoDestinationPermanentMessageError Counter,
            appCountryStatsCntInsideAtTotal           Counter,
            appCountryStatsCntInsideAtSuccess         Counter,
            appCountryStatsCntInsideAtSourceError     Counter,
            appCountryStatsCntInsideAtRoutingError    Counter,
            appCountryStatsCntInsideAtDestinationTemporaryError Counter,
            appCountryStatsCntInsideAtDestinationPermanentRecipientError Counter,
            appCountryStatsCntInsideAtDestinationPermanentMessageError Counter,
            appCountryStatsCntOutsideAoTotal          Counter,
            appCountryStatsCntOutsideAoSuccess        Counter,
            appCountryStatsCntOutsideAoSourceError    Counter,
            appCountryStatsCntOutsideAoRoutingError   Counter,
            appCountryStatsCntOutsideAoDestinationTemporaryError Counter,
            appCountryStatsCntOutsideAoDestinationPermanentRecipientError Counter,
            appCountryStatsCntOutsideAoDestinationPermanentMessageError Counter,
            appCountryStatsCntOutsideAtTotal          Counter,
            appCountryStatsCntOutsideAtSuccess        Counter,
            appCountryStatsCntOutsideAtSourceError    Counter,
            appCountryStatsCntOutsideAtRoutingError   Counter,
            appCountryStatsCntOutsideAtDestinationTemporaryError Counter,
            appCountryStatsCntOutsideAtDestinationPermanentRecipientError Counter,
            appCountryStatsCntOutsideAtDestinationPermanentMessageError Counter
        }

    appCountryStatsIndex1 OBJECT-TYPE

        SYNTAX  CountryTableIndex
        ACCESS  read-write
        STATUS  mandatory
        DESCRIPTION
            "Index of entry in table containing AO/MT statistics per country
            and per application. This index is actually a reference to the
            related country. Its value is equal to the index of the country
            entry that specifies the country."
        ::= { appCountryStatsEntry 1 }

    appCountryStatsIndex2 OBJECT-TYPE
        SYNTAX  ApplicationTableIndex
        ACCESS  read-write
        STATUS  mandatory
        DESCRIPTION
            "Index of entry in table containing AO/MT statistics per country
            and per application. This index is actually a reference to the
            related application. Its value is equal to the index of the
            country entry that specifies the application."
        ::= { appCountryStatsEntry 2 }

    appCountryStatsMoTotalCounter OBJECT-TYPE
        SYNTAX  Counter
        ACCESS  read-write
        STATUS  mandatory
        DESCRIPTION
            "Counter specifying the total number of times an MO/SM was
            received."
        ::= { appCountryStatsEntry 11 }

    appCountryStatsMoSuccessfulCounter OBJECT-TYPE
        SYNTAX  Counter
        ACCESS  read-write
        STATUS  mandatory
        DESCRIPTION
            "Counter specifying the number of times an MO/SM was successfully
             routed to its destination. The following events result in
             incrementing of this counter:
             - receiving a MO/SM matching a rule with action equal to
               discardWithAck
             - receiving an ACK from an application as result of an MO/SM
               being routed to the application
             - receiving an ACK from an SMSC as result of an MO/SM being
               routed to the SMSC."
        ::= { appCountryStatsEntry 12 }

    appCountryStatsMoTimeoutCounter OBJECT-TYPE
        SYNTAX  Counter
        ACCESS  read-write
        STATUS  mandatory
        DESCRIPTION
            "Counter specifying the number of times that routing an MO/SM to
            its destination resulted in a timeout. The following events
            result in incrementing of this counter:
             - not receiving a response from an application on an MO/SM
               being routed to the application within the maximum response
               time
             - receiving an ACK from an SMSC as result of an MO/SM being
               routed to an SMSC within the maximum response time."
        ::= { appCountryStatsEntry 13 }

    appCountryStatsMoDroppedCounter OBJECT-TYPE
        SYNTAX  Counter
        ACCESS  read-write
        STATUS  mandatory
        DESCRIPTION
            "Counter specifying the number of times that an MO/SM has not
            been routed to its destination due to decimation (this is only
            applicable when routing to an application)."
        ::= { appCountryStatsEntry 14 }

    appCountryStatsMoDiscardWithNakCounter OBJECT-TYPE
        SYNTAX  Counter
        ACCESS  read-write
        STATUS  mandatory
        DESCRIPTION
            "Counter specifying the number of times that TPR has rejected an
            MO/SM as result of a routing rule with action equal to
            discardWithNak or because none of the routing rules match."
        ::= { appCountryStatsEntry 15 }

    appCountryStatsMoRejectedByTprCounter OBJECT-TYPE
        SYNTAX  Counter
        ACCESS  read-write
        STATUS  mandatory
        DESCRIPTION
            "Counter specifying the number of times that TPR has rejected an
            MO/SM as result of incorrect syntax of the MO/SM."
        ::= { appCountryStatsEntry 16 }

    appCountryStatsMoRejectedByAppCounter OBJECT-TYPE
        SYNTAX  Counter
        ACCESS  read-write
        STATUS  mandatory
        DESCRIPTION
            "Counter specifying the number of times that routing to an
            application resulted in the application rejecting the MO/SM by
            sending a NAK."
        ::= { appCountryStatsEntry 17 }

    appCountryStatsMoUnknownResultCounter OBJECT-TYPE
        SYNTAX  Counter
        ACCESS  read-write
        STATUS  mandatory
        DESCRIPTION
            "Counter specifying the number of times that the result of
            routing an MO/SM to its destination could not be retrieved (this
            is only applicable when using optimal routing towards an SMSC)."
        ::= { appCountryStatsEntry 18 }

    appCountryStatsMoSysFailErrorCounter OBJECT-TYPE
        SYNTAX  Counter
        ACCESS  read-write
        STATUS  mandatory
        DESCRIPTION
            "Counter specifying the number of times that routing to an SMSC
            resulted in the SMSC rejecting the MO/SM with a System-Failure
            error on MAP level."
        ::= { appCountryStatsEntry 19 }

    appCountryStatsMoDataMisErrorCounter OBJECT-TYPE
        SYNTAX  Counter
        ACCESS  read-write
        STATUS  mandatory
        DESCRIPTION
            "Counter specifying the number of times that routing to an SMSC
            resulted in the SMSC rejecting the MO/SM with a Data-Missing
            error on MAP level."
        ::= { appCountryStatsEntry 20 }

    appCountryStatsMoUnexpDataValErrorCounter OBJECT-TYPE
        SYNTAX  Counter
        ACCESS  read-write
        STATUS  mandatory
        DESCRIPTION
            "Counter specifying the number of times that routing to an SMSC
            resulted in the SMSC rejecting the MO/SM with a Unexpected-Data-
            Value error on MAP level."
        ::= { appCountryStatsEntry 21 }

    appCountryStatsMoFacNotSuppErrorCounter OBJECT-TYPE
        SYNTAX  Counter
        ACCESS  read-write
        STATUS  mandatory
        DESCRIPTION
            "Counter specifying the number of times that routing to an SMSC
            resulted in the SMSC rejecting the MO/SM with a Facility-Not-
            Supported error on MAP level."
        ::= { appCountryStatsEntry 22 }

    appCountryStatsMoUnkScErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Unknown-
            Service-Centre."
        ::= { appCountryStatsEntry 23 }

    appCountryStatsMoScCongErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to SC-
            Congestion."
        ::= { appCountryStatsEntry 24 }


    appCountryStatsMoInvSmeAddrErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Invalid-
            SME-Address."
        ::= { appCountryStatsEntry 25 }

    appCountryStatsMoSubNotScSubErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to
            Subscriber-Not-SC-Subscriber."
        ::= { appCountryStatsEntry 26 }

    appCountryStatsMoOtherErrorsCounter OBJECT-TYPE
        SYNTAX  Counter
        ACCESS  read-write
        STATUS  mandatory
        DESCRIPTION
            "Counter specifying the number of times that routing to an SMSC
            resulted in the SMSC rejecting the MO/SM with another MAP error
            (or possibly a failure cause) than specified for the
            other MO counters."
        ::= { appCountryStatsEntry 27 }

    appCountryStatsMoTcapAbortedCounter OBJECT-TYPE
        SYNTAX  Counter
        ACCESS  read-write
        STATUS  mandatory
        DESCRIPTION
            "Counter specifying the number of times that routing to an SMSC
            resulted in the SMSC rejecting the MO/SM by sending a TC-ABORT
            on TCAP level."
        ::= { appCountryStatsEntry 28 }

    appCountryStatsMoSccpAbortedCounter OBJECT-TYPE
        SYNTAX  Counter
        ACCESS  read-write
        STATUS  mandatory
        DESCRIPTION
            "Counter specifying the number of times that routing to an SMSC
            resulted in the SMSC rejecting the MO/SM by sending a UDTS on
            SCCP level."
        ::= { appCountryStatsEntry 29 }


    appCountryStatsMtTotalCounter OBJECT-TYPE
        SYNTAX  Counter
        ACCESS  read-write
        STATUS  mandatory
        DESCRIPTION
            "Counter specifying the total number of times an MT/SM was issued
            by the TPR. This counter is incremented whenever:
            - the TPR issues a MT/SM on behalf of an application that is
              directly connected to the TPR
            - the TPR receives all MT/SM's from an SMSC and directs the MT/SM
              to its destination."
        ::= { appCountryStatsEntry 30 }

    appCountryStatsMtSuccessfulCounter OBJECT-TYPE
        SYNTAX  Counter
        ACCESS  read-write
        STATUS  mandatory
        DESCRIPTION
            "Counter specifying the number of times an MT/SM was successfully
            delivered."
        ::= { appCountryStatsEntry 31 }

    appCountryStatsMtTimeoutCounter OBJECT-TYPE
        SYNTAX  Counter
        ACCESS  read-write
        STATUS  mandatory
        DESCRIPTION
            "Counter specifying the number of times that delivering an MT/SM
            resulted in a timeout."
        ::= { appCountryStatsEntry 32 }

    appCountryStatsMtAbsSubErrorCounter OBJECT-TYPE
        SYNTAX  Counter
        ACCESS  read-write
        STATUS  mandatory
        DESCRIPTION
            "Counter specifying the number of times that delivering an MT/SM
            resulted in an Absent-Subscriber error."
        ::= { appCountryStatsEntry 33 }

    appCountryStatsMtSysFailErrorCounter OBJECT-TYPE
        SYNTAX  Counter
        ACCESS  read-write
        STATUS  mandatory
        DESCRIPTION
            "Counter specifying the number of times that delivering an MT/SM
            resulted in an System-Failure error."
        ::= { appCountryStatsEntry 34 }

    appCountryStatsMtDataMisErrorCounter OBJECT-TYPE
        SYNTAX  Counter
        ACCESS  read-write
        STATUS  mandatory
        DESCRIPTION
            "Counter specifying the number of times that delivering an MT/SM
            resulted in an Data-Missing error."
        ::= { appCountryStatsEntry 35 }

    appCountryStatsMtUnexpDataValErrorCounter OBJECT-TYPE
        SYNTAX  Counter
        ACCESS  read-write
        STATUS  mandatory
        DESCRIPTION
            "Counter specifying the number of times that delivering an MT/SM
            resulted in an Unexpected-Data-Value error."
        ::= { appCountryStatsEntry 36 }

    appCountryStatsMtFacNotSuppErrorCounter OBJECT-TYPE
        SYNTAX  Counter
        ACCESS  read-write
        STATUS  mandatory
        DESCRIPTION
            "Counter specifying the number of times that delivering an MT/SM
            resulted in an Facility-Not-Supported error."
        ::= { appCountryStatsEntry 37 }

    appCountryStatsMtUnidenSubErrorCounter OBJECT-TYPE
        SYNTAX  Counter
        ACCESS  read-write
        STATUS  mandatory
        DESCRIPTION
            "Counter specifying the number of times that delivering an MT/SM
            resulted in an Unidentified-Subscriber error."
        ::= { appCountryStatsEntry 38 }

    appCountryStatsMtIllSubErrorCounter OBJECT-TYPE
        SYNTAX  Counter
        ACCESS  read-write
        STATUS  mandatory
        DESCRIPTION
            "Counter specifying the number of times that delivering an MT/SM
            resulted in an Illegal-Subscriber error."
        ::= { appCountryStatsEntry 39 }

    appCountryStatsMtIllEquipErrorCounter OBJECT-TYPE
        SYNTAX  Counter
        ACCESS  read-write
        STATUS  mandatory
        DESCRIPTION
            "Counter specifying the number of times that delivering an MT/SM
            resulted in an Illegal-Equipment error."
        ::= { appCountryStatsEntry 40 }

    appCountryStatsMtSubBusyForMtSmErrorCounter OBJECT-TYPE
        SYNTAX  Counter
        ACCESS  read-write
        STATUS  mandatory
        DESCRIPTION
            "Counter specifying the number of times that delivering an MT/SM
            resulted in an Subscriber-Busy-For-MT-SMS error."
        ::= { appCountryStatsEntry 41 }

    appCountryStatsMtInvSmeAddrErrorCounter OBJECT-TYPE
        SYNTAX  Counter
        ACCESS  read-write
        STATUS  mandatory
        DESCRIPTION
            "Counter specifying the number of times that delivering an MT/SM
            resulted in a SM-Delivery-Failure error with failure cause equal
            to Invalid-SME-Address."
        ::= { appCountryStatsEntry 42 }

    appCountryStatsMtEquipProtErrorCounter OBJECT-TYPE
        SYNTAX  Counter

        ACCESS  read-write
        STATUS  mandatory
        DESCRIPTION
            "Counter specifying the number of times that delivering an MT/SM
            resulted in a SM-Delivery-Failure error with failure cause equal
            to Equipment-Protocol-Error."
        ::= { appCountryStatsEntry 43 }

    appCountryStatsMtEquipNotSmEquipErrorCounter OBJECT-TYPE
        SYNTAX  Counter
        ACCESS  read-write
        STATUS  mandatory
        DESCRIPTION
            "Counter specifying the number of times that delivering an MT/SM
            resulted in a SM-Delivery-Failure error with failure cause equal
            to Equipment-Not-SM-equipped."
        ::= { appCountryStatsEntry 44 }

    appCountryStatsMtMemCapExcErrorCounter OBJECT-TYPE
        SYNTAX  Counter
        ACCESS  read-write
        STATUS  mandatory
        DESCRIPTION
            "Counter specifying the number of times that delivering an MT/SM
            resulted in a SM-Delivery-Failure error with failure cause equal
            to Memory-Capacity-Exceeded."
        ::= { appCountryStatsEntry 45 }

    appCountryStatsMtOtherErrorsCounter OBJECT-TYPE
        SYNTAX  Counter
        ACCESS  read-write
        STATUS  mandatory
        DESCRIPTION
            "Counter specifying the number of times that delivering an MT/SM
            resulted in another MAP error (or possibly a failure cause) than
            specified for the other MT counters."
        ::= { appCountryStatsEntry 46 }

    appCountryStatsMtTcapAbortedCounter OBJECT-TYPE

        SYNTAX  Counter
        ACCESS  read-write
        STATUS  mandatory
        DESCRIPTION
            "Counter specifying the number of times that delivering an MT/SM
            resulted in the MSC/SGSN rejecting the MT/SM by sending a TC-ABORT
            on TCAP level."
        ::= { appCountryStatsEntry 47 }

    appCountryStatsMtSccpAbortedCounter OBJECT-TYPE
        SYNTAX  Counter
        ACCESS  read-write
        STATUS  mandatory
        DESCRIPTION
            "Counter specifying the number of times that delivering an MT/SM
            resulted in the MSC/SGSN rejecting the MT/SM by sending a UDTS on
            SCCP level."
        ::= { appCountryStatsEntry 48 }

    appCountryStatsMtFallbackToVersion2Counter OBJECT-TYPE
        SYNTAX  Counter
        ACCESS  read-write
        STATUS  mandatory
        DESCRIPTION
            "Counter specifying the number of times that delivering an MT/SM
            resulted in the MSC/SGSN requesting to fallback to MAP version 2."
        ::= { appCountryStatsEntry 49 }

    appCountryStatsMtFallbackToVersion1Counter OBJECT-TYPE
        SYNTAX  Counter
        ACCESS  read-write
        STATUS  mandatory
        DESCRIPTION
            "Counter specifying the number of times that delivering an MT/SM
            resulted in the MSC/SGSN requesting to fallback to MAP version 1."
        ::= { appCountryStatsEntry 50 }

    appCountryStatsMtAlternatePathUsedCounter OBJECT-TYPE
        SYNTAX  Counter
        ACCESS  read-write
        STATUS  mandatory
        DESCRIPTION
            "Counter specifying the number of times that for delivering an
            MT/SM both paths (through MSC and through SGSN) were available
            and that delivery on the primary path failed (and the alternate
            path was thus used)."
        ::= { appCountryStatsEntry 51 }

    appCountryStatsMtAlternatePathNotUsedCounter OBJECT-TYPE
        SYNTAX  Counter
        ACCESS  read-write
        STATUS  mandatory
        DESCRIPTION
            "Counter specifying the number of times that for delivering an
            MT/SM both paths (through MSC and through SGSN) were available
            and that delivery on the primary path succeeded (and the
            alternate path was thus not used)."
        ::= { appCountryStatsEntry 52 }

    appCountryStatsSriSmTotalCounter OBJECT-TYPE
        SYNTAX  Counter
        ACCESS  read-write
        STATUS  mandatory
        DESCRIPTION
            "Counter specifying the total number of times a Send-Routing-Info-
            For-SM operation was issued
            by the TPR. This counter is incremented whenever:
            - the TPR issues a Send-Routing-Info-For-SM operation as part of
              the delivery of a MT/SM that was sent by an application that is
              directly connected to the TPR
            - the TPR receives all Send-Routing-Info-For-SM operations from
              an SMSC and directs the opeation to its destination."
        ::= { appCountryStatsEntry 53 }

    appCountryStatsSriSmSuccessCounter OBJECT-TYPE
        SYNTAX  Counter
        ACCESS  read-write
        STATUS  mandatory
        DESCRIPTION
            "Counter specifying the number of times a Send-Routing-Info-For-
            SM operation was successfully issued."
        ::= { appCountryStatsEntry 54 }

    appCountryStatsSriSmTimeoutCounter OBJECT-TYPE
        SYNTAX  Counter
        ACCESS  read-write
        STATUS  mandatory
        DESCRIPTION
            "Counter specifying the number of times that issueing a
            Send-Routing- Info-For-SM operation resulted in a timeout."
        ::= { appCountryStatsEntry 55 }

    appCountryStatsSriSmSysFailErrorCounter OBJECT-TYPE
        SYNTAX  Counter
        ACCESS  read-write
        STATUS  mandatory
        DESCRIPTION
            "Counter specifying the number of times that issueing a
            Send-Routing- Info-For-SM operation resulted in a System-Failure
            error."
        ::= { appCountryStatsEntry 56 }

    appCountryStatsSriSmDataMisErrorCounter OBJECT-TYPE
        SYNTAX  Counter
        ACCESS  read-write
        STATUS  mandatory
        DESCRIPTION
            "Counter specifying the number of times that issueing a
            Send-Routing- Info-For-SM operation resulted in a Data-Missing
            error."
        ::= { appCountryStatsEntry 57 }

    appCountryStatsSriSmUnexpDataValErrorCounter OBJECT-TYPE
        SYNTAX  Counter
        ACCESS  read-write
        STATUS  mandatory
        DESCRIPTION
            "Counter specifying the number of times that issueing a
            Send-Routing- Info-For-SM operation resulted in a
            Unexpected-Data-Value error."
        ::= { appCountryStatsEntry 58 }

    appCountryStatsSriSmFacNotSuppErrorCounter OBJECT-TYPE
        SYNTAX  Counter
        ACCESS  read-write
        STATUS  mandatory
        DESCRIPTION
            "Counter specifying the number of times that issueing a
            Send-Routing- Info-For-SM operation resulted in a
            Facility-Not-Supported error."
        ::= { appCountryStatsEntry 59 }

    appCountryStatsSriSmUnkSubErrorCounter OBJECT-TYPE
        SYNTAX  Counter
        ACCESS  read-write
        STATUS  mandatory
        DESCRIPTION
            "Counter specifying the number of times that issueing a
            Send-Routing- Info-For-SM operation resulted in a
            Unknown-Subscriber error."
        ::= { appCountryStatsEntry 60 }

    appCountryStatsSriSmAbsSubErrorCounter OBJECT-TYPE
        SYNTAX  Counter
        ACCESS  read-write
        STATUS  mandatory
        DESCRIPTION
            "Counter specifying the number of times that issueing a
            Send-Routing- Info-For-SM operation resulted in a
            Absent-Subscriber error."
        ::= { appCountryStatsEntry 61 }

    appCountryStatsSriSmCallBarredErrorCounter OBJECT-TYPE
        SYNTAX  Counter
        ACCESS  read-write
        STATUS  mandatory
        DESCRIPTION
            "Counter specifying the number of times that issueing a
            Send-Routing- Info-For-SM operation resulted in a Call-Barred
            error."
        ::= { appCountryStatsEntry 62 }

    appCountryStatsSriSmTeleServNotProvErrorCounter OBJECT-TYPE
        SYNTAX  Counter
        ACCESS  read-write
        STATUS  mandatory
        DESCRIPTION
            "Counter specifying the number of times that issueing a
            Send-Routing- Info-For-SM operation resulted in a
            Teleservice-Not-Provisioned error."
        ::= { appCountryStatsEntry 63 }

    appCountryStatsSriSmOtherErrorsCounter OBJECT-TYPE
        SYNTAX  Counter
        ACCESS  read-write
        STATUS  mandatory
        DESCRIPTION
            "Counter specifying the number of times that issueing a
            Send-Routing- Info-For-SM operation resulted in another error
            than specified for the other Send-Routing-Info-For-SM counters."
        ::= { appCountryStatsEntry 64 }

    appCountryStatsSriSmTcapAbortedCounter OBJECT-TYPE
        SYNTAX  Counter
        ACCESS  read-write
        STATUS  mandatory
        DESCRIPTION
            "Counter specifying the number of times that issueing a
            Send-Routing- Info-For-SM operation resulted in the HLR rejecting
            the operation by sending a TC-ABORT on TCAP level."
        ::= { appCountryStatsEntry 65 }

    appCountryStatsSriSmSccpAbortedCounter OBJECT-TYPE
        SYNTAX  Counter
        ACCESS  read-write
        STATUS  mandatory
        DESCRIPTION
            "Counter specifying the number of times that issueing a
            Send-Routing- Info-For-SM operation resulted in the HLR rejecting
            the operation by sending a UDTS on SCCP level."
        ::= { appCountryStatsEntry 66 }

    appCountryStatsSriSmFallbackToVersion2Counter OBJECT-TYPE
        SYNTAX  Counter
        ACCESS  read-write
        STATUS  mandatory
        DESCRIPTION
            "Counter specifying the number of times that issueing a
            Send-Routing- Info-For-SM operation resulted in the HLR
            requesting to fallback to MAP version 2."
        ::= { appCountryStatsEntry 67 }

    appCountryStatsSriSmFallbackToVersion1Counter OBJECT-TYPE
        SYNTAX  Counter
        ACCESS  read-write
        STATUS  mandatory
        DESCRIPTION
            "Counter specifying the number of times that issueing a
            Send-Routing- Info-For-SM operation resulted in the HLR
            requesting to fallback to MAP version 1."
        ::= { appCountryStatsEntry 68 }

    appCountryStatsRepStsTotalCounter OBJECT-TYPE
        SYNTAX  Counter
        ACCESS  read-write
        STATUS  mandatory
        DESCRIPTION
            "Counter specifying the total number of times a Report-SM-
            Delivery-Status operation was issued
            by the TPR. This counter is incremented whenever:
            - the TPR issues a Report-SM-Delivery-Status operation as part of
              the delivery of a MT/SM that was sent by an application that is

              directly connected to the TPR
            - the TPR receives all Report-SM-Delivery-Status operations from
              an SMSC and directs the opeation to its destination."
        ::= { appCountryStatsEntry 69 }

    appCountryStatsRepStsSuccessCounter OBJECT-TYPE
        SYNTAX  Counter
        ACCESS  read-write
        STATUS  mandatory
        DESCRIPTION
            "Counter specifying the number of times a Report-SM-Delivery-
            Status operation was successfully issued."
        ::= { appCountryStatsEntry 70 }

    appCountryStatsRepStsTimeoutCounter OBJECT-TYPE
        SYNTAX  Counter
        ACCESS  read-write
        STATUS  mandatory
        DESCRIPTION
            "Counter specifying the number of times that issueing a Report-SM-
            Delivery-Status operation resulted in a timeout."
        ::= { appCountryStatsEntry 71 }

    appCountryStatsRepStsSysFailErrorCounter OBJECT-TYPE
        SYNTAX  Counter
        ACCESS  read-write
        STATUS  mandatory
        DESCRIPTION
            "Counter specifying the number of times that issueing a Report-SM-
            Delivery-Status operation resulted in a System-Failure error."
        ::= { appCountryStatsEntry 72 }

    appCountryStatsRepStsDataMisErrorCounter OBJECT-TYPE
        SYNTAX  Counter
        ACCESS  read-write
        STATUS  mandatory
        DESCRIPTION
            "Counter specifying the number of times that issueing a Report-SM-
            Delivery-Status operation resulted in a Data-Missing error."
        ::= { appCountryStatsEntry 73 }

    appCountryStatsRepStsUnexpDataValErrorCounter OBJECT-TYPE
        SYNTAX  Counter
        ACCESS  read-write
        STATUS  mandatory
        DESCRIPTION
            "Counter specifying the number of times that issueing a Report-SM-
            Delivery-Status operation resulted in a Unexpected-Data-Value
            error."
        ::= { appCountryStatsEntry 74 }

    appCountryStatsRepStsUnkSubErrorCounter OBJECT-TYPE
        SYNTAX  Counter
        ACCESS  read-write
        STATUS  mandatory
        DESCRIPTION
           "Counter specifying the number of times that issueing a Report-SM-
            Delivery-Status operation resulted in a Unknown-Subscriber
            error."
        ::= { appCountryStatsEntry 75 }


    appCountryStatsRepStsMsgWaitListFullErrorCounter OBJECT-TYPE
        SYNTAX  Counter
        ACCESS  read-write
        STATUS  mandatory
        DESCRIPTION
           "Counter specifying the number of times that issueing a Report-SM-
            Delivery-Status operation resulted in a Message-Waiting-List-Full
            error."
        ::= { appCountryStatsEntry 76 }

    appCountryStatsRepStsOtherErrorsCounter OBJECT-TYPE
        SYNTAX  Counter
        ACCESS  read-write
        STATUS  mandatory
        DESCRIPTION
            "Counter specifying the number of times that issueing a
            Report-SM- Delivery-Status operation resulted in in another error
            than specified for the other Report-SM-Delivery-Status counters."
        ::= { appCountryStatsEntry 77 }

    appCountryStatsRepStsTcapAbortedCounter OBJECT-TYPE
        SYNTAX  Counter
        ACCESS  read-write
        STATUS  mandatory
        DESCRIPTION
            "Counter specifying the number of times that issueing a Report-SM-
            Delivery-Status operation resulted in the HLR rejecting the
            operation by sending a TC-ABORT on TCAP level."
        ::= { appCountryStatsEntry 78 }

    appCountryStatsRepStsSccpAbortedCounter OBJECT-TYPE
        SYNTAX  Counter
        ACCESS  read-write
        STATUS  mandatory
        DESCRIPTION
            "Counter specifying the number of times that issueing a Report-SM-
            Delivery-Status operation resulted in the HLR rejecting the
            operation by sending a UDTS on SCCP level."
        ::= { appCountryStatsEntry 79 }

    appCountryStatsRepStsFallbackToVersion2Counter OBJECT-TYPE
        SYNTAX  Counter
        ACCESS  read-write
        STATUS  mandatory
        DESCRIPTION
            "Counter specifying the number of times that issueing a Report-SM-
            Delivery-Status operation resulted in the HLR requesting to
            fallback to MAP version 2."
        ::= { appCountryStatsEntry 80 }

    appCountryStatsRepStsFallbackToVersion1Counter OBJECT-TYPE
        SYNTAX  Counter
        ACCESS  read-write
        STATUS  mandatory
        DESCRIPTION
            "Counter specifying the number of times that issueing a Report-SM-
            Delivery-Status operation resulted in the HLR requesting to
            fallback to MAP version 1."
        ::= { appCountryStatsEntry 81 }

    appCountryStatsCntInsideAoTotal OBJECT-TYPE
        SYNTAX  Counter
        ACCESS  read-write
        STATUS  mandatory
        DESCRIPTION
            "Counter specifying the total number of times an AO/SM was
            sent towards a service centre."
        ::= { appCountryStatsEntry 91 }

    appCountryStatsCntInsideAoSuccess OBJECT-TYPE
        SYNTAX  Counter
        ACCESS  read-write
        STATUS  mandatory
        DESCRIPTION
            "Counter specifying the number of times an AO/SM was
            successfully routed to its destination."
        ::= { appCountryStatsEntry 92 }

    appCountryStatsCntInsideAoSourceError OBJECT-TYPE
        SYNTAX  Counter
        ACCESS  read-write
        STATUS  mandatory
        DESCRIPTION
            "Counter specifying the number of times an AO/SM towards
             a service centre resulted in a source error
             (like a syntax error). The error mapping
             table is used to identify a source error. With a correct
             error mapping table it is not possible that this counter
             increases."
        ::= { appCountryStatsEntry 93 }

    appCountryStatsCntInsideAoRoutingError OBJECT-TYPE
        SYNTAX  Counter
        ACCESS  read-write
        STATUS  mandatory
        DESCRIPTION
            "Counter specifying the number of times an AO/SM towards
            a service centre resulted in a routing error. The error
            mapping table is used to identify a routing error."
        ::= { appCountryStatsEntry 94 }

    appCountryStatsCntInsideAoDestinationTemporaryError OBJECT-TYPE
        SYNTAX  Counter
        ACCESS  read-write
        STATUS  mandatory
        DESCRIPTION
            "Counter specifying the number of times an AO/SM towards
            a service centre resulted in a temporary error. The error
            mapping table is used to identify a temporary error."
        ::= { appCountryStatsEntry 95 }

    appCountryStatsCntInsideAoDestinationPermanentRecipientError OBJECT-TYPE
        SYNTAX  Counter
        ACCESS  read-write
        STATUS  mandatory
        DESCRIPTION
            "Counter specifying the number of times an AO/SM towards
            a service centre resulted in a permanent recipient error. 
            The error mapping table is used to identify a permanent 
            recipient error."
        ::= { appCountryStatsEntry 96 }

    appCountryStatsCntInsideAoDestinationPermanentMessageError OBJECT-TYPE
        SYNTAX  Counter
        ACCESS  read-write
        STATUS  mandatory
        DESCRIPTION
            "Counter specifying the number of times an AO/SM towards
            a service centre resulted in a permanent message error. The 
            error mapping table is used to identify a permanent message 
            error."
        ::= { appCountryStatsEntry 97 }

    appCountryStatsCntInsideAtTotal OBJECT-TYPE
        SYNTAX  Counter
        ACCESS  read-write
        STATUS  mandatory
        DESCRIPTION
            "Counter specifying the total number of times an AT/SM was
            received from a service centre."
        ::= { appCountryStatsEntry 98 }

    appCountryStatsCntInsideAtSuccess OBJECT-TYPE
        SYNTAX  Counter
        ACCESS  read-write
        STATUS  mandatory
        DESCRIPTION
            "Counter specifying the number of times an AT/SM was
            successfully routed to its destination."
        ::= { appCountryStatsEntry 99 }

    appCountryStatsCntInsideAtSourceError OBJECT-TYPE
        SYNTAX  Counter
        ACCESS  read-write
        STATUS  mandatory
        DESCRIPTION
            "Counter specifying the number of times an AT/SM from
             a service centre resulted in a source error
             (like a syntax error). The error mapping
             table is used to identify a source error."
        ::= { appCountryStatsEntry 100 }

    appCountryStatsCntInsideAtRoutingError OBJECT-TYPE
        SYNTAX  Counter
        ACCESS  read-write
        STATUS  mandatory
        DESCRIPTION
            "Counter specifying the number of times an AT/SM from
            a service centre resulted in a routing error. The error
            mapping table is used to identify a routing error."
        ::= { appCountryStatsEntry 101 }

    appCountryStatsCntInsideAtDestinationTemporaryError OBJECT-TYPE
        SYNTAX  Counter
        ACCESS  read-write
        STATUS  mandatory
        DESCRIPTION
            "Counter specifying the number of times an AT/SM from
            a service centre resulted in a temporary error. The error
            mapping table is used to identify a temporary error."
        ::= { appCountryStatsEntry 102 }

    appCountryStatsCntInsideAtDestinationPermanentRecipientError OBJECT-TYPE
        SYNTAX  Counter
        ACCESS  read-write
        STATUS  mandatory
        DESCRIPTION
            "Counter specifying the number of times an AT/SM from
            a service centre resulted in a permanent recipient error. 
            The error mapping table is used to identify a permanent 
            recipient error."
        ::= { appCountryStatsEntry 103 }

    appCountryStatsCntInsideAtDestinationPermanentMessageError OBJECT-TYPE
        SYNTAX  Counter
        ACCESS  read-write
        STATUS  mandatory
        DESCRIPTION
            "Counter specifying the number of times an AT/SM from
            a service centre resulted in a permanent message error. The 
            error mapping table is used to identify a permanent message 
            error."
        ::= { appCountryStatsEntry 104 }

    appCountryStatsCntOutsideAoTotal OBJECT-TYPE
        SYNTAX  Counter
        ACCESS  read-write
        STATUS  mandatory
        DESCRIPTION
            "Counter specifying the total number of times an AO/SM was
            received from an application."
        ::= { appCountryStatsEntry 105 }

    appCountryStatsCntOutsideAoSuccess OBJECT-TYPE
        SYNTAX  Counter
        ACCESS  read-write
        STATUS  mandatory
        DESCRIPTION
            "Counter specifying the number of times an AO/SM was
            successfully routed to its destination."
        ::= { appCountryStatsEntry 106 }

    appCountryStatsCntOutsideAoSourceError OBJECT-TYPE
        SYNTAX  Counter
        ACCESS  read-write
        STATUS  mandatory
        DESCRIPTION
            "Counter specifying the number of times an AO/SM from
             an application resulted in a source error
             (like a syntax error). The error mapping
             table is used to identify a source error."
        ::= { appCountryStatsEntry 107 }

    appCountryStatsCntOutsideAoRoutingError OBJECT-TYPE
        SYNTAX  Counter
        ACCESS  read-write
        STATUS  mandatory
        DESCRIPTION
            "Counter specifying the number of times an AO/SM from
            an application resulted in a routing error. The error
            mapping table is used to identify a routing error."
        ::= { appCountryStatsEntry 108 }

    appCountryStatsCntOutsideAoDestinationTemporaryError OBJECT-TYPE
        SYNTAX  Counter
        ACCESS  read-write
        STATUS  mandatory
        DESCRIPTION
            "Counter specifying the number of times an AO/SM from
            an application resulted in a temporary error. The error
            mapping table is used to identify a temporary error."
        ::= { appCountryStatsEntry 109 }

    appCountryStatsCntOutsideAoDestinationPermanentRecipientError OBJECT-TYPE
        SYNTAX  Counter
        ACCESS  read-write
        STATUS  mandatory
        DESCRIPTION
            "Counter specifying the number of times an AO/SM from
            an application resulted in a permanent recipient error. 
            The error mapping table is used to identify a permanent 
            recipient error."
        ::= { appCountryStatsEntry 110 }

    appCountryStatsCntOutsideAoDestinationPermanentMessageError OBJECT-TYPE
        SYNTAX  Counter
        ACCESS  read-write
        STATUS  mandatory
        DESCRIPTION
            "Counter specifying the number of times an AO/SM from
            an application resulted in a permanent message error. 
            The error mapping table is used to identify a permanent 
            message error."
        ::= { appCountryStatsEntry 111 }

    appCountryStatsCntOutsideAtTotal OBJECT-TYPE
        SYNTAX  Counter
        ACCESS  read-write
        STATUS  mandatory
        DESCRIPTION
            "Counter specifying the total number of times an AT/SM was
            sent towards an application."
        ::= { appCountryStatsEntry 112 }

    appCountryStatsCntOutsideAtSuccess OBJECT-TYPE
        SYNTAX  Counter
        ACCESS  read-write
        STATUS  mandatory
        DESCRIPTION
            "Counter specifying the number of times an AT/SM was
            successfully routed to its destination."
        ::= { appCountryStatsEntry 113 }

    appCountryStatsCntOutsideAtSourceError OBJECT-TYPE
        SYNTAX  Counter
        ACCESS  read-write
        STATUS  mandatory
        DESCRIPTION
            "Counter specifying the number of times an AT/SM towards
             an application resulted in a source error
             (like a syntax error). The error mapping
             table is used to identify a source error. With a correct
             error mapping table it is not possible that this counter
             increases."
        ::= { appCountryStatsEntry 114 }

    appCountryStatsCntOutsideAtRoutingError OBJECT-TYPE
        SYNTAX  Counter
        ACCESS  read-write
        STATUS  mandatory
        DESCRIPTION
            "Counter specifying the number of times an AT/SM towards
            an application resulted in a routing error. The error
            mapping table is used to identify a routing error."
        ::= { appCountryStatsEntry 115 }

    appCountryStatsCntOutsideAtDestinationTemporaryError OBJECT-TYPE
        SYNTAX  Counter
        ACCESS  read-write
        STATUS  mandatory
        DESCRIPTION
            "Counter specifying the number of times an AT/SM towards
            an application resulted in a temporary error. The error
            mapping table is used to identify a temporary error."
        ::= { appCountryStatsEntry 116 }

    appCountryStatsCntOutsideAtDestinationPermanentRecipientError OBJECT-TYPE
        SYNTAX  Counter
        ACCESS  read-write
        STATUS  mandatory
        DESCRIPTION
            "Counter specifying the number of times an AT/SM towards
            an application resulted in a permanent recipient error. 
            The error mapping table is used to identify a permanent 
            recipient error."
        ::= { appCountryStatsEntry 117 }

    appCountryStatsCntOutsideAtDestinationPermanentMessageError OBJECT-TYPE
        SYNTAX  Counter
        ACCESS  read-write
        STATUS  mandatory
        DESCRIPTION
            "Counter specifying the number of times an AT/SM towards
            an application resulted in a permanent message error. The 
            error mapping table is used to identify a permanent message 
            error."
        ::= { appCountryStatsEntry 118 }

    appMobNetworkStatsTable OBJECT-TYPE
        SYNTAX  SEQUENCE OF AppMobNetworkStatsEntry
        ACCESS  not-accessible
        STATUS  mandatory
        DESCRIPTION
            "A table containing AO/MT statistics per mobile network and per
            application."
        ::= { sms 43 }

    appMobNetworkStatsEntry OBJECT-TYPE
        SYNTAX  AppMobNetworkStatsEntry
        ACCESS  not-accessible
        STATUS  mandatory
        DESCRIPTION
            "Table entry containing AO/MT statistics for one specific mobile
            network and specific application."
        INDEX   { appMobNetworkStatsIndex1, appMobNetworkStatsIndex2 }
        ::= { appMobNetworkStatsTable 1 }

    AppMobNetworkStatsEntry ::=
        SEQUENCE {
            appMobNetworkStatsIndex1                MobNetworkTableIndex,
            appMobNetworkStatsIndex2                ApplicationTableIndex,
            appMobNetworkStatsMoTotalCounter     Counter,
            appMobNetworkStatsMoSuccessfulCounter Counter,
            appMobNetworkStatsMoTimeoutCounter   Counter,
            appMobNetworkStatsMoDroppedCounter   Counter,
            appMobNetworkStatsMoDiscardWithNakCounter Counter,
            appMobNetworkStatsMoRejectedByTprCounter Counter,
            appMobNetworkStatsMoRejectedByAppCounter Counter,
            appMobNetworkStatsMoUnknownResultCounter Counter,
            appMobNetworkStatsMoSysFailErrorCounter Counter,
            appMobNetworkStatsMoDataMisErrorCounter Counter,
            appMobNetworkStatsMoUnexpDataValErrorCounter Counter,
            appMobNetworkStatsMoFacNotSuppErrorCounter Counter,
            appMobNetworkStatsMoUnkScErrorCounter Counter,
            appMobNetworkStatsMoScCongErrorCounter Counter,
            appMobNetworkStatsMoInvSmeAddrErrorCounter Counter,
            appMobNetworkStatsMoSubNotScSubErrorCounter Counter,
            appMobNetworkStatsMoOtherErrorsCounter Counter,
            appMobNetworkStatsMoTcapAbortedCounter Counter,
            appMobNetworkStatsMoSccpAbortedCounter Counter,
            appMobNetworkStatsMtTotalCounter     Counter,
            appMobNetworkStatsMtSuccessfulCounter Counter,
            appMobNetworkStatsMtTimeoutCounter   Counter,
            appMobNetworkStatsMtAbsSubErrorCounter Counter,
            appMobNetworkStatsMtSysFailErrorCounter Counter,
            appMobNetworkStatsMtDataMisErrorCounter Counter,
            appMobNetworkStatsMtUnexpDataValErrorCounter Counter,
            appMobNetworkStatsMtFacNotSuppErrorCounter Counter,
            appMobNetworkStatsMtUnidenSubErrorCounter Counter,
            appMobNetworkStatsMtIllSubErrorCounter Counter,
            appMobNetworkStatsMtIllEquipErrorCounter Counter,
            appMobNetworkStatsMtSubBusyForMtSmErrorCounter Counter,
            appMobNetworkStatsMtInvSmeAddrErrorCounter Counter,
            appMobNetworkStatsMtEquipProtErrorCounter Counter,
            appMobNetworkStatsMtEquipNotSmEquipErrorCounter Counter,
            appMobNetworkStatsMtMemCapExcErrorCounter Counter,
            appMobNetworkStatsMtOtherErrorsCounter Counter,
            appMobNetworkStatsMtTcapAbortedCounter Counter,
            appMobNetworkStatsMtSccpAbortedCounter Counter,
            appMobNetworkStatsMtFallbackToVersion2Counter Counter,
            appMobNetworkStatsMtFallbackToVersion1Counter Counter,
            appMobNetworkStatsMtAlternatePathUsedCounter Counter,
            appMobNetworkStatsMtAlternatePathNotUsedCounter Counter,
            appMobNetworkStatsSriSmTotalCounter  Counter,
            appMobNetworkStatsSriSmSuccessCounter Counter,
            appMobNetworkStatsSriSmTimeoutCounter Counter,
            appMobNetworkStatsSriSmSysFailErrorCounter Counter,
            appMobNetworkStatsSriSmDataMisErrorCounter Counter,
            appMobNetworkStatsSriSmUnexpDataValErrorCounter Counter,
            appMobNetworkStatsSriSmFacNotSuppErrorCounter Counter,
            appMobNetworkStatsSriSmUnkSubErrorCounter Counter,
            appMobNetworkStatsSriSmAbsSubErrorCounter Counter,
            appMobNetworkStatsSriSmCallBarredErrorCounter Counter,
            appMobNetworkStatsSriSmTeleServNotProvErrorCounter Counter,
            appMobNetworkStatsSriSmOtherErrorsCounter Counter,
            appMobNetworkStatsSriSmTcapAbortedCounter Counter,
            appMobNetworkStatsSriSmSccpAbortedCounter Counter,
            appMobNetworkStatsSriSmFallbackToVersion2Counter Counter,
            appMobNetworkStatsSriSmFallbackToVersion1Counter Counter,
            appMobNetworkStatsRepStsTotalCounter Counter,
            appMobNetworkStatsRepStsSuccessCounter Counter,
            appMobNetworkStatsRepStsTimeoutCounter Counter,
            appMobNetworkStatsRepStsSysFailErrorCounter Counter,
            appMobNetworkStatsRepStsDataMisErrorCounter Counter,
            appMobNetworkStatsRepStsUnexpDataValErrorCounter Counter,
            appMobNetworkStatsRepStsUnkSubErrorCounter Counter,
            appMobNetworkStatsRepStsMsgWaitListFullErrorCounter Counter,
            appMobNetworkStatsRepStsOtherErrorsCounter Counter,
            appMobNetworkStatsRepStsTcapAbortedCounter Counter,
            appMobNetworkStatsRepStsSccpAbortedCounter Counter,
            appMobNetworkStatsRepStsFallbackToVersion2Counter Counter,
            appMobNetworkStatsRepStsFallbackToVersion1Counter Counter,
            appMobNetworkStatsCntInsideAoTotal           Counter,
            appMobNetworkStatsCntInsideAoSuccess         Counter,
            appMobNetworkStatsCntInsideAoSourceError     Counter,
            appMobNetworkStatsCntInsideAoRoutingError    Counter,
            appMobNetworkStatsCntInsideAoDestinationTemporaryError Counter,
            appMobNetworkStatsCntInsideAoDestinationPermanentRecipientError Counter,
            appMobNetworkStatsCntInsideAoDestinationPermanentMessageError Counter,
            appMobNetworkStatsCntInsideAtTotal           Counter,
            appMobNetworkStatsCntInsideAtSuccess         Counter,
            appMobNetworkStatsCntInsideAtSourceError     Counter,
            appMobNetworkStatsCntInsideAtRoutingError    Counter,
            appMobNetworkStatsCntInsideAtDestinationTemporaryError Counter,
            appMobNetworkStatsCntInsideAtDestinationPermanentRecipientError Counter,
            appMobNetworkStatsCntInsideAtDestinationPermanentMessageError Counter,
            appMobNetworkStatsCntOutsideAoTotal          Counter,
            appMobNetworkStatsCntOutsideAoSuccess        Counter,
            appMobNetworkStatsCntOutsideAoSourceError    Counter,
            appMobNetworkStatsCntOutsideAoRoutingError   Counter,
            appMobNetworkStatsCntOutsideAoDestinationTemporaryError Counter,
            appMobNetworkStatsCntOutsideAoDestinationPermanentRecipientError Counter,
            appMobNetworkStatsCntOutsideAoDestinationPermanentMessageError Counter,
            appMobNetworkStatsCntOutsideAtTotal          Counter,
            appMobNetworkStatsCntOutsideAtSuccess        Counter,
            appMobNetworkStatsCntOutsideAtSourceError    Counter,
            appMobNetworkStatsCntOutsideAtRoutingError   Counter,
            appMobNetworkStatsCntOutsideAtDestinationTemporaryError Counter,
            appMobNetworkStatsCntOutsideAtDestinationPermanentRecipientError Counter,
            appMobNetworkStatsCntOutsideAtDestinationPermanentMessageError Counter
        }

    appMobNetworkStatsIndex1 OBJECT-TYPE
        SYNTAX  MobNetworkTableIndex
        ACCESS  read-write
        STATUS  mandatory
        DESCRIPTION
            "Index of entry in table containing AO/MT statistics per mobile
            network and per application. This index is actually a reference to
            the related mobile network. Its value is equal to the index of the
            mobile network entry that specifies the mobile network."
        ::= { appMobNetworkStatsEntry 1 }

    appMobNetworkStatsIndex2 OBJECT-TYPE
        SYNTAX  ApplicationTableIndex
        ACCESS  read-write
        STATUS  mandatory
        DESCRIPTION
            "Index of entry in table containing AO/MT statistics per mobile
            network and per application. This index is actually a reference to
            the related application. Its value is equal to the index of the
            mobile network entry that specifies the application."
        ::= { appMobNetworkStatsEntry 2 }

    appMobNetworkStatsMoTotalCounter OBJECT-TYPE
        SYNTAX  Counter
        ACCESS  read-write
        STATUS  mandatory
        DESCRIPTION
            "Counter specifying the total number of times an MO/SM was
            received."
        ::= { appMobNetworkStatsEntry 11 }


    appMobNetworkStatsMoSuccessfulCounter OBJECT-TYPE
        SYNTAX  Counter
        ACCESS  read-write
        STATUS  mandatory
        DESCRIPTION
            "Counter specifying the number of times an MO/SM was successfully
             routed to its destination. The following events result in
             incrementing of this counter:
             - receiving a MO/SM matching a rule with action equal to
               discardWithAck
             - receiving an ACK from an application as result of an MO/SM
               being routed to the application
             - receiving an ACK from an SMSC as result of an MO/SM being
               routed to the SMSC."
        ::= { appMobNetworkStatsEntry 12 }

    appMobNetworkStatsMoTimeoutCounter OBJECT-TYPE
        SYNTAX  Counter
        ACCESS  read-write
        STATUS  mandatory
        DESCRIPTION
            "Counter specifying the number of times that routing an MO/SM to
            its destination resulted in a timeout. The following events
            result in incrementing of this counter:
             - not receiving a response from an application on an MO/SM
               being routed to the application within the maximum response
               time
             - receiving an ACK from an SMSC as result of an MO/SM being
               routed to an SMSC within the maximum response time."
        ::= { appMobNetworkStatsEntry 13 }

    appMobNetworkStatsMoDroppedCounter OBJECT-TYPE
        SYNTAX  Counter
        ACCESS  read-write
        STATUS  mandatory
        DESCRIPTION
            "Counter specifying the number of times that an MO/SM has not
            been routed to its destination due to decimation (this is only
            applicable when routing to an application)."
        ::= { appMobNetworkStatsEntry 14 }

    appMobNetworkStatsMoDiscardWithNakCounter OBJECT-TYPE
        SYNTAX  Counter
        ACCESS  read-write
        STATUS  mandatory
        DESCRIPTION
            "Counter specifying the number of times that TPR has rejected an
            MO/SM as result of a routing rule with action equal to
            discardWithNak or because none of the routing rules match."
        ::= { appMobNetworkStatsEntry 15 }

    appMobNetworkStatsMoRejectedByTprCounter OBJECT-TYPE
        SYNTAX  Counter
        ACCESS  read-write
        STATUS  mandatory
        DESCRIPTION
            "Counter specifying the number of times that TPR has rejected an
            MO/SM as result of incorrect syntax of the MO/SM."
        ::= { appMobNetworkStatsEntry 16 }

    appMobNetworkStatsMoRejectedByAppCounter OBJECT-TYPE
        SYNTAX  Counter
        ACCESS  read-write
        STATUS  mandatory
        DESCRIPTION
            "Counter specifying the number of times that routing to an
            application resulted in the application rejecting the MO/SM by
            sending a NAK."
        ::= { appMobNetworkStatsEntry 17 }

    appMobNetworkStatsMoUnknownResultCounter OBJECT-TYPE
        SYNTAX  Counter
        ACCESS  read-write
        STATUS  mandatory
        DESCRIPTION
            "Counter specifying the number of times that the result of routing
            an MO/SM to its destination could not be retrieved (this is only
            applicable when using optimal routing towards an SMSC)."
        ::= { appMobNetworkStatsEntry 18 }

    appMobNetworkStatsMoSysFailErrorCounter OBJECT-TYPE
        SYNTAX  Counter
        ACCESS  read-write
        STATUS  mandatory
        DESCRIPTION
            "Counter specifying the number of times that routing to an SMSC
            resulted in the SMSC rejecting the MO/SM with a System-Failure
            error on MAP level."
        ::= { appMobNetworkStatsEntry 19 }

    appMobNetworkStatsMoDataMisErrorCounter OBJECT-TYPE
        SYNTAX  Counter
        ACCESS  read-write
        STATUS  mandatory
        DESCRIPTION
            "Counter specifying the number of times that routing to an SMSC
            resulted in the SMSC rejecting the MO/SM with a Data-Missing
            error on MAP level."
        ::= { appMobNetworkStatsEntry 20 }

    appMobNetworkStatsMoUnexpDataValErrorCounter OBJECT-TYPE
        SYNTAX  Counter
        ACCESS  read-write
        STATUS  mandatory
        DESCRIPTION
            "Counter specifying the number of times that routing to an SMSC
            resulted in the SMSC rejecting the MO/SM with a Unexpected-Data-
            Value error on MAP level."
        ::= { appMobNetworkStatsEntry 21 }

    appMobNetworkStatsMoFacNotSuppErrorCounter OBJECT-TYPE
        SYNTAX  Counter
        ACCESS  read-write
        STATUS  mandatory
        DESCRIPTION
            "Counter specifying the number of times that routing to an SMSC
            resulted in the SMSC rejecting the MO/SM with a Facility-Not-
            Supported error on MAP level."
        ::= { appMobNetworkStatsEntry 22 }

    appMobNetworkStatsMoUnkScErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Unknown-
            Service-Centre."
        ::= { appMobNetworkStatsEntry 23 }

    appMobNetworkStatsMoScCongErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to SC-
            Congestion."
        ::= { appMobNetworkStatsEntry 24 }

    appMobNetworkStatsMoInvSmeAddrErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Invalid-
            SME-Address."
        ::= { appMobNetworkStatsEntry 25 }

    appMobNetworkStatsMoSubNotScSubErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to
            Subscriber-Not-SC-Subscriber."
        ::= { appMobNetworkStatsEntry 26 }

    appMobNetworkStatsMoOtherErrorsCounter OBJECT-TYPE
        SYNTAX  Counter
        ACCESS  read-write
        STATUS  mandatory
        DESCRIPTION
            "Counter specifying the number of times that routing to an SMSC
            resulted in the SMSC rejecting the MO/SM with another MAP error
            (or possibly a failure cause) than specified for the
            other MO counters."
        ::= { appMobNetworkStatsEntry 27 }

    appMobNetworkStatsMoTcapAbortedCounter OBJECT-TYPE
        SYNTAX  Counter
        ACCESS  read-write
        STATUS  mandatory
        DESCRIPTION
            "Counter specifying the number of times that routing to an SMSC
            resulted in the SMSC rejecting the MO/SM by sending a TC-ABORT
            on TCAP level."
        ::= { appMobNetworkStatsEntry 28 }

    appMobNetworkStatsMoSccpAbortedCounter OBJECT-TYPE
        SYNTAX  Counter
        ACCESS  read-write
        STATUS  mandatory
        DESCRIPTION
            "Counter specifying the number of times that routing to an SMSC
            resulted in the SMSC rejecting the MO/SM by sending a UDTS on
            SCCP level."
        ::= { appMobNetworkStatsEntry 29 }

    appMobNetworkStatsMtTotalCounter OBJECT-TYPE
        SYNTAX  Counter
        ACCESS  read-write
        STATUS  mandatory
        DESCRIPTION
            "Counter specifying the total number of times an MT/SM was issued
            by the TPR. This counter is incremented whenever:
            - the TPR issues a MT/SM on behalf of an application that is
              directly connected to the TPR
            - the TPR receives all MT/SM's from an SMSC and directs the MT/SM
              to its destination."
        ::= { appMobNetworkStatsEntry 30 }

    appMobNetworkStatsMtSuccessfulCounter OBJECT-TYPE
        SYNTAX  Counter
        ACCESS  read-write
        STATUS  mandatory
        DESCRIPTION
            "Counter specifying the number of times an MT/SM was successfully
            delivered."
        ::= { appMobNetworkStatsEntry 31 }

    appMobNetworkStatsMtTimeoutCounter OBJECT-TYPE
        SYNTAX  Counter
        ACCESS  read-write
        STATUS  mandatory
        DESCRIPTION
            "Counter specifying the number of times that delivering an MT/SM
            resulted in a timeout."
        ::= { appMobNetworkStatsEntry 32 }

    appMobNetworkStatsMtAbsSubErrorCounter OBJECT-TYPE
        SYNTAX  Counter
        ACCESS  read-write
        STATUS  mandatory
        DESCRIPTION
            "Counter specifying the number of times that delivering an MT/SM
            resulted in an Absent-Subscriber error."
        ::= { appMobNetworkStatsEntry 33 }

    appMobNetworkStatsMtSysFailErrorCounter OBJECT-TYPE
        SYNTAX  Counter
        ACCESS  read-write
        STATUS  mandatory
        DESCRIPTION
            "Counter specifying the number of times that delivering an MT/SM
            resulted in an System-Failure error."
        ::= { appMobNetworkStatsEntry 34 }

    appMobNetworkStatsMtDataMisErrorCounter OBJECT-TYPE
        SYNTAX  Counter
        ACCESS  read-write
        STATUS  mandatory
        DESCRIPTION
            "Counter specifying the number of times that delivering an MT/SM
            resulted in an Data-Missing error."
        ::= { appMobNetworkStatsEntry 35 }

    appMobNetworkStatsMtUnexpDataValErrorCounter OBJECT-TYPE
        SYNTAX  Counter
        ACCESS  read-write
        STATUS  mandatory
        DESCRIPTION
            "Counter specifying the number of times that delivering an MT/SM
            resulted in an Unexpected-Data-Value error."
        ::= { appMobNetworkStatsEntry 36 }

    appMobNetworkStatsMtFacNotSuppErrorCounter OBJECT-TYPE
        SYNTAX  Counter
        ACCESS  read-write
        STATUS  mandatory
        DESCRIPTION
            "Counter specifying the number of times that delivering an MT/SM
            resulted in an Facility-Not-Supported error."
        ::= { appMobNetworkStatsEntry 37 }

    appMobNetworkStatsMtUnidenSubErrorCounter OBJECT-TYPE
        SYNTAX  Counter
        ACCESS  read-write
        STATUS  mandatory
        DESCRIPTION
            "Counter specifying the number of times that delivering an MT/SM
            resulted in an Unidentified-Subscriber error."
        ::= { appMobNetworkStatsEntry 38 }

    appMobNetworkStatsMtIllSubErrorCounter OBJECT-TYPE
        SYNTAX  Counter
        ACCESS  read-write
        STATUS  mandatory
        DESCRIPTION
            "Counter specifying the number of times that delivering an MT/SM
            resulted in an Illegal-Subscriber error."
        ::= { appMobNetworkStatsEntry 39 }

    appMobNetworkStatsMtIllEquipErrorCounter OBJECT-TYPE
        SYNTAX  Counter
        ACCESS  read-write
        STATUS  mandatory
        DESCRIPTION
            "Counter specifying the number of times that delivering an MT/SM
            resulted in an Illegal-Equipment error."
        ::= { appMobNetworkStatsEntry 40 }

    appMobNetworkStatsMtSubBusyForMtSmErrorCounter OBJECT-TYPE
        SYNTAX  Counter
        ACCESS  read-write
        STATUS  mandatory
        DESCRIPTION
            "Counter specifying the number of times that delivering an MT/SM
            resulted in an Subscriber-Busy-For-MT-SMS error."
        ::= { appMobNetworkStatsEntry 41 }

    appMobNetworkStatsMtInvSmeAddrErrorCounter OBJECT-TYPE
        SYNTAX  Counter
        ACCESS  read-write
        STATUS  mandatory
        DESCRIPTION
            "Counter specifying the number of times that delivering an MT/SM
            resulted in a SM-Delivery-Failure error with failure cause equal
            to Invalid-SME-Address."
        ::= { appMobNetworkStatsEntry 42 }

    appMobNetworkStatsMtEquipProtErrorCounter OBJECT-TYPE
        SYNTAX  Counter
        ACCESS  read-write
        STATUS  mandatory
        DESCRIPTION
            "Counter specifying the number of times that delivering an MT/SM
            resulted in a SM-Delivery-Failure error with failure cause equal
            to Equipment-Protocol-Error."
        ::= { appMobNetworkStatsEntry 43 }

    appMobNetworkStatsMtEquipNotSmEquipErrorCounter OBJECT-TYPE
        SYNTAX  Counter
        ACCESS  read-write
        STATUS  mandatory
        DESCRIPTION
            "Counter specifying the number of times that delivering an MT/SM
            resulted in a SM-Delivery-Failure error with failure cause equal
            to Equipment-Not-SM-equipped."
        ::= { appMobNetworkStatsEntry 44 }

    appMobNetworkStatsMtMemCapExcErrorCounter OBJECT-TYPE
        SYNTAX  Counter
        ACCESS  read-write
        STATUS  mandatory
        DESCRIPTION
            "Counter specifying the number of times that delivering an MT/SM
            resulted in a SM-Delivery-Failure error with failure cause equal
            to Memory-Capacity-Exceeded."
        ::= { appMobNetworkStatsEntry 45 }

    appMobNetworkStatsMtOtherErrorsCounter OBJECT-TYPE
        SYNTAX  Counter
        ACCESS  read-write
        STATUS  mandatory
        DESCRIPTION
            "Counter specifying the number of times that delivering an MT/SM
            resulted in another MAP error (or possibly a failure cause) than
            specified for the other MT counters."
        ::= { appMobNetworkStatsEntry 46 }

    appMobNetworkStatsMtTcapAbortedCounter OBJECT-TYPE
        SYNTAX  Counter
        ACCESS  read-write
        STATUS  mandatory
        DESCRIPTION
            "Counter specifying the number of times that delivering an MT/SM
            resulted in the MSC/SGSN rejecting the MT/SM by sending a TC-ABORT
            on TCAP level."
        ::= { appMobNetworkStatsEntry 47 }

    appMobNetworkStatsMtSccpAbortedCounter OBJECT-TYPE
        SYNTAX  Counter
        ACCESS  read-write
        STATUS  mandatory
        DESCRIPTION
            "Counter specifying the number of times that delivering an MT/SM
            resulted in the MSC/SGSN rejecting the MT/SM by sending a UDTS on
            SCCP level."
        ::= { appMobNetworkStatsEntry 48 }

    appMobNetworkStatsMtFallbackToVersion2Counter OBJECT-TYPE
        SYNTAX  Counter
        ACCESS  read-write
        STATUS  mandatory
        DESCRIPTION
            "Counter specifying the number of times that delivering an MT/SM
            resulted in the MSC/SGSN requesting to fallback to MAP version 2."
        ::= { appMobNetworkStatsEntry 49 }

    appMobNetworkStatsMtFallbackToVersion1Counter OBJECT-TYPE
        SYNTAX  Counter
        ACCESS  read-write
        STATUS  mandatory
        DESCRIPTION
            "Counter specifying the number of times that delivering an MT/SM
            resulted in the MSC/SGSN requesting to fallback to MAP version 1."
        ::= { appMobNetworkStatsEntry 50 }

    appMobNetworkStatsMtAlternatePathUsedCounter OBJECT-TYPE
        SYNTAX  Counter
        ACCESS  read-write
        STATUS  mandatory
        DESCRIPTION
            "Counter specifying the number of times that for delivering an
            MT/SM both paths (through MSC and through SGSN) were available
            and that delivery on the primary path failed (and the alternate
            path was thus used)."
        ::= { appMobNetworkStatsEntry 51 }

    appMobNetworkStatsMtAlternatePathNotUsedCounter OBJECT-TYPE
        SYNTAX  Counter
        ACCESS  read-write
        STATUS  mandatory
        DESCRIPTION
            "Counter specifying the number of times that for delivering an
            MT/SM both paths (through MSC and through SGSN) were available
            and that delivery on the primary path succeeded (and the
            alternate path was thus not used)."
        ::= { appMobNetworkStatsEntry 52 }

    appMobNetworkStatsSriSmTotalCounter OBJECT-TYPE
        SYNTAX  Counter
        ACCESS  read-write
        STATUS  mandatory
        DESCRIPTION
            "Counter specifying the total number of times a Send-Routing-Info-
            For-SM operation was issued
            by the TPR. This counter is incremented whenever:
            - the TPR issues a Send-Routing-Info-For-SM operation as part of
              the delivery of a MT/SM that was sent by an application that is
              directly connected to the TPR
            - the TPR receives all Send-Routing-Info-For-SM operations from
              an SMSC and directs the opeation to its destination."
        ::= { appMobNetworkStatsEntry 53 }

    appMobNetworkStatsSriSmSuccessCounter OBJECT-TYPE
        SYNTAX  Counter
        ACCESS  read-write
        STATUS  mandatory
        DESCRIPTION
            "Counter specifying the number of times a Send-Routing-Info-For-
            SM operation was successfully issued."
        ::= { appMobNetworkStatsEntry 54 }

    appMobNetworkStatsSriSmTimeoutCounter OBJECT-TYPE
        SYNTAX  Counter
        ACCESS  read-write
        STATUS  mandatory
        DESCRIPTION
            "Counter specifying the number of times that issueing a
            Send-Routing- Info-For-SM operation resulted in a timeout."
        ::= { appMobNetworkStatsEntry 55 }

    appMobNetworkStatsSriSmSysFailErrorCounter OBJECT-TYPE
        SYNTAX  Counter
        ACCESS  read-write
        STATUS  mandatory
        DESCRIPTION
            "Counter specifying the number of times that issueing a
            Send-Routing- Info-For-SM operation resulted in a System-Failure
            error."
        ::= { appMobNetworkStatsEntry 56 }

    appMobNetworkStatsSriSmDataMisErrorCounter OBJECT-TYPE
        SYNTAX  Counter
        ACCESS  read-write
        STATUS  mandatory
        DESCRIPTION
            "Counter specifying the number of times that issueing a
            Send-Routing- Info-For-SM operation resulted in a Data-Missing
            error."
        ::= { appMobNetworkStatsEntry 57 }

    appMobNetworkStatsSriSmUnexpDataValErrorCounter OBJECT-TYPE
        SYNTAX  Counter
        ACCESS  read-write
        STATUS  mandatory
        DESCRIPTION
            "Counter specifying the number of times that issueing a
            Send-Routing- Info-For-SM operation resulted in a
            Unexpected-Data-Value error."
        ::= { appMobNetworkStatsEntry 58 }

    appMobNetworkStatsSriSmFacNotSuppErrorCounter OBJECT-TYPE
        SYNTAX  Counter
        ACCESS  read-write
        STATUS  mandatory
        DESCRIPTION
            "Counter specifying the number of times that issueing a
            Send-Routing- Info-For-SM operation resulted in a
            Facility-Not-Supported error."
        ::= { appMobNetworkStatsEntry 59 }

    appMobNetworkStatsSriSmUnkSubErrorCounter OBJECT-TYPE
        SYNTAX  Counter
        ACCESS  read-write
        STATUS  mandatory
        DESCRIPTION
            "Counter specifying the number of times that issueing a
            Send-Routing- Info-For-SM operation resulted in a
            Unknown-Subscriber error."
        ::= { appMobNetworkStatsEntry 60 }

    appMobNetworkStatsSriSmAbsSubErrorCounter OBJECT-TYPE
        SYNTAX  Counter
        ACCESS  read-write
        STATUS  mandatory
        DESCRIPTION
            "Counter specifying the number of times that issueing a
            Send-Routing- Info-For-SM operation resulted in a
            Absent-Subscriber error."
        ::= { appMobNetworkStatsEntry 61 }

    appMobNetworkStatsSriSmCallBarredErrorCounter OBJECT-TYPE

        SYNTAX  Counter
        ACCESS  read-write
        STATUS  mandatory
        DESCRIPTION
            "Counter specifying the number of times that issueing a
            Send-Routing- Info-For-SM operation resulted in a Call-Barred
            error."
        ::= { appMobNetworkStatsEntry 62 }

    appMobNetworkStatsSriSmTeleServNotProvErrorCounter OBJECT-TYPE
        SYNTAX  Counter
        ACCESS  read-write
        STATUS  mandatory
        DESCRIPTION
            "Counter specifying the number of times that issueing a
            Send-Routing- Info-For-SM operation resulted in a
            Teleservice-Not-Provisioned error."
        ::= { appMobNetworkStatsEntry 63 }

    appMobNetworkStatsSriSmOtherErrorsCounter OBJECT-TYPE
        SYNTAX  Counter
        ACCESS  read-write
        STATUS  mandatory
        DESCRIPTION
            "Counter specifying the number of times that issueing a
            Send-Routing- Info-For-SM operation resulted in another error
            than specified for the other Send-Routing-Info-For-SM counters."
        ::= { appMobNetworkStatsEntry 64 }

    appMobNetworkStatsSriSmTcapAbortedCounter OBJECT-TYPE
        SYNTAX  Counter
        ACCESS  read-write
        STATUS  mandatory
        DESCRIPTION
            "Counter specifying the number of times that issueing a
            Send-Routing- Info-For-SM operation resulted in the HLR rejecting
            the operation by sending a TC-ABORT on TCAP level."
        ::= { appMobNetworkStatsEntry 65 }

    appMobNetworkStatsSriSmSccpAbortedCounter OBJECT-TYPE
        SYNTAX  Counter
        ACCESS  read-write
        STATUS  mandatory
        DESCRIPTION
            "Counter specifying the number of times that issueing a
            Send-Routing- Info-For-SM operation resulted in the HLR rejecting
            the operation by sending a UDTS on SCCP level."
        ::= { appMobNetworkStatsEntry 66 }

    appMobNetworkStatsSriSmFallbackToVersion2Counter OBJECT-TYPE
        SYNTAX  Counter
        ACCESS  read-write
        STATUS  mandatory
        DESCRIPTION
            "Counter specifying the number of times that issueing a
            Send-Routing- Info-For-SM operation resulted in the HLR
            requesting to fallback to MAP version 2."
        ::= { appMobNetworkStatsEntry 67 }

    appMobNetworkStatsSriSmFallbackToVersion1Counter OBJECT-TYPE
        SYNTAX  Counter
        ACCESS  read-write
        STATUS  mandatory
        DESCRIPTION
            "Counter specifying the number of times that issueing a
            Send-Routing- Info-For-SM operation resulted in the HLR
            requesting to fallback to MAP version 1."
        ::= { appMobNetworkStatsEntry 68 }

    appMobNetworkStatsRepStsTotalCounter OBJECT-TYPE
        SYNTAX  Counter
        ACCESS  read-write
        STATUS  mandatory
        DESCRIPTION
            "Counter specifying the total number of times a Report-SM-
            Delivery-Status operation was issued
            by the TPR. This counter is incremented whenever:
            - the TPR issues a Report-SM-Delivery-Status operation as part of
              the delivery of a MT/SM that was sent by an application that is
              directly connected to the TPR
            - the TPR receives all Report-SM-Delivery-Status operations from
              an SMSC and directs the opeation to its destination."
        ::= { appMobNetworkStatsEntry 69 }

    appMobNetworkStatsRepStsSuccessCounter OBJECT-TYPE
        SYNTAX  Counter
        ACCESS  read-write
        STATUS  mandatory
        DESCRIPTION
            "Counter specifying the number of times a Report-SM-Delivery-
            Status operation was successfully issued."
        ::= { appMobNetworkStatsEntry 70 }

    appMobNetworkStatsRepStsTimeoutCounter OBJECT-TYPE
        SYNTAX  Counter
        ACCESS  read-write
        STATUS  mandatory
        DESCRIPTION
            "Counter specifying the number of times that issueing a Report-SM-
            Delivery-Status operation resulted in a timeout."
        ::= { appMobNetworkStatsEntry 71 }


    appMobNetworkStatsRepStsSysFailErrorCounter OBJECT-TYPE
        SYNTAX  Counter
        ACCESS  read-write
        STATUS  mandatory
        DESCRIPTION
            "Counter specifying the number of times that issueing a Report-SM-
            Delivery-Status operation resulted in a System-Failure error."
        ::= { appMobNetworkStatsEntry 72 }

    appMobNetworkStatsRepStsDataMisErrorCounter OBJECT-TYPE
        SYNTAX  Counter
        ACCESS  read-write
        STATUS  mandatory
        DESCRIPTION
            "Counter specifying the number of times that issueing a Report-SM-
            Delivery-Status operation resulted in a Data-Missing error."
        ::= { appMobNetworkStatsEntry 73 }

    appMobNetworkStatsRepStsUnexpDataValErrorCounter OBJECT-TYPE
        SYNTAX  Counter
        ACCESS  read-write
        STATUS  mandatory
        DESCRIPTION
            "Counter specifying the number of times that issueing a Report-SM-
            Delivery-Status operation resulted in a Unexpected-Data-Value
            error."
        ::= { appMobNetworkStatsEntry 74 }

    appMobNetworkStatsRepStsUnkSubErrorCounter OBJECT-TYPE
        SYNTAX  Counter
        ACCESS  read-write
        STATUS  mandatory
        DESCRIPTION
           "Counter specifying the number of times that issueing a Report-SM-
            Delivery-Status operation resulted in a Unknown-Subscriber
            error."
        ::= { appMobNetworkStatsEntry 75 }

    appMobNetworkStatsRepStsMsgWaitListFullErrorCounter OBJECT-TYPE
        SYNTAX  Counter
        ACCESS  read-write
        STATUS  mandatory
        DESCRIPTION
           "Counter specifying the number of times that issueing a Report-SM-
            Delivery-Status operation resulted in a Message-Waiting-List-Full
            error."
        ::= { appMobNetworkStatsEntry 76 }

    appMobNetworkStatsRepStsOtherErrorsCounter OBJECT-TYPE
        SYNTAX  Counter
        ACCESS  read-write
        STATUS  mandatory
        DESCRIPTION
            "Counter specifying the number of times that issueing a
            Report-SM- Delivery-Status operation resulted in in another error
            than specified for the other Report-SM-Delivery-Status counters."
        ::= { appMobNetworkStatsEntry 77 }

    appMobNetworkStatsRepStsTcapAbortedCounter OBJECT-TYPE
        SYNTAX  Counter
        ACCESS  read-write
        STATUS  mandatory
        DESCRIPTION
            "Counter specifying the number of times that issueing a Report-SM-
            Delivery-Status operation resulted in the HLR rejecting the
            operation by sending a TC-ABORT on TCAP level."
        ::= { appMobNetworkStatsEntry 78 }

    appMobNetworkStatsRepStsSccpAbortedCounter OBJECT-TYPE
        SYNTAX  Counter
        ACCESS  read-write
        STATUS  mandatory
        DESCRIPTION
            "Counter specifying the number of times that issueing a Report-SM-
            Delivery-Status operation resulted in the HLR rejecting the
            operation by sending a UDTS on SCCP level."
        ::= { appMobNetworkStatsEntry 79 }

    appMobNetworkStatsRepStsFallbackToVersion2Counter OBJECT-TYPE
        SYNTAX  Counter
        ACCESS  read-write
        STATUS  mandatory
        DESCRIPTION
            "Counter specifying the number of times that issueing a Report-SM-
            Delivery-Status operation resulted in the HLR requesting to
            fallback to MAP version 2."
        ::= { appMobNetworkStatsEntry 80 }

    appMobNetworkStatsRepStsFallbackToVersion1Counter OBJECT-TYPE
        SYNTAX  Counter
        ACCESS  read-write
        STATUS  mandatory
        DESCRIPTION
            "Counter specifying the number of times that issueing a Report-SM-
            Delivery-Status operation resulted in the HLR requesting to
            fallback to MAP version 1."
        ::= { appMobNetworkStatsEntry 81 }

    appMobNetworkStatsCntInsideAoTotal OBJECT-TYPE
        SYNTAX  Counter
        ACCESS  read-write
        STATUS  mandatory
        DESCRIPTION
            "Counter specifying the total number of times an AO/SM was
            sent towards a service centre."
        ::= { appMobNetworkStatsEntry 91 }

    appMobNetworkStatsCntInsideAoSuccess OBJECT-TYPE
        SYNTAX  Counter
        ACCESS  read-write
        STATUS  mandatory
        DESCRIPTION
            "Counter specifying the number of times an AO/SM was
            successfully routed to its destination."
        ::= { appMobNetworkStatsEntry 92 }

    appMobNetworkStatsCntInsideAoSourceError OBJECT-TYPE
        SYNTAX  Counter
        ACCESS  read-write
        STATUS  mandatory
        DESCRIPTION
            "Counter specifying the number of times an AO/SM towards
             a service centre resulted in a source error
             (like a syntax error). The error mapping
             table is used to identify a source error. With a correct
             error mapping table it is not possible that this counter
             increases."
        ::= { appMobNetworkStatsEntry 93 }

    appMobNetworkStatsCntInsideAoRoutingError OBJECT-TYPE
        SYNTAX  Counter
        ACCESS  read-write
        STATUS  mandatory
        DESCRIPTION
            "Counter specifying the number of times an AO/SM towards
            a service centre resulted in a routing error. The error
            mapping table is used to identify a routing error."
        ::= { appMobNetworkStatsEntry 94 }

    appMobNetworkStatsCntInsideAoDestinationTemporaryError OBJECT-TYPE
        SYNTAX  Counter
        ACCESS  read-write
        STATUS  mandatory
        DESCRIPTION
            "Counter specifying the number of times an AO/SM towards
            a service centre resulted in a temporary error. The error
            mapping table is used to identify a temporary error."
        ::= { appMobNetworkStatsEntry 95 }

    appMobNetworkStatsCntInsideAoDestinationPermanentRecipientError OBJECT-TYPE
        SYNTAX  Counter
        ACCESS  read-write
        STATUS  mandatory
        DESCRIPTION
            "Counter specifying the number of times an AO/SM towards
            a service centre resulted in a permanent recipient error. 
            The error mapping table is used to identify a permanent 
            recipient error."
        ::= { appMobNetworkStatsEntry 96 }

    appMobNetworkStatsCntInsideAoDestinationPermanentMessageError OBJECT-TYPE
        SYNTAX  Counter
        ACCESS  read-write
        STATUS  mandatory
        DESCRIPTION
            "Counter specifying the number of times an AO/SM towards
            a service centre resulted in a permanent message error. The 
            error mapping table is used to identify a permanent message 
            error."
        ::= { appMobNetworkStatsEntry 97 }

    appMobNetworkStatsCntInsideAtTotal OBJECT-TYPE
        SYNTAX  Counter
        ACCESS  read-write
        STATUS  mandatory
        DESCRIPTION
            "Counter specifying the total number of times an AT/SM was
            received from a service centre."
        ::= { appMobNetworkStatsEntry 98 }

    appMobNetworkStatsCntInsideAtSuccess OBJECT-TYPE
        SYNTAX  Counter
        ACCESS  read-write
        STATUS  mandatory
        DESCRIPTION
            "Counter specifying the number of times an AT/SM was
            successfully routed to its destination."
        ::= { appMobNetworkStatsEntry 99 }

    appMobNetworkStatsCntInsideAtSourceError OBJECT-TYPE
        SYNTAX  Counter
        ACCESS  read-write
        STATUS  mandatory
        DESCRIPTION
            "Counter specifying the number of times an AT/SM from
             a service centre resulted in a source error
             (like a syntax error). The error mapping
             table is used to identify a source error."
        ::= { appMobNetworkStatsEntry 100 }

    appMobNetworkStatsCntInsideAtRoutingError OBJECT-TYPE
        SYNTAX  Counter
        ACCESS  read-write
        STATUS  mandatory
        DESCRIPTION
            "Counter specifying the number of times an AT/SM from
            a service centre resulted in a routing error. The error
            mapping table is used to identify a routing error."
        ::= { appMobNetworkStatsEntry 101 }

    appMobNetworkStatsCntInsideAtDestinationTemporaryError OBJECT-TYPE
        SYNTAX  Counter
        ACCESS  read-write
        STATUS  mandatory
        DESCRIPTION
            "Counter specifying the number of times an AT/SM from
            a service centre resulted in a temporary error. The error
            mapping table is used to identify a temporary error."
        ::= { appMobNetworkStatsEntry 102 }

    appMobNetworkStatsCntInsideAtDestinationPermanentRecipientError OBJECT-TYPE
        SYNTAX  Counter
        ACCESS  read-write
        STATUS  mandatory
        DESCRIPTION
            "Counter specifying the number of times an AT/SM from
            a service centre resulted in a permanent recipient error. 
            The error mapping table is used to identify a permanent 
            recipient error."
        ::= { appMobNetworkStatsEntry 103 }

    appMobNetworkStatsCntInsideAtDestinationPermanentMessageError OBJECT-TYPE
        SYNTAX  Counter
        ACCESS  read-write
        STATUS  mandatory
        DESCRIPTION
            "Counter specifying the number of times an AT/SM from
            a service centre resulted in a permanent message error. The 
            error mapping table is used to identify a permanent message 
            error."
        ::= { appMobNetworkStatsEntry 104 }

    appMobNetworkStatsCntOutsideAoTotal OBJECT-TYPE
        SYNTAX  Counter
        ACCESS  read-write
        STATUS  mandatory
        DESCRIPTION
            "Counter specifying the total number of times an AO/SM was
            received from an application."
        ::= { appMobNetworkStatsEntry 105 }

    appMobNetworkStatsCntOutsideAoSuccess OBJECT-TYPE
        SYNTAX  Counter
        ACCESS  read-write
        STATUS  mandatory
        DESCRIPTION
            "Counter specifying the number of times an AO/SM was
            successfully routed to its destination."
        ::= { appMobNetworkStatsEntry 106 }

    appMobNetworkStatsCntOutsideAoSourceError OBJECT-TYPE
        SYNTAX  Counter
        ACCESS  read-write
        STATUS  mandatory
        DESCRIPTION
            "Counter specifying the number of times an AO/SM from
             an application resulted in a source error
             (like a syntax error). The error mapping
             table is used to identify a source error."
        ::= { appMobNetworkStatsEntry 107 }

    appMobNetworkStatsCntOutsideAoRoutingError OBJECT-TYPE
        SYNTAX  Counter
        ACCESS  read-write
        STATUS  mandatory
        DESCRIPTION
            "Counter specifying the number of times an AO/SM from
            an application resulted in a routing error. The error
            mapping table is used to identify a routing error."
        ::= { appMobNetworkStatsEntry 108 }

    appMobNetworkStatsCntOutsideAoDestinationTemporaryError OBJECT-TYPE
        SYNTAX  Counter
        ACCESS  read-write
        STATUS  mandatory
        DESCRIPTION
            "Counter specifying the number of times an AO/SM from
            an application resulted in a temporary error. The error
            mapping table is used to identify a temporary error."
        ::= { appMobNetworkStatsEntry 109 }

    appMobNetworkStatsCntOutsideAoDestinationPermanentRecipientError OBJECT-TYPE
        SYNTAX  Counter
        ACCESS  read-write
        STATUS  mandatory
        DESCRIPTION
            "Counter specifying the number of times an AO/SM from
            an application resulted in a permanent recipient error. 
            The error mapping table is used to identify a permanent 
            recipient error."
        ::= { appMobNetworkStatsEntry 110 }

    appMobNetworkStatsCntOutsideAoDestinationPermanentMessageError OBJECT-TYPE
        SYNTAX  Counter
        ACCESS  read-write
        STATUS  mandatory
        DESCRIPTION
            "Counter specifying the number of times an AO/SM from
            an application resulted in a permanent message error. 
            The error mapping table is used to identify a permanent 
            message error."
        ::= { appMobNetworkStatsEntry 111 }

    appMobNetworkStatsCntOutsideAtTotal OBJECT-TYPE
        SYNTAX  Counter
        ACCESS  read-write
        STATUS  mandatory
        DESCRIPTION
            "Counter specifying the total number of times an AT/SM was
            sent towards an application."
        ::= { appMobNetworkStatsEntry 112 }

    appMobNetworkStatsCntOutsideAtSuccess OBJECT-TYPE
        SYNTAX  Counter
        ACCESS  read-write
        STATUS  mandatory
        DESCRIPTION
            "Counter specifying the number of times an AT/SM was
            successfully routed to its destination."
        ::= { appMobNetworkStatsEntry 113 }

    appMobNetworkStatsCntOutsideAtSourceError OBJECT-TYPE
        SYNTAX  Counter
        ACCESS  read-write
        STATUS  mandatory
        DESCRIPTION
            "Counter specifying the number of times an AT/SM towards
             an application resulted in a source error
             (like a syntax error). The error mapping
             table is used to identify a source error. With a correct
             error mapping table it is not possible that this counter
             increases."
        ::= { appMobNetworkStatsEntry 114 }

    appMobNetworkStatsCntOutsideAtRoutingError OBJECT-TYPE
        SYNTAX  Counter
        ACCESS  read-write
        STATUS  mandatory
        DESCRIPTION
            "Counter specifying the number of times an AT/SM towards
            an application resulted in a routing error. The error
            mapping table is used to identify a routing error."
        ::= { appMobNetworkStatsEntry 115 }

    appMobNetworkStatsCntOutsideAtDestinationTemporaryError OBJECT-TYPE
        SYNTAX  Counter
        ACCESS  read-write
        STATUS  mandatory
        DESCRIPTION
            "Counter specifying the number of times an AT/SM towards
            an application resulted in a temporary error. The error
            mapping table is used to identify a temporary error."
        ::= { appMobNetworkStatsEntry 116 }

    appMobNetworkStatsCntOutsideAtDestinationPermanentRecipientError OBJECT-TYPE
        SYNTAX  Counter
        ACCESS  read-write
        STATUS  mandatory
        DESCRIPTION
            "Counter specifying the number of times an AT/SM towards
            an application resulted in a permanent recipient error. 
            The error mapping table is used to identify a permanent 
            recipient error."
        ::= { appMobNetworkStatsEntry 117 }

    appMobNetworkStatsCntOutsideAtDestinationPermanentMessageError OBJECT-TYPE
        SYNTAX  Counter
        ACCESS  read-write
        STATUS  mandatory
        DESCRIPTION
            "Counter specifying the number of times an AT/SM towards
            an application resulted in a permanent message error. The 
            error mapping table is used to identify a permanent message 
            error."
        ::= { appMobNetworkStatsEntry 118 }


    appAtRecipientCountryStatsTable OBJECT-TYPE
        SYNTAX  SEQUENCE OF AppAtRecipientCountryStatsEntry
        ACCESS  not-accessible
        STATUS  mandatory
        DESCRIPTION
            "A table containing AT statistics per country associated
            with the recipient (MSISDN) number and per application.
            For each application, the collection of these statistics
            can be enabled/disabled separately."
        ::= { sms 44 }

    appAtRecipientCountryStatsEntry OBJECT-TYPE
        SYNTAX  AppAtRecipientCountryStatsEntry
        ACCESS  not-accessible
        STATUS  mandatory
        DESCRIPTION
            "A 'row' in the appAtRecipientCountryStatsTable. Contains
            statistics per AT delivery result."
        INDEX   { appAtRecipientCountryStatsCountryIndex,
                  appAtRecipientCountryStatsApplicationIndex }
        ::= { appAtRecipientCountryStatsTable 1 }

    AppAtRecipientCountryStatsEntry ::=
        SEQUENCE {
            appAtRecipientCountryStatsCountryIndex     CountryTableIndex,
            appAtRecipientCountryStatsApplicationIndex ApplicationTableIndex,
            appAtRecipientCountryStatsInsideTotal      Counter,
            appAtRecipientCountryStatsInsideSuccess    Counter,
            appAtRecipientCountryStatsInsideSourceError Counter,
            appAtRecipientCountryStatsInsideRoutingError Counter,
            appAtRecipientCountryStatsInsideDestTempError Counter,
            appAtRecipientCountryStatsInsideDestPermRecipError Counter,
            appAtRecipientCountryStatsInsideDestPermMessageError Counter,
            appAtRecipientCountryStatsOutsideTotal     Counter,
            appAtRecipientCountryStatsOutsideSuccess   Counter,
            appAtRecipientCountryStatsOutsideSourceError Counter,
            appAtRecipientCountryStatsOutsideRoutingError Counter,
            appAtRecipientCountryStatsOutsideDestTempError Counter,
            appAtRecipientCountryStatsOutsideDestPermRecipError Counter,
            appAtRecipientCountryStatsOutsideDestPermMessageError Counter
        }

    appAtRecipientCountryStatsCountryIndex OBJECT-TYPE
        SYNTAX  CountryTableIndex
        ACCESS  read-write
        STATUS  mandatory
        DESCRIPTION
            "First index of appAtRecipientCountryStatsTable, specifying the
            country instance for which the corresponding statistics apply."
        ::= { appAtRecipientCountryStatsEntry 1 }

    appAtRecipientCountryStatsApplicationIndex OBJECT-TYPE
        SYNTAX  ApplicationTableIndex
        ACCESS  read-write
        STATUS  mandatory
        DESCRIPTION
            "Second index of appAtRecipientCountryStatsTable, specifying the
            application instance for which the corresponding statistics
            apply."
        ::= { appAtRecipientCountryStatsEntry 2 }

    appAtRecipientCountryStatsInsideTotal OBJECT-TYPE
        SYNTAX  Counter
        ACCESS  read-only
        STATUS  mandatory
        DESCRIPTION
            "Counter specifying the total number of received AT messages per
            application and recipient's country."
        ::= { appAtRecipientCountryStatsEntry 11 }

    appAtRecipientCountryStatsInsideSuccess OBJECT-TYPE
        SYNTAX  Counter
        ACCESS  read-write
        STATUS  mandatory
        DESCRIPTION
            "Counter specifying the number of received AT messages per
            application and recipient's country, which were accepted by the
            router."
        ::= { appAtRecipientCountryStatsEntry 12 }

    appAtRecipientCountryStatsInsideSourceError OBJECT-TYPE
        SYNTAX  Counter
        ACCESS  read-write
        STATUS  mandatory
        DESCRIPTION
            "Counter specifying the number of received AT messages per
            application and recipient's country, which were rejected by the
            router with a 'source error'."
        ::= { appAtRecipientCountryStatsEntry 13 }

    appAtRecipientCountryStatsInsideRoutingError OBJECT-TYPE
        SYNTAX  Counter
        ACCESS  read-write
        STATUS  mandatory
        DESCRIPTION
            "Counter specifying the number of received AT messages per
            application and recipient's country, which were rejected by the
            router with a 'routing error'."
        ::= { appAtRecipientCountryStatsEntry 14 }

    appAtRecipientCountryStatsInsideDestTempError OBJECT-TYPE
        SYNTAX  Counter
        ACCESS  read-write
        STATUS  mandatory
        DESCRIPTION
            "Counter specifying the number of received AT messages per
            application and recipient's country, which were rejected by the
            router with a 'destination temporary error'."
        ::= { appAtRecipientCountryStatsEntry 15 }

    appAtRecipientCountryStatsInsideDestPermRecipError OBJECT-TYPE
        SYNTAX  Counter
        ACCESS  read-write
        STATUS  mandatory
        DESCRIPTION
            "Counter specifying the number of received AT messages per
            application and recipient's country, which were rejected by the
            router with a 'destination permanent recipient error'."
        ::= { appAtRecipientCountryStatsEntry 16 }

    appAtRecipientCountryStatsInsideDestPermMessageError OBJECT-TYPE
        SYNTAX  Counter
        ACCESS  read-write
        STATUS  mandatory
        DESCRIPTION
            "Counter specifying the number of received AT messages per
            application and recipient's country, which were rejected by the
            router with a 'destination permanent message error'."
        ::= { appAtRecipientCountryStatsEntry 17 }

    appAtRecipientCountryStatsOutsideTotal OBJECT-TYPE
        SYNTAX  Counter
        ACCESS  read-only
        STATUS  mandatory
        DESCRIPTION
            "Counter specifying the total number of sent AT messages per
            application and recipient's country."
        ::= { appAtRecipientCountryStatsEntry 31 }

    appAtRecipientCountryStatsOutsideSuccess OBJECT-TYPE
        SYNTAX  Counter
        ACCESS  read-write
        STATUS  mandatory
        DESCRIPTION
            "Counter specifying the number of sent AT messages per
            application and recipient's country, which were successfully
            delivered to the application."
        ::= { appAtRecipientCountryStatsEntry 32 }

    appAtRecipientCountryStatsOutsideSourceError OBJECT-TYPE
        SYNTAX  Counter
        ACCESS  read-write
        STATUS  mandatory
        DESCRIPTION
            "Counter specifying the number of sent AT messages per
            application and recipient's country, which were rejected by the
            application with a 'source error'."
        ::= { appAtRecipientCountryStatsEntry 33 }

    appAtRecipientCountryStatsOutsideRoutingError OBJECT-TYPE
        SYNTAX  Counter
        ACCESS  read-write
        STATUS  mandatory
        DESCRIPTION
            "Counter specifying the number of sent AT messages per
            application and recipient's country, which were rejected by the
            application with a 'routing error'."
        ::= { appAtRecipientCountryStatsEntry 34 }

    appAtRecipientCountryStatsOutsideDestTempError OBJECT-TYPE
        SYNTAX  Counter
        ACCESS  read-write
        STATUS  mandatory
        DESCRIPTION
            "Counter specifying the number of sent AT messages per
            application and recipient's country, which were rejected by the
            application with a 'destination temporary error'."
        ::= { appAtRecipientCountryStatsEntry 35 }

    appAtRecipientCountryStatsOutsideDestPermRecipError OBJECT-TYPE
        SYNTAX  Counter
        ACCESS  read-write
        STATUS  mandatory
        DESCRIPTION
            "Counter specifying the number of sent AT messages per
            application and recipient's country, which were rejected by the
            application with a 'destination permanent recipient error'."
        ::= { appAtRecipientCountryStatsEntry 36 }

    appAtRecipientCountryStatsOutsideDestPermMessageError OBJECT-TYPE
        SYNTAX  Counter
        ACCESS  read-write
        STATUS  mandatory
        DESCRIPTION
            "Counter specifying the number of sent AT messages per
            application and recipient's country, which were rejected by the
            application with a 'destination permanent message error'."
        ::= { appAtRecipientCountryStatsEntry 37 }


    appAtRecipientMobNetworkStatsTable OBJECT-TYPE
        SYNTAX  SEQUENCE OF AppAtRecipientMobNetworkStatsEntry
        ACCESS  not-accessible
        STATUS  mandatory
        DESCRIPTION
            "A table containing AT statistics per country associated
            with the recipient (MSISDN) number and per application.
            For each application, the collection of these statistics
            can be enabled/disabled separately."
        ::= { sms 45 }

    appAtRecipientMobNetworkStatsEntry OBJECT-TYPE
        SYNTAX  AppAtRecipientMobNetworkStatsEntry
        ACCESS  not-accessible
        STATUS  mandatory
        DESCRIPTION
            "A 'row' in the appAtRecipientMobNetworkStatsTable. Contains
            statistics per AT delivery result."
        INDEX   { appAtRecipientMobNetworkStatsMobNetworkIndex,
                  appAtRecipientMobNetworkStatsApplicationIndex }
        ::= { appAtRecipientMobNetworkStatsTable 1 }

    AppAtRecipientMobNetworkStatsEntry ::=
        SEQUENCE {
            appAtRecipientMobNetworkStatsMobNetworkIndex  MobNetworkTableIndex,
            appAtRecipientMobNetworkStatsApplicationIndex ApplicationTableIndex,
            appAtRecipientMobNetworkStatsInsideTotal      Counter,
            appAtRecipientMobNetworkStatsInsideSuccess    Counter,
            appAtRecipientMobNetworkStatsInsideSourceError Counter,
            appAtRecipientMobNetworkStatsInsideRoutingError Counter,
            appAtRecipientMobNetworkStatsInsideDestTempError Counter,
            appAtRecipientMobNetworkStatsInsideDestPermRecipError Counter,
            appAtRecipientMobNetworkStatsInsideDestPermMessageError Counter,
            appAtRecipientMobNetworkStatsOutsideTotal     Counter,
            appAtRecipientMobNetworkStatsOutsideSuccess   Counter,
            appAtRecipientMobNetworkStatsOutsideSourceError Counter,
            appAtRecipientMobNetworkStatsOutsideRoutingError Counter,
            appAtRecipientMobNetworkStatsOutsideDestTempError Counter,
            appAtRecipientMobNetworkStatsOutsideDestPermRecipError Counter,
            appAtRecipientMobNetworkStatsOutsideDestPermMessageError Counter
        }

    appAtRecipientMobNetworkStatsMobNetworkIndex OBJECT-TYPE
        SYNTAX  MobNetworkTableIndex
        ACCESS  read-write
        STATUS  mandatory
        DESCRIPTION
            "First index of appAtRecipientMobNetworkStatsTable, specifying
            the mobile network instance for which the corresponding
            statistics apply."
        ::= { appAtRecipientMobNetworkStatsEntry 1 }

    appAtRecipientMobNetworkStatsApplicationIndex OBJECT-TYPE
        SYNTAX  ApplicationTableIndex
        ACCESS  read-write
        STATUS  mandatory
        DESCRIPTION
            "Second index of appAtRecipientMobNetworkStatsTable, specifying
            the application instance for which the corresponding statistics
            apply."
        ::= { appAtRecipientMobNetworkStatsEntry 2 }

    appAtRecipientMobNetworkStatsInsideTotal OBJECT-TYPE
        SYNTAX  Counter
        ACCESS  read-only
        STATUS  mandatory
        DESCRIPTION
            "Counter specifying the total number of received AT messages
            per application and recipient's mobile network."
        ::= { appAtRecipientMobNetworkStatsEntry 11 }

    appAtRecipientMobNetworkStatsInsideSuccess OBJECT-TYPE
        SYNTAX  Counter
        ACCESS  read-write
        STATUS  mandatory
        DESCRIPTION
            "Counter specifying the number of received AT messages per
            application and recipient's mobile network, which were accepted
            by the router."
        ::= { appAtRecipientMobNetworkStatsEntry 12 }

    appAtRecipientMobNetworkStatsInsideSourceError OBJECT-TYPE
        SYNTAX  Counter
        ACCESS  read-write
        STATUS  mandatory
        DESCRIPTION
            "Counter specifying the number of received AT messages per
            application and recipient's mobile network, which were rejected
            by the router with a 'source error'."
        ::= { appAtRecipientMobNetworkStatsEntry 13 }

    appAtRecipientMobNetworkStatsInsideRoutingError OBJECT-TYPE
        SYNTAX  Counter
        ACCESS  read-write
        STATUS  mandatory
        DESCRIPTION
            "Counter specifying the number of received AT messages per
            application and recipient's mobile network, which were rejected
            by the router with a 'routing error'."
        ::= { appAtRecipientMobNetworkStatsEntry 14 }

    appAtRecipientMobNetworkStatsInsideDestTempError OBJECT-TYPE
        SYNTAX  Counter
        ACCESS  read-write
        STATUS  mandatory
        DESCRIPTION
            "Counter specifying the number of received AT messages per
            application and recipient's mobile network, which were rejected
            by the router with a 'destination temporary error'."
        ::= { appAtRecipientMobNetworkStatsEntry 15 }

    appAtRecipientMobNetworkStatsInsideDestPermRecipError OBJECT-TYPE
        SYNTAX  Counter
        ACCESS  read-write
        STATUS  mandatory
        DESCRIPTION
            "Counter specifying the number of received AT messages per
            application and recipient's mobile network, which were rejected
            by the router with a 'destination permanent recipient error'."
        ::= { appAtRecipientMobNetworkStatsEntry 16 }

    appAtRecipientMobNetworkStatsInsideDestPermMessageError OBJECT-TYPE
        SYNTAX  Counter
        ACCESS  read-write
        STATUS  mandatory
        DESCRIPTION
            "Counter specifying the number of received AT messages per
            application and recipient's mobile network, which were rejected
            by the router with a 'destination permanent message error'."
        ::= { appAtRecipientMobNetworkStatsEntry 17 }

    appAtRecipientMobNetworkStatsOutsideTotal OBJECT-TYPE
        SYNTAX  Counter
        ACCESS  read-only
        STATUS  mandatory
        DESCRIPTION
            "Counter specifying the total number of sent AT messages per
            application and recipient's mobile network."
        ::= { appAtRecipientMobNetworkStatsEntry 31 }

    appAtRecipientMobNetworkStatsOutsideSuccess OBJECT-TYPE
        SYNTAX  Counter
        ACCESS  read-write
        STATUS  mandatory
        DESCRIPTION
            "Counter specifying the number of sent AT messages per
            application and recipient's mobile network, which were
            successfully delivered to the application."
        ::= { appAtRecipientMobNetworkStatsEntry 32 }

    appAtRecipientMobNetworkStatsOutsideSourceError OBJECT-TYPE
        SYNTAX  Counter
        ACCESS  read-write
        STATUS  mandatory
        DESCRIPTION
            "Counter specifying the number of sent AT messages per
            application and recipient's mobile network, which were rejected
            by the application with a 'source error'."
        ::= { appAtRecipientMobNetworkStatsEntry 33 }

    appAtRecipientMobNetworkStatsOutsideRoutingError OBJECT-TYPE
        SYNTAX  Counter
        ACCESS  read-write
        STATUS  mandatory
        DESCRIPTION
            "Counter specifying the number of sent AT messages per
            application and recipient's mobile network, which were rejected
            by the application with a 'routing error'."
        ::= { appAtRecipientMobNetworkStatsEntry 34 }

    appAtRecipientMobNetworkStatsOutsideDestTempError OBJECT-TYPE
        SYNTAX  Counter
        ACCESS  read-write
        STATUS  mandatory
        DESCRIPTION
            "Counter specifying the number of sent AT messages per
            application and recipient's mobile network, which were rejected
            by the application with a 'destination temporary error'."
        ::= { appAtRecipientMobNetworkStatsEntry 35 }

    appAtRecipientMobNetworkStatsOutsideDestPermRecipError OBJECT-TYPE
        SYNTAX  Counter
        ACCESS  read-write
        STATUS  mandatory
        DESCRIPTION
            "Counter specifying the number of sent AT messages per
            application and recipient's mobile network, which were rejected
            by the application with a 'destination permanent recipient
            error'."
        ::= { appAtRecipientMobNetworkStatsEntry 36 }

    appAtRecipientMobNetworkStatsOutsideDestPermMessageError OBJECT-TYPE
        SYNTAX  Counter
        ACCESS  read-write
        STATUS  mandatory
        DESCRIPTION
            "Counter specifying the number of sent AT messages per
            application and recipient's mobile network, which were rejected
            by the application with a 'destination permanent message error'."
        ::= { appAtRecipientMobNetworkStatsEntry 37 }


    appCharAsciiToGsmTable OBJECT-TYPE
        SYNTAX  SEQUENCE OF AppCharAsciiToGsmEntry
        ACCESS  not-accessible
        STATUS  mandatory
        DESCRIPTION
            "A table for the conversion from character of the IA5 (7-bit
            ASCII) and Latin/ISO-8859-1 (8-bit ASCII) character set to the
            GSM default alphabet."
        ::= { sms 47 }

    appCharAsciiToGsmEntry OBJECT-TYPE
        SYNTAX  AppCharAsciiToGsmEntry
        ACCESS  not-accessible
        STATUS  mandatory
        DESCRIPTION
            "Table entry for the conversion of character from the GSM default
            alphabet to the IA5 (7-bit ASCII) and Latin/ISO-8859-1 (8-bit
            ASCII) character set."
        INDEX   { appCharAsciiToGsmIndex }
        ::= { appCharAsciiToGsmTable 1 }

    AppCharAsciiToGsmEntry ::=
        SEQUENCE {
            appCharAsciiToGsmIndex                AppCharIndex,
            appCharAsciiToGsmAsciiCode            AsciiCharCode,
            appCharAsciiToGsmGsmCode              GsmCharCode
        }

    appCharAsciiToGsmIndex OBJECT-TYPE
        SYNTAX  AppCharIndex
        ACCESS  not-accessible
        STATUS  mandatory
        DESCRIPTION
            "Index of entry in table for conversion of character from the GSM
            default alphabet to the IA5 (7-bit ASCII) and Latin/ISO-8859-1
            (8-bit ASCII) character set.

            The index of an entry is equal to:

              index := (ordinal value of appCharAsciiToGsmAsciiCode) - 1"
        ::= { appCharAsciiToGsmEntry 1 }

    appCharAsciiToGsmAsciiCode OBJECT-TYPE
        SYNTAX  AsciiCharCode
        ACCESS  read-write
        STATUS  mandatory
        DESCRIPTION
            "Coding of character in IA5 (7-bit ASCII) and Latin/ISO-8859-1
            (8-bit ASCII) format."
        ::= { appCharAsciiToGsmEntry 2 }

    appCharAsciiToGsmGsmCode OBJECT-TYPE
        SYNTAX  GsmCharCode
        ACCESS  read-write
        STATUS  mandatory
        DESCRIPTION
            "Coding of character in GSM format. This code comprises one septet
            in case the character is from the basic table of the GSM default
            alphabet and two septets in case the character is from the
            extension table of the GSM default alphabet."
        ::= { appCharAsciiToGsmEntry 3 }

    appAliasTable OBJECT-TYPE
        SYNTAX  SEQUENCE OF AppAliasEntry
        ACCESS  not-accessible
        STATUS  mandatory
        DESCRIPTION
            "Table with aliases for an Application."
        ::= { sms 48 }

    appAliasEntry OBJECT-TYPE
        SYNTAX  AppAliasEntry
        ACCESS  not-accessible
        STATUS  mandatory
        DESCRIPTION
            "Table entry defining a single alias for an application."
        INDEX   { appAliasIndex1, appAliasIndex2 }
        ::= { appAliasTable 1 }

    AppAliasEntry ::=
        SEQUENCE {
            appAliasIndex1                      ApplicationTableIndex,
            appAliasIndex2                      AliasTableIndex,
            appAlias                            AliasString
        }

    appAliasIndex1 OBJECT-TYPE
        SYNTAX  ApplicationTableIndex
        ACCESS  not-accessible
        STATUS  mandatory
        DESCRIPTION
            "Index for appAliasTable.
            Its value is equal to the index of the corresponding
            applicationTable entry."
        ::= { appAliasEntry 1}

    appAliasIndex2 OBJECT-TYPE
        SYNTAX  AliasTableIndex
        ACCESS  not-accessible
        STATUS  mandatory
        DESCRIPTION
            "Index for appAliasTable.
             This index identifies one specific alias."
        ::= { appAliasEntry 2}

    appAlias OBJECT-TYPE
        SYNTAX  AliasString
        ACCESS  read-write
        STATUS  mandatory
        DESCRIPTION
            "Alphanumeric Alias for an application. This Alias needs to be
            unique"
        ::= { appAliasEntry 3}

    appOriginatorListTable OBJECT-TYPE
        SYNTAX  SEQUENCE OF AppOriginatorListEntry
        ACCESS  not-accessible
        STATUS  mandatory
        DESCRIPTION
            "Table with originator lists for the applications. Before an
            entry to this table can be added, the relating application needs
            to exist."
        ::= { sms 49 }

    appOriginatorListEntry OBJECT-TYPE
        SYNTAX  AppOriginatorListEntry
        ACCESS  not-accessible
        STATUS  mandatory
        DESCRIPTION
            "Table entry defining an originator list for an application.
             Note that the conditions on the originator that make up the list 
             are in the subordinate appOriginatorListConditionTable."
        INDEX   { appOriginatorListIndex }
        ::= { appOriginatorListTable 1 }

    AppOriginatorListEntry ::=
        SEQUENCE {
            appOriginatorListIndex                       ApplicationTableIndex,
            appOriginatorListAdminState                  AdminState,  
            appOriginatorListType                        ListType
        }

    appOriginatorListIndex OBJECT-TYPE
        SYNTAX  ApplicationTableIndex
        ACCESS  not-accessible
        STATUS  mandatory
        DESCRIPTION
            "Index for appOriginatorListTable (same as one used for
            applicationTable)."
        ::= { appOriginatorListEntry 1}
    
    appOriginatorListAdminState OBJECT-TYPE
        SYNTAX  AdminState
        ACCESS  read-write
        STATUS  mandatory
        DESCRIPTION
            "Administrative state of the originator list of an application.

            Transition from 'inactive' to 'active' and vice versa is possible
            as long as the relating application is existing. 

            For details, refer to the comment on the AdminState type."
        ::= { appOriginatorListEntry 2 }

    appOriginatorListType OBJECT-TYPE
        SYNTAX  ListType
        ACCESS  read-write
        STATUS  mandatory
        DESCRIPTION
            "Type of originator list. Default is 'whiteList."
        ::= { appOriginatorListEntry 3}
        
    
    appOriginatorListConditionTable OBJECT-TYPE
        SYNTAX  SEQUENCE OF AppOriginatorListConditionEntry
        ACCESS  not-accessible
        STATUS  mandatory
        DESCRIPTION
            "A table containing the conditions for the originator list of an 
             application."
        ::= { sms 50 }

    appOriginatorListConditionEntry OBJECT-TYPE
        SYNTAX  AppOriginatorListConditionEntry
        ACCESS  not-accessible
        STATUS  mandatory
        DESCRIPTION
            "Table entry defining a single condition spec for an originator
            list of an application."
        INDEX   { appOriginatorListConditionIndex1, appOriginatorListConditionIndex2 }
        ::= { appOriginatorListConditionTable 1 }

    AppOriginatorListConditionEntry ::=
        SEQUENCE {
            appOriginatorListConditionIndex1      ApplicationTableIndex,
            appOriginatorListConditionIndex2      AppOriginatorListConditionTableIndex,
            appOriginatorListCondition            ConditionSpec
        }

    appOriginatorListConditionIndex1 OBJECT-TYPE
        SYNTAX  ApplicationTableIndex
        ACCESS  not-accessible
        STATUS  mandatory
        DESCRIPTION
            "Index of entry in table containing condition specifications for
            a originator list of an application. This index is a reference to
            the related application entity. Its value is equal to the index
            of the application in the appOriginatorListTable (as well as
            applicationTable)."
        ::= { appOriginatorListConditionEntry 1 }

    appOriginatorListConditionIndex2 OBJECT-TYPE
        SYNTAX  AppOriginatorListConditionTableIndex
        ACCESS  not-accessible
        STATUS  mandatory
        DESCRIPTION
            "Index of entry in table containing condition specifications for
            an originator list of an application. This index identifies one
            specific condition."
        ::= { appOriginatorListConditionEntry 2 }

    appOriginatorListCondition OBJECT-TYPE
        SYNTAX  ConditionSpec
        ACCESS  read-write
        STATUS  mandatory
        DESCRIPTION
            "Condition specification. Restrictions:
               - the 'not' (!) operation on a condition is not allowed
               - only the following condition types are allowed in a list:
                    SINGLEMSISDN
                    MSISDNRANGE
                    MSISDNPREFIX
                    SINGLESHORTNUMBER
                    SHORTNUMBERRANGE
                    SHORTNUMBERPREFIX
                    ALPHANUMADDRESS
                    
            Refer to the comment on the ConditionSpec Type for the general
            description."
        ::= { appOriginatorListConditionEntry 3 }

    smscTable OBJECT-TYPE
        SYNTAX  SEQUENCE OF SmscEntry
        ACCESS  not-accessible
        STATUS  mandatory
        DESCRIPTION
            "A table containing properties for each SMSC."
        ::= { sms 51 }

    smscEntry OBJECT-TYPE
        SYNTAX  SmscEntry
        ACCESS  not-accessible
        STATUS  mandatory
        DESCRIPTION
            "Table entry defining a single SMSC."
        INDEX   { smscIndex }
        ::= { smscTable 1 }

    SmscEntry ::=
        SEQUENCE {
            smscIndex                             SmscTableIndex,
            smscAdminState                        AdminState,
            smscOperationalState                  SmscOperationalState,
            smscName                              NameString,
            smscSccpAddress                       E164Address,
            smscThroughput                        Throughput,
            smscTestAccessTimer                   TestAccessTimer,
            smscMapAddress                        E164Address,
            smscMoTotalCounter                    Counter,
            smscMoSuccessfulCounter               Counter,
            smscMoTimeoutCounter                  Counter,
            smscMoDroppedCounter                  Counter,
            smscMoDiscardWithNakCounter           Counter,
            smscMoRejectedByTprCounter            Counter,
            smscMoRejectedByAppCounter            Counter,
            smscMoUnknownResultCounter            Counter,
            smscMoSysFailErrorCounter             Counter,
            smscMoDataMisErrorCounter             Counter,
            smscMoUnexpDataValErrorCounter        Counter,
            smscMoFacNotSuppErrorCounter          Counter,
            smscMoUnkScErrorCounter               Counter,
            smscMoScCongErrorCounter              Counter,
            smscMoInvSmeAddrErrorCounter          Counter,
            smscMoSubNotScSubErrorCounter         Counter,
            smscMoOtherErrorsCounter              Counter,
            smscMoTcapAbortedCounter              Counter,
            smscMoSccpAbortedCounter              Counter
        }

    smscIndex OBJECT-TYPE
        SYNTAX  SmscTableIndex
        ACCESS  not-accessible
        STATUS  mandatory
        DESCRIPTION
            "Index of entry in SMSC table."
        ::= { smscEntry 1 }

    smscAdminState OBJECT-TYPE
        SYNTAX  AdminState
        ACCESS  read-write
        STATUS  mandatory
        DESCRIPTION
            "Administrative state of the SMSC.

            Transition from 'inactive' to 'active' is only possible when:
            1) name supplied and not already in use by another SMSC;
            2) address supplied and not already in use by another SMSC;

            Transition from 'active' to 'inactive' is only possible when:
            1) SMSC is not being referred.

            For details, refer to the comment on the AdminState type."
        ::= { smscEntry 2 }

    smscOperationalState OBJECT-TYPE
        SYNTAX  SmscOperationalState
        ACCESS  read-only
        STATUS  mandatory
        DESCRIPTION
            "Operational state of the SMSC."
        ::= { smscEntry 3 }

    smscName OBJECT-TYPE
        SYNTAX  NameString
        ACCESS  read-write
        STATUS  mandatory
        DESCRIPTION
            "Name for the SMSC."
        ::= { smscEntry 4 }


    smscSccpAddress OBJECT-TYPE
        SYNTAX  E164Address
        ACCESS  read-write
        STATUS  mandatory
        DESCRIPTION
            "Internationally encoded E164 address excluding the international
            prefix for the SCCP address of the SMSC."
        ::= { smscEntry 5 }

    smscThroughput OBJECT-TYPE
        SYNTAX  Throughput
        ACCESS  read-write
        STATUS  mandatory
        DESCRIPTION
            "Maximum throughput in terms of SM's routed per second to an
            SMSC."
        ::= { smscEntry 6 }

    smscTestAccessTimer OBJECT-TYPE
        SYNTAX  TestAccessTimer
        ACCESS  read-only
        STATUS  mandatory
        DESCRIPTION
            "TextPass is capable to keep track of the accessibility of the
            SMSC.
            It does this by sending test messages at regular intervals. This
            timer defines the duration of this interval in units of seconds.
            Setting this timer to 0, which is the default, disables the 'test
            accessibility' feature."
        ::= { smscEntry 7 }

    smscMapAddress OBJECT-TYPE
        SYNTAX  E164Address
        ACCESS  read-write
        STATUS  mandatory
        DESCRIPTION
            "Internationally encoded E164 address excluding the international
            prefix for the MAP address of the SMSC. If not specified, the MAP
            address as specified in the incoming MAP MO-ForwardSM message is
            taken."
        ::= { smscEntry 8 }

    smscMoTotalCounter OBJECT-TYPE
        SYNTAX  Counter
        ACCESS  read-write
        STATUS  mandatory
        DESCRIPTION
            "Counter specifying the total number of times an MO/SM was
            received."
        ::= { smscEntry 11 }

    smscMoSuccessfulCounter OBJECT-TYPE
        SYNTAX  Counter
        ACCESS  read-write
        STATUS  mandatory
        DESCRIPTION
            "Counter specifying the number of times an MO/SM was successfully
             routed to its destination. The following events result in
             incrementing of this counter:
             - receiving a MO/SM matching a rule with action equal to
               discardWithAck
             - receiving an ACK from an application as result of an MO/SM
               being routed to the application
             - receiving an ACK from an SMSC as result of an MO/SM being
               routed to the SMSC."
        ::= { smscEntry 12 }

    smscMoTimeoutCounter OBJECT-TYPE
        SYNTAX  Counter
        ACCESS  read-write
        STATUS  mandatory
        DESCRIPTION
            "Counter specifying the number of times that routing an MO/SM to
            its destination resulted in a timeout. The following events
            result in incrementing of this counter:
             - not receiving a response from an application on an MO/SM
               being routed to the application within the maximum response
               time
             - receiving an ACK from an SMSC as result of an MO/SM being
               routed to an SMSC within the maximum response time."
        ::= { smscEntry 13 }

    smscMoDroppedCounter OBJECT-TYPE
        SYNTAX  Counter
        ACCESS  read-write
        STATUS  mandatory
        DESCRIPTION
            "Counter specifying the number of times that an MO/SM has not
            been routed to its destination due to decimation (this is only
            applicable when routing to an application)."
        ::= { smscEntry 14 }

    smscMoDiscardWithNakCounter OBJECT-TYPE
        SYNTAX  Counter
        ACCESS  read-write
        STATUS  mandatory
        DESCRIPTION
            "Counter specifying the number of times that TPR has rejected an
            MO/SM as result of a routing rule with action equal to
            discardWithNak or because none of the routing rules match."
        ::= { smscEntry 15 }

    smscMoRejectedByTprCounter OBJECT-TYPE
        SYNTAX  Counter
        ACCESS  read-write
        STATUS  mandatory
        DESCRIPTION
            "Counter specifying the number of times that TPR has rejected an
            MO/SM as result of incorrect syntax of the MO/SM."
        ::= { smscEntry 16 }

    smscMoRejectedByAppCounter OBJECT-TYPE
        SYNTAX  Counter
        ACCESS  read-write
        STATUS  mandatory
        DESCRIPTION
            "Counter specifying the number of times that routing to an
            application resulted in the application rejecting the MO/SM by
            sending a NAK."
        ::= { smscEntry 17 }

    smscMoUnknownResultCounter OBJECT-TYPE
        SYNTAX  Counter
        ACCESS  read-write
        STATUS  mandatory
        DESCRIPTION
            "Counter specifying the number of times that the result of routing
            an MO/SM to its destination could not be retrieved (this is only
            applicable when using optimal routing towards an SMSC)."
        ::= { smscEntry 18 }

    smscMoSysFailErrorCounter OBJECT-TYPE
        SYNTAX  Counter
        ACCESS  read-write
        STATUS  mandatory
        DESCRIPTION
            "Counter specifying the number of times that routing to an SMSC
            resulted in the SMSC rejecting the MO/SM with a System-Failure
            error on MAP level."
        ::= { smscEntry 19 }

    smscMoDataMisErrorCounter OBJECT-TYPE
        SYNTAX  Counter
        ACCESS  read-write
        STATUS  mandatory
        DESCRIPTION
            "Counter specifying the number of times that routing to an SMSC
            resulted in the SMSC rejecting the MO/SM with a Data-Missing
            error on MAP level."
        ::= { smscEntry 20 }

    smscMoUnexpDataValErrorCounter OBJECT-TYPE
        SYNTAX  Counter
        ACCESS  read-write
        STATUS  mandatory
        DESCRIPTION
            "Counter specifying the number of times that routing to an SMSC
            resulted in the SMSC rejecting the MO/SM with a Unexpected-Data-
            Value error on MAP level."
        ::= { smscEntry 21 }

    smscMoFacNotSuppErrorCounter OBJECT-TYPE
        SYNTAX  Counter
        ACCESS  read-write
        STATUS  mandatory
        DESCRIPTION
            "Counter specifying the number of times that routing to an SMSC
            resulted in the SMSC rejecting the MO/SM with a Facility-Not-
            Supported error on MAP level."
        ::= { smscEntry 22 }

    smscMoUnkScErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Unknown-
            Service-Centre."
        ::= { smscEntry 23 }

    smscMoScCongErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to SC-
            Congestion."
        ::= { smscEntry 24 }

    smscMoInvSmeAddrErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Invalid-
            SME-Address."
        ::= { smscEntry 25 }

    smscMoSubNotScSubErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to
            Subscriber-Not-SC-Subscriber."
        ::= { smscEntry 26 }

    smscMoOtherErrorsCounter OBJECT-TYPE
        SYNTAX  Counter
        ACCESS  read-write
        STATUS  mandatory
        DESCRIPTION
            "Counter specifying the number of times that routing to an SMSC
            resulted in the SMSC rejecting the MO/SM with another MAP error
            (or possibly a failure cause) than specified for the
            other MO counters."
        ::= { smscEntry 27 }

    smscMoTcapAbortedCounter OBJECT-TYPE
        SYNTAX  Counter
        ACCESS  read-write
        STATUS  mandatory
        DESCRIPTION
            "Counter specifying the number of times that routing to an SMSC
            resulted in the SMSC rejecting the MO/SM by sending a TC-ABORT
            on TCAP level."
        ::= { smscEntry 28 }

    smscMoSccpAbortedCounter OBJECT-TYPE
        SYNTAX  Counter
        ACCESS  read-write
        STATUS  mandatory
        DESCRIPTION
            "Counter specifying the number of times that routing to an SMSC
            resulted in the SMSC rejecting the MO/SM by sending a UDTS on
            SCCP level."
        ::= { smscEntry 29 }


    -- the List Entity

    listTable OBJECT-TYPE
        SYNTAX  SEQUENCE OF ListEntry
        ACCESS  not-accessible
        STATUS  mandatory
        DESCRIPTION
            "A table containing properties for each list entity
             The related condion specifications will be placed in in the
             listConditionTable."
        ::= { sms 61 }


    listEntry OBJECT-TYPE
        SYNTAX  ListEntry
        ACCESS  not-accessible
        STATUS  mandatory
        DESCRIPTION
            "Table entry defining a list."
        INDEX   { listIndex }
        ::= { listTable 1 }

    ListEntry ::=
        SEQUENCE {
            listIndex                             ListTableIndex,
            listAdminState                        AdminState,
            listName                              NameString,
            listType                              ListTypeBits
        }

    listIndex OBJECT-TYPE
        SYNTAX  ListTableIndex
        ACCESS  not-accessible
        STATUS  mandatory
        DESCRIPTION
            "Index of entry in list table."
        ::= { listEntry 1 }

    listAdminState OBJECT-TYPE
        SYNTAX  AdminState
        ACCESS  read-write
        STATUS  mandatory
        DESCRIPTION
            "Administrative state of a list entity."
        ::= { listEntry 2 }

    listName OBJECT-TYPE
        SYNTAX  NameString
        ACCESS  read-write
        STATUS  mandatory
        DESCRIPTION
            "Name of a list entity."
        ::= { listEntry 3 }

    listType OBJECT-TYPE
        SYNTAX  ListTypeBits
        ACCESS  read-write
        STATUS  mandatory
        DESCRIPTION
            "Bitmap indicating the type(s) of conditions contained in a list.
             At this moment only one type per list is allowed. A mix of types
             may be supported in the future.
             Refer to the comment on the ListTypeBits for the values."
        ::= { listEntry 4 }

    listConditionTable OBJECT-TYPE
        SYNTAX  SEQUENCE OF ListConditionEntry
        ACCESS  not-accessible
        STATUS  mandatory
        DESCRIPTION
            "A table containing the conditions for each list entity."
        ::= { sms 62 }

    listConditionEntry OBJECT-TYPE
        SYNTAX  ListConditionEntry
        ACCESS  not-accessible
        STATUS  mandatory
        DESCRIPTION
            "Table entry defining a single condition spec for a list entity."
        INDEX   { listConditionIndex1, listConditionIndex2 }
        ::= { listConditionTable 1 }

    ListConditionEntry ::=
        SEQUENCE {
            listConditionIndex1                   ListTableIndex,
            listConditionIndex2                   ListConditionTableIndex,
            listCondition                         ConditionSpec
        }

    listConditionIndex1 OBJECT-TYPE
        SYNTAX  ListTableIndex
        ACCESS  not-accessible
        STATUS  mandatory
        DESCRIPTION
            "Index of entry in table containing condition specifications
             for a list entity. This index is a reference to the related
             list entity. Its value is equal to the index of the listTable
             entry."
        ::= { listConditionEntry 1 }

    listConditionIndex2 OBJECT-TYPE
        SYNTAX  ListConditionTableIndex
        ACCESS  not-accessible
        STATUS  mandatory
        DESCRIPTION
            "Index of entry in table containing condition specifications
             for a list entity. This index identifies one specific condition."
        ::= { listConditionEntry 2 }

    listCondition OBJECT-TYPE
        SYNTAX  ConditionSpec
        ACCESS  read-write
        STATUS  mandatory
        DESCRIPTION
            "Condition specification. Restrictions:
               - the 'not' (!) operation on a condition is not allowed
               - only the following condition types are allowed in a list:
                    SINGLEMSISDN
                    MSISDNRANGE
                    MSISDNPREFIX
                    SINGLEIMSI
                    IMSIRANGE
                    SINGLESHORTNUMBER
                    SHORTNUMBERRANGE
                    SHORTNUMBERPREFIX
                    SINGLEPOINTCODE
                    POINTCODERANGE
                    ALPHANUMADDRESS
                    

               (In the future the following types may be added:
                    APPLICATION
                    COUNTRY
                    NETWORK
                    PID
                    DCS
                    TON
                    NPI )

            Refer to the comment on the ConditionSpec Type for the general
            description."
        ::= { listConditionEntry 3 }

    -- SmscGroupTable

    smscGroupTable OBJECT-TYPE
        SYNTAX  SEQUENCE OF SmscGroupEntry
        ACCESS  not-accessible
        STATUS  mandatory
        DESCRIPTION
            "A table to group SMSCs of the same type (GSM, ANSI, AO). GSM 
            messages and ANSI messages that are routed to an SMSC group are 
            distributed over the SMSCs in the requested group based on a 
            prioritised, weighted load balancing scheme. Distribution for AO 
            message is done using a load balancing scheme based on priority."
        ::= { sms 63 }

    smscGroupEntry OBJECT-TYPE
        SYNTAX  SmscGroupEntry
        ACCESS  not-accessible
        STATUS  mandatory
        DESCRIPTION
            "Table entry defining a single SMSC group entry."
        INDEX   { smscGroupIndex }
        ::= { smscGroupTable 1 }

    SmscGroupEntry ::=
        SEQUENCE {
            smscGroupIndex      SmscGroupIndex,
            smscGroupAdminState AdminState,
            smscGroupName       NameString,
            smscGroupType       SmscGroupType
        }

    smscGroupIndex OBJECT-TYPE
        SYNTAX  SmscGroupIndex
        ACCESS  read-write
        STATUS  mandatory
        DESCRIPTION
            "Index of entry in SMSC group table."
        ::= { smscGroupEntry 1 }

    smscGroupAdminState OBJECT-TYPE
        SYNTAX  AdminState
        ACCESS  read-write
        STATUS  mandatory
        DESCRIPTION
            "Administrative state of the SMSC group. In order
            to activate an SMSC group entry, the following conditions
            must be satisfied:

            1) The name field must be set to a value unique for the 
               SMSC group table.
            2) The type field must refer to an existing SMSC table.

            In order to deactivate an SMSC group, the following
            conditions must be satisfied:

            1) The group must not be referenced. A group may be
               referenced by other objects such as routing rules."
         ::= { smscGroupEntry 2 }

    smscGroupName OBJECT-TYPE
        SYNTAX  NameString
        ACCESS  read-write
        STATUS  mandatory
        DESCRIPTION
            "Descriptive unique name of an SMSC group."
        ::= { smscGroupEntry 3 }

    smscGroupType OBJECT-TYPE
        SYNTAX  SmscGroupType
        ACCESS  read-write
        STATUS  mandatory
        DESCRIPTION
            "Type of SMSCs belonging to this SMSC group. See the 
            definition of the SmscGroupType for more information.
            By default, this field is set to 'ansi'."
        ::= { smscGroupEntry 4 }

    -- SMSC Group Member Table

    smscGroupMemberTable OBJECT-TYPE
        SYNTAX  SEQUENCE OF SmscGroupMemberEntry
        ACCESS  not-accessible
        STATUS  mandatory
        DESCRIPTION
            "A table for grouping SMSCs of the same type into SMSC groups.
            GSM messages and ANSI messages that are routed to an SMSC group 
            are distributed over the SMSCs in the requested group based on a 
            prioritised, weighted load balancing scheme. Distribution for AO 
            messages is done using a load balancing scheme based on priority
            Each entry in the SMSC group member assignes one SMSC to one
            SMSC group. Both SMSCs and SMSC groups are defined in separate
            tables. The SMSC group table defines which type of SMSC may
            belong to an SMSC group.

            An GSM or ANSI SMSC group member entry can throttle the number of 
            SMs sent through the referenced group to the referenced SMSC per 
            unit of time by means of a maximum throughput regulation scheme.

            Mo/SMs to be submitted to an SMSC in an GSM or ANSI SMSC group are 
            load-balanced according to the following scheme:

            1) Only SMSC's for which the following conditions apply are
               considered:
               a) The operational state of the SMSC as defined in its own
                  table is 'available'.
               b) The operational state of the SMSC as defined in the group
                  member table is 'available'.
            2) Always, SM's are routed to the SMSC with the highest priority.
            3) In case multiple SMSC's have the same priority, SM's are
               distributed by considering the weights that are defined for the
               SMSC's. The higher the weight that is defined for an SMSC, the
               more SM's it will receive. The load balancing mechanism will
               attempt to route messages for the same recipient to the same
               SMSC.

            AO/SMs to be submitted to an SMSC in an AO SMSC group are 
            load-balanced according to a scheme that uses priority, but not 
            weights and a throughput threshold.

            The following sample aims to illustrate the prioritised, weighted
            load balancing scheme. Suppose that the following SMSC group
            members have been defined for an SMSC group:

                                               SMSC's          group member's
                      priority  weight   operationalState    operationalState
                     ---------------------------------------------------------
                SMSC1    3        5          available           available
                SMSC2    5        1        notReachable          available
                SMSC3    6        1          available      throughputExceeded
                SMSC4    4        2          available           available
                SMSC5    4        3          available           available

            The distribution of the SM's for theSMSC group will be as
            following:

            1) SMSC1 will not receive any SM's, since its priority is too low.
            2) SMSC2 will not receive any SM's, since the operationalState of
               the SMSC in the smscTable is not 'available'
            3) SMSC3 will not receive any SM's, since the operationalState of
               the SMSC in this table is not 'available'
            4) SMSC4 will receive 40% of the SM's, as its weight (=2) is 40%
               of the total weight of the SMSC's that are considered (=2+3=5)
            5) SMSC5 will receive 60% of the SM's, as its weight (=3) is 60%
               of the total weight of the SMSC's that are considered (=2+3=5)
               
            Note that for SMSC groups of type"
        ::= { sms 64 }

    smscGroupMemberEntry OBJECT-TYPE
        SYNTAX  SmscGroupMemberEntry
        ACCESS  not-accessible
        STATUS  mandatory
        DESCRIPTION
            "Table entry defining a single SMSC group member entry."
        INDEX   { smscGroupMemberIndex1, smscGroupMemberIndex2 }
        ::= { smscGroupMemberTable 1 }

    SmscGroupMemberEntry ::=
        SEQUENCE {
            smscGroupMemberIndex1           SmscGroupIndex,
            smscGroupMemberIndex2           AnySmscTableIndex,
            smscGroupMemberAdminState       AdminState,
            smscGroupMemberOperationalState SmscGroupMemberOperationalState,
            smscGroupMemberPriority         Priority,
            smscGroupMemberWeight           Weight,
            smscGroupMemberThroughput       Throughput
        }
    
    smscGroupMemberIndex1 OBJECT-TYPE
        SYNTAX  SmscGroupIndex
        ACCESS  read-write
        STATUS  mandatory
        DESCRIPTION
            "Primary index of entry in SMSC group member table.
            Specifies which SMSC group the member belongs to."
        ::= { smscGroupMemberEntry 1 }

    smscGroupMemberIndex2 OBJECT-TYPE
        SYNTAX  AnySmscTableIndex
        ACCESS  read-write
        STATUS  mandatory
        DESCRIPTION
            "Secondary index of entry in the SMSC group member table.
            Specifies which SMSC is a member of the SMSC group specified
            by the primary index. Depending on the type of the SMSC group,
            this is an index into the corresponding SMSC table."
        ::= { smscGroupMemberEntry 2 }

    smscGroupMemberAdminState OBJECT-TYPE
        SYNTAX  AdminState
        ACCESS  read-write
        STATUS  mandatory
        DESCRIPTION
            "Administrative state of the SMSC group member. Only group
            members, the administrative state of which is 'active' are
            considered when load-distributing messages to a group of 
            SMSCs. In order to activate an SMSC group member, the
            following conditions must be satisfied:

            1) The administrative state of the SMSC must be 'active'."
        ::= { smscGroupMemberEntry 3 }

    smscGroupMemberOperationalState OBJECT-TYPE
        SYNTAX  SmscGroupMemberOperationalState
        ACCESS  read-only
        STATUS  mandatory
        DESCRIPTION
            "Operational State of the SMSC group member. Only group
            members with an operational state of available are eligible
            by the load-balancing mechanism. The operational state is
            'available' if the administrative state of the SMSC group
            member id 'active' and the throughput limit does not prevent
            messages from being sent to the references SMSC."
        ::= { smscGroupMemberEntry 4 }

    smscGroupMemberPriority OBJECT-TYPE
        SYNTAX  Priority
        ACCESS  read-write
        STATUS  mandatory
        DESCRIPTION
            "Priority of the SMSC group member. Messages are only load-
            balanced between 'available' SMSC group members with the
            highest priority. The priority of a group member can only be
            changed when the group member's administrative state is
            'disabled'."
        ::= { smscGroupMemberEntry 5 }

    smscGroupMemberWeight OBJECT-TYPE
        SYNTAX  Weight
        ACCESS  read-write
        STATUS  mandatory
        DESCRIPTION
            "Weight of the SMSC group member. Messages are load-balanced
            between SMSC group members or the same (highest) priority
            according to their weight. A higher weight corresponds to a 
            higher load. The weight of a group member can only be changed
            when the group member's administrative state is 'disabled'.
            This object does not apply for an AO SMSC group."
        ::= { smscGroupMemberEntry 6 }

    smscGroupMemberThroughput OBJECT-TYPE
        SYNTAX  Throughput
        ACCESS  read-write
        STATUS  mandatory
        DESCRIPTION
            "Throughput constraint of an SMSC group member. No more than
            the specified number of messages per second are sent to the
            SMSC referenced by the SMSC group member for the referenced
            SMSC group. If the value is set to 0, no throughput limit
            is applied for this SMSC group member. The throughput limit
            of a group member can only be changed when the group member's
            administrative state is 'disabled'.
            This object does not apply for an AO SMSC group."
        ::= { smscGroupMemberEntry 7 }

    loadBalancingGroupTable OBJECT-TYPE
        SYNTAX  SEQUENCE OF LoadBalancingGroupEntry
        ACCESS  not-accessible
        STATUS  mandatory
        DESCRIPTION
            "Table of load balancing groups. The type parameter of each
            group specifies the type of instances that are grouped within
            the corresponding load balancing group."
        ::= { sms 65 }

    loadBalancingGroupEntry OBJECT-TYPE
        SYNTAX  LoadBalancingGroupEntry
        ACCESS  not-accessible
        STATUS  mandatory
        DESCRIPTION
            "A row in the loadBalancingGroupTable. Only load balancing
            groups with an administrative state of 'active' can be used
            and/or referenced."
        INDEX  { loadBalancingGroupIndex }
        ::= { loadBalancingGroupTable 1 }

    LoadBalancingGroupEntry ::=
        SEQUENCE {
            loadBalancingGroupIndex      LoadBalancingGroupTableIndex,
            loadBalancingGroupAdminState AdminState,
            loadBalancingGroupName       NameString,
            loadBalancingGroupType       GroupType,
            loadBalancingGroupCounter    Counter
        }

    loadBalancingGroupIndex OBJECT-TYPE
        SYNTAX  LoadBalancingGroupTableIndex
        ACCESS  read-write
        STATUS  mandatory
        DESCRIPTION
            "Index of entry in loadBalancingGroupTable."
        ::= { loadBalancingGroupEntry 1 }

    loadBalancingGroupAdminState OBJECT-TYPE
        SYNTAX  AdminState
        ACCESS  read-write
        STATUS  mandatory
        DESCRIPTION
            "Administrative state of the load balancing group. A group
            can only be used/referenced if its administrative state is
            active.
            In order to activate a group, the following conditions must
            be met:

                1) The group's name must be unique.
                2) The group's type must be valid.

            In order to delete a group, the following conditions must
            be met:

                1) The group must have no (more) members.

            "
        ::= { loadBalancingGroupEntry 2 }

    loadBalancingGroupName OBJECT-TYPE
        SYNTAX  NameString
        ACCESS  read-write
        STATUS  mandatory
        DESCRIPTION
            "Name of the load balancing group. The name can only be
            changed while the group is inactive. Each active group must
            have a unique name. By default, this parameter is set to the
            empty string."
        ::= { loadBalancingGroupEntry 3 }

    loadBalancingGroupType OBJECT-TYPE
        SYNTAX  GroupType
        ACCESS  read-write
        STATUS  mandatory
        DESCRIPTION
            "Type of the members of the group. All members of the group
            are of the same type. The type can only be changed while the
            group has no members. By default, this parameter is set to
            'undefined'."
        ::= { loadBalancingGroupEntry 4 }

    loadBalancingGroupCounter OBJECT-TYPE
        SYNTAX  Counter
        ACCESS  read-write
        STATUS  mandatory
        DESCRIPTION
            "Counter specifying how often the group has been requested to
            apply load balancing."
        ::= { loadBalancingGroupEntry 11 }


    loadBalancingGroupMemberTable OBJECT-TYPE
        SYNTAX  SEQUENCE OF LoadBalancingGroupMemberEntry
        ACCESS  not-accessible
        STATUS  mandatory
        DESCRIPTION
            "Table of load balancing group members. This table is used
            to assign members to a load balancing group."
        ::= { sms 66 }

    loadBalancingGroupMemberEntry OBJECT-TYPE
        SYNTAX  LoadBalancingGroupMemberEntry
        ACCESS  not-accessible
        STATUS  mandatory
        DESCRIPTION
            "A row in the loadBalancingGroupMemberTable."
        INDEX  { loadBalancingGroupMemberGroupIndex,
                 loadBalancingGroupMemberIndex }
        ::= { loadBalancingGroupMemberTable 1 }

    LoadBalancingGroupMemberEntry ::=
        SEQUENCE {
            loadBalancingGroupMemberGroupIndex LoadBalancingGroupTableIndex,
            loadBalancingGroupMemberIndex      LoadBalancingGroupMemberTableIndex,
            loadBalancingGroupMemberAdminState AdminState,
            loadBalancingGroupMemberPriority   Priority,
            loadBalancingGroupMemberWeight     Weight,
            loadBalancingGroupMemberCounter    Counter
        }

    loadBalancingGroupMemberGroupIndex OBJECT-TYPE
        SYNTAX  LoadBalancingGroupTableIndex
        ACCESS  read-write
        STATUS  mandatory
        DESCRIPTION
            "First index of the table, specifying the load balancing group,
            to which the member belongs."
        ::= { loadBalancingGroupMemberEntry 1 }

    loadBalancingGroupMemberIndex OBJECT-TYPE
        SYNTAX  LoadBalancingGroupMemberTableIndex
        ACCESS  read-write
        STATUS  mandatory
        DESCRIPTION
            "Second index of the table, specifying the instance that shall
            be a member of the load balancing group. The
            loadBalancingGroupTable's type parameter specifies the type of
            instance referred to."
        ::= { loadBalancingGroupMemberEntry 2 }

    loadBalancingGroupMemberAdminState OBJECT-TYPE
        SYNTAX  AdminState
        ACCESS  read-write
        STATUS  mandatory
        DESCRIPTION
            "Administrative state of the member. Inside the router, this
            parameter is used for the sole purpose of deleting a member
            from its group. A member can be deleted anytime."
        ::= { loadBalancingGroupMemberEntry 3 }

    loadBalancingGroupMemberPriority OBJECT-TYPE
        SYNTAX  Priority
        ACCESS  read-write
        STATUS  mandatory
        DESCRIPTION
            "The priority of the member inside the group. When the group
            is used for load balancing, only eligible members with the
            highest available priority are served. By default, a priority
            of 50 is used."
        ::= { loadBalancingGroupMemberEntry 11 }

    loadBalancingGroupMemberWeight OBJECT-TYPE
        SYNTAX  Weight
        ACCESS  read-write
        STATUS  mandatory
        DESCRIPTION
            "The weight of a member, relative to other member of the same
            group and priority. Load balancing is done relative to these
            weights: a member with weight 2 will be served twice as often
            as a member with weight 1. By default, a weight of 1 is used."
        ::= { loadBalancingGroupMemberEntry 12 }

    loadBalancingGroupMemberCounter OBJECT-TYPE
        SYNTAX  Counter
        ACCESS  read-write
        STATUS  mandatory
        DESCRIPTION
            "Counter specifying how often a group member has been selected
            during load balancing."
        ::= { loadBalancingGroupMemberEntry 21 }

    -- ExternalConditionTable
    externalConditionTable OBJECT-TYPE
        SYNTAX  SEQUENCE OF ExternalConditionEntry
        ACCESS  not-accessible
        STATUS  mandatory
        DESCRIPTION
            "A table containing properties and counters for each
            ExternalCondition.  ExternalConditions are external applications
            or processes that can be requested to validate the routing of a
            SM, via External Condition rules.
            For each ExternalCondition the fields that are passed to this
            external condition can be configured. On receipt of a
            validationRequest for a SM, the external condition process returns
            a evaluationResponse indicating True or False. The interpretation
            of this value is determined by the applicable External Condition
            rule.
            If modification of the SM by the external condition process is
            allowed, the evaluationResponse may also contain new values for
            the fields to be changed.
            "
        ::= { sms 71 }

    externalConditionEntry OBJECT-TYPE
        SYNTAX  ExternalConditionEntry
        ACCESS  not-accessible
        STATUS  mandatory
        DESCRIPTION
            "Table entry defining a single ExternalCondition."
        INDEX   { externalConditionIndex }
        ::= { externalConditionTable 1 }

    ExternalConditionEntry ::=
        SEQUENCE {
            externalConditionIndex                             ExternalConditionTableIndex,
            externalConditionAdminState                        AdminState,
            externalConditionName                              NameString,
            externalConditionUserIdentity                      EciUserIdentity,
            externalConditionPassword                          EciPassword,
            externalConditionModificationAllowed               Boolean,
            externalConditionMaxInactivityTime                 EciTimer,
            externalConditionMaxResponseTime                   EciTimer,
            externalConditionMaxSessions                       EciConnections,
            externalConditionThroughput                        Throughput,
            externalConditionFormatOriginator                  ApplicationAddressFormat,
            externalConditionFormatRecipient                   ApplicationAddressFormat,
            externalConditionFormatMsc                         ApplicationAddressFormat,
            externalConditionFormatSmsc                        ApplicationAddressFormat,
            externalConditionDefaultNotConnectedResponse       Boolean,
            externalConditionDefaultTimeoutResponse            Boolean,
            externalConditionDefaultInvalidResponseResponse    Boolean,
            externalConditionDefaultDisconnectResponse         Boolean,
            externalConditionDefaultThroughputExceededResponse Boolean,
            externalConditionSessionsCounter                   EciConnections,
            externalConditionTotalCounter                      Counter,
            externalConditionSuccessfulCounter                 Counter,
            externalConditionRejectedCounter                   Counter,
            externalConditionTimeoutCounter                    Counter,
            externalConditionDisconnectCounter                 Counter,
            externalConditionNotificationCounter               Counter,
            externalConditionDistributionKeyOriginatorAddress  Boolean,
            externalConditionDistributionKeyRecipientAddress   Boolean,
            externalConditionDistributionKeyCallingPartySCCPAddress Boolean,
            externalConditionIncludeOriginatorAddressField     Boolean,
            externalConditionIncludeOriginatorImsiField        Boolean,
            externalConditionIncludeOriginatingApplicationField Boolean,
            externalConditionIncludeRecipientAddressField      Boolean,
            externalConditionIncludeRecipientImsiField         Boolean,
            externalConditionIncludeOriginalSubmitTimeField    Boolean,
            externalConditionIncludeUniqueSubmitTimeField      Boolean,
            externalConditionIncludeLengthOfMessageField       Boolean,
            externalConditionIncludePriorityIndicatorField     Boolean,
            externalConditionIncludeUserDataHeaderIndicatorField Boolean,
            externalConditionIncludeMoreMessagesToSendIndicatorField Boolean,
            externalConditionIncludeSingleShotIndicatorField   Boolean,
            externalConditionIncludeReplyPathIndicatorField    Boolean,
            externalConditionIncludeNotificationRequestField   Boolean,
            externalConditionIncludeValidityPeriodField        Boolean,
            externalConditionIncludeDeferPeriodField           Boolean,
            externalConditionIncludeCalledPartyAddressField    Boolean,
            externalConditionIncludeDestinationPointCodeField  Boolean,
            externalConditionIncludeCallingPartyAddressField   Boolean,
            externalConditionIncludeOriginatingPointCodeField  Boolean,
            externalConditionIncludeProtocolIdField            Boolean,
            externalConditionIncludeConsolidationField         Boolean,
            externalConditionIncludeBillingIdentifierField     Boolean,
            externalConditionIncludeCmReferenceNumberField     Boolean,
            externalConditionIncludeCmCurrentSegmentField      Boolean,
            externalConditionIncludeCmTotalSegmentsField       Boolean,
            externalConditionIncludeTariffClassField           Boolean,
            externalConditionIncludeServiceDescriptionField    Boolean,
            externalConditionIncludeDataCodingSchemeField      Boolean,
            externalConditionIncludeUserDataField              Boolean,
            externalConditionIncludeUserDataHeaderField        Boolean,
            externalConditionIncludeDeliveryStatusField        Boolean,
            externalConditionIncludeNotificationAddressField   Boolean,
            externalConditionIncludeNotificationPidField       Boolean,
            externalConditionIncludeNotificationTypeField      Boolean,
            externalConditionIncludeDeliveryTimeField          Boolean,
            externalConditionIncludeSmscAddressField           Boolean,
            externalConditionIncludeMscAddressField            Boolean,
            externalConditionIncludeSgsnAddressField           Boolean,
            externalConditionIncludeTcapTransactionIdField     Boolean,
            externalConditionIncludeLmsiField                  Boolean,
            externalConditionIncludeMwStatusField              Boolean,
            externalConditionIncludeHlrErrorField              Boolean,
            externalConditionIncludeSelectedExternalConditionRuleField     Boolean,
            externalConditionIncludeAlphanumericOriginatorField Boolean,
            externalConditionIncludeAlphanumericRecipientField Boolean,
            externalConditionIncludeStatusReportInfoField      Boolean,
            externalConditionIncludeSmppMessageIdField         Boolean,
            externalConditionIncludeBillingInfoField           Boolean,
            externalConditionIncludeApplicationProtocolField   Boolean,
            externalConditionIncludeApplicationPortField       Boolean,
            externalConditionIncludeChargeIndicationField      Boolean,
            externalConditionIncludeExternalAttributesField    Boolean,
            externalConditionIncludeRecipientRoutingNumberField Boolean,
            externalConditionIncludeContentRatingField         Boolean,
            externalConditionIncludeTerminatingApplicationField Boolean,
            externalConditionIncludeOriginatorApplicationChargingUnitsField Boolean,
            externalConditionIncludeRecipientApplicationChargingUnitsField Boolean,
            externalConditionIncludeXsServiceIndicatorField    Boolean
        }

    externalConditionIndex OBJECT-TYPE
        SYNTAX  ExternalConditionTableIndex
        ACCESS  read-write
        STATUS  mandatory
        DESCRIPTION
            "Index of entry in ExternalCondition table."
        ::= { externalConditionEntry 1 }

    externalConditionAdminState OBJECT-TYPE
        SYNTAX  AdminState
        ACCESS  read-write
        STATUS  mandatory
        DESCRIPTION
            "Administrative state of the ExternalCondition.

            Transition from 'inactive' to 'active' is only possible when:
            1) name has been supplied;
            2) name is not already in use by another external condition;
            3) userIdentity has been supplied and is unique;

            For details, refer to the comment on the AdminState type."
        ::= { externalConditionEntry 2 }

    externalConditionName OBJECT-TYPE
        SYNTAX  NameString
        ACCESS  read-write
        STATUS  mandatory
        DESCRIPTION
            "Name of the ExternalCondition."
        ::= { externalConditionEntry 3 }

    externalConditionUserIdentity OBJECT-TYPE
        SYNTAX  EciUserIdentity
        ACCESS  read-write
        STATUS  mandatory
        DESCRIPTION
            "User identity of the ExternalCondition. The external condition
            application will use this identity during authorization after
            connecting to the TextPass device."
        ::= { externalConditionEntry 4 }

    externalConditionPassword OBJECT-TYPE
        SYNTAX  EciPassword
        ACCESS  read-write
        STATUS  mandatory
        DESCRIPTION
            "Password of the ExternalCondition. The external condition
            application will use this password during authorization after
            connecting to the TextPass device."
        ::= { externalConditionEntry 5 }

    externalConditionModificationAllowed OBJECT-TYPE
        SYNTAX  Boolean
        ACCESS  read-write
        STATUS  mandatory
        DESCRIPTION
            "Flag indicating whether or not the external condition application
            is allowed to modify one or more fields of the SM. If set to True,
            the external condition application may include new values for the
            fields it wants to change in the evaluationResponse message.
            Default is False."
        ::= { externalConditionEntry 6 }

    externalConditionMaxInactivityTime OBJECT-TYPE
        SYNTAX  EciTimer
        ACCESS  read-write
        STATUS  mandatory
        DESCRIPTION
            "Maximum time span, expressed in seconds, that a link to an
            external condition application is idle before TextPass
            disconnects it."
        ::= { externalConditionEntry 10 }

    externalConditionMaxResponseTime OBJECT-TYPE
        SYNTAX  EciTimer
        ACCESS  read-write
        STATUS  mandatory
        DESCRIPTION
            "Maximum time span, expressed in seconds, that TextPass waits for
            a response from an external condition application before it
            considers the relating request as timed out.
            When set to zero, TextPass does not wait for a response message."
        ::= { externalConditionEntry 11 }

    externalConditionMaxSessions OBJECT-TYPE
        SYNTAX  EciConnections
        ACCESS  read-write
        STATUS  mandatory
        DESCRIPTION
            "Maximum number of connections links between TextPass and the
            external condition application. By default, a limit of 128
            sessions is used."
        ::= { externalConditionEntry 12 }

    externalConditionThroughput OBJECT-TYPE
        SYNTAX  Throughput
        ACCESS  read-write
        STATUS  mandatory
        DESCRIPTION
            "Maximum number of evaluationRequests per second allowed for an
            externalConditionApplication. When the maximum throughput is
            reached, the DefaultThroughputExceededResponse is applied.
            Zero means unlimited. Default is 0 (unlimited)."
        ::= { externalConditionEntry 13 }

    externalConditionFormatOriginator OBJECT-TYPE
        SYNTAX  ApplicationAddressFormat
        ACCESS  read-write
        STATUS  mandatory
        DESCRIPTION
            "Indicator specifying how the originator should be specified in
            an ECI request. When the value is equal to 'asSystemWideSetting',
            the format as specified by smsPropFormatEciOriginator is taken.
            Default is 'asSystemWideSetting'."
        ::= { externalConditionEntry 14 }

    externalConditionFormatRecipient OBJECT-TYPE
        SYNTAX  ApplicationAddressFormat
        ACCESS  read-write
        STATUS  mandatory
        DESCRIPTION
            "Indicator specifying how the recipient should be specified in an
            ECI request. When the value is equal to 'asSystemWideSetting',
            the format as specified by smsPropFormatEciRecipient is taken.
            Default is 'asSystemWideSetting'."
        ::= { externalConditionEntry 15 }

    externalConditionFormatMsc OBJECT-TYPE
        SYNTAX  ApplicationAddressFormat
        ACCESS  read-write
        STATUS  mandatory
        DESCRIPTION
            "Indicator specifying how the MSC should be specified in an ECI
            request. When the value is equal to 'asSystemWideSetting', the 
            format as specified by smsPropFormatEciMsc is taken. Default is 
            'asSystemWideSetting'."
        ::= { externalConditionEntry 16 }

    externalConditionFormatSmsc OBJECT-TYPE
        SYNTAX  ApplicationAddressFormat
        ACCESS  read-write
        STATUS  mandatory
        DESCRIPTION
            "Indicator specifying how the SMSC should be specified in an
             ECI request. When the value is equal to 'asSystemWideSetting', 
             the format as specified by  smsPropFormatEciSmsc is taken. 
             Default is 'asSystemWideSetting'."
        ::= { externalConditionEntry 17 }

    externalConditionDefaultNotConnectedResponse OBJECT-TYPE
        SYNTAX  Boolean
        ACCESS  read-write
        STATUS  mandatory
        DESCRIPTION
            "Specifies what value should be assumed for the
            evaluationResult field of the evaluationResponse message if
            the evaluation of the external condition can not be requested
            because the EC application is not connected. By default, a
            result of 'true' is assumed."
        ::= { externalConditionEntry 21 }

    externalConditionDefaultTimeoutResponse OBJECT-TYPE
        SYNTAX  Boolean
        ACCESS  read-write
        STATUS  mandatory
        DESCRIPTION
            "Specifies what value should be assumed for the
            evaluationResult field of the evaluationResponse message if
            the evaluation of the external condition timed out. By default,
            a result of 'true' is assumed."
        ::= { externalConditionEntry 22 }

    externalConditionDefaultInvalidResponseResponse OBJECT-TYPE
        SYNTAX  Boolean
        ACCESS  read-write
        STATUS  mandatory
        DESCRIPTION
            "Specifies what value should be assumed for the
            evaluationResult field of the evaluationResponse message if
            the evaluation of the external condition resulted in receiving
            an invalid evaluationResponse message. By default, a result of
            'true' is assumed."
        ::= { externalConditionEntry 23 }

    externalConditionDefaultDisconnectResponse OBJECT-TYPE
        SYNTAX  Boolean
        ACCESS  read-write
        STATUS  mandatory
        DESCRIPTION
            "Specifies what value should be assumed for the
            evaluationResult field of the evaluationResponse message if
            the EC application disconnects while the evaluation of the
            external condition is pending. By default, a result of
            'true' is assumed."
        ::= { externalConditionEntry 24 }

    externalConditionDefaultThroughputExceededResponse OBJECT-TYPE
        SYNTAX  Boolean
        ACCESS  read-write
        STATUS  mandatory
        DESCRIPTION
            "Specifies what value should be assumed for the
            evaluationResult field of the evaluationResponse message if
            the evaluation of the external condition can not be requested
            when the throughput limit of the EC application is reached.
            By default, a result of 'true' is assumed."
        ::= { externalConditionEntry 25 }

    externalConditionSessionsCounter OBJECT-TYPE
        SYNTAX  EciConnections
        ACCESS  read-only
        STATUS  mandatory
        DESCRIPTION
            "Number of sessions currently established between TextPass and
            the external condition application."
        ::= { externalConditionEntry 31 }

    externalConditionTotalCounter OBJECT-TYPE
        SYNTAX  Counter
        ACCESS  read-write
        STATUS  mandatory
        DESCRIPTION
            "Total number of validationRequests sent to the External Condition
            application."
        ::= { externalConditionEntry 32 }


    externalConditionSuccessfulCounter OBJECT-TYPE
        SYNTAX  Counter
        ACCESS  read-write
        STATUS  mandatory
        DESCRIPTION
            "Number of validationRequests to which the External Condition
            application has responded with True."
        ::= { externalConditionEntry 33 }

    externalConditionRejectedCounter OBJECT-TYPE
        SYNTAX  Counter
        ACCESS  read-write
        STATUS  mandatory
        DESCRIPTION
            "Number of validationRequests to which the External Condition
            application has responded with False."
        ::= { externalConditionEntry 34 }

    externalConditionTimeoutCounter OBJECT-TYPE
        SYNTAX  Counter
        ACCESS  read-write
        STATUS  mandatory
        DESCRIPTION
            "Number of validationRequests to which the External Condition
            application has not responded within the specified
            MaxResponseTime."
        ::= { externalConditionEntry 35 }

    externalConditionDisconnectCounter OBJECT-TYPE
        SYNTAX  Counter
        ACCESS  read-write
        STATUS  mandatory
        DESCRIPTION
            "Number of validationRequests to which the External Condition
            application has not responded due to the session being
            disconnected."
        ::= { externalConditionEntry 36 }

    externalConditionNotificationCounter OBJECT-TYPE
        SYNTAX  Counter
        ACCESS  read-write
        STATUS  mandatory
        DESCRIPTION
            "Number of validationResponses in which the External Condition
            application has indicated that it wants to receive a notification
            of the routing result of the SM."
        ::= { externalConditionEntry 37 }

    externalConditionDistributionKeyOriginatorAddress OBJECT-TYPE
        SYNTAX  Boolean
        ACCESS  read-write
        STATUS  mandatory
        DESCRIPTION
            "If true, use the originator address as a key to
             calculate load distribution. 
             Can be used together with other key(s).
             The key can ONLY be selected if at least one IP Address
             is provisioned in the externalConditionIPTable for this
             entry."
        ::= { externalConditionEntry 48 }

    externalConditionDistributionKeyRecipientAddress OBJECT-TYPE
        SYNTAX  Boolean
        ACCESS  read-write
        STATUS  mandatory
        DESCRIPTION
            "If true, use the recipient address as a key to
             calculate load distribution. 
             Can be used together with other key(s).
             The key can ONLY be selected if at least one IP Address
             is provisioned in the externalConditionIPTable for this
             entry."
        ::= { externalConditionEntry 49 }

    externalConditionDistributionKeyCallingPartySCCPAddress OBJECT-TYPE
        SYNTAX  Boolean
        ACCESS  read-write
        STATUS  mandatory
        DESCRIPTION
            "If true, use the CallingPartySCCPAddress as a key to
             calculate load distribution. 
             Can be used together with other key(s).
             The key can ONLY be selected if at least one IP Address
             is provisioned in the externalConditionIPTable for this
             entry."
        ::= { externalConditionEntry 50 }

    externalConditionIncludeOriginatorAddressField OBJECT-TYPE
        SYNTAX  Boolean
        ACCESS  read-write
        STATUS  mandatory
        DESCRIPTION
            "Indicator specifying whether the field 'originatorAddress'
            should be included in the validationRequest or not.
            By default, the field is included."
        ::= { externalConditionEntry 51 }

    externalConditionIncludeOriginatorImsiField OBJECT-TYPE
        SYNTAX  Boolean
        ACCESS  read-write
        STATUS  mandatory
        DESCRIPTION
            "Indicator specifying whether the field 'originatorImsi'
            should be included in the validationRequest or not.
            By default, the field is not included."
        ::= { externalConditionEntry 52 }

    externalConditionIncludeOriginatingApplicationField OBJECT-TYPE
        SYNTAX  Boolean
        ACCESS  read-write
        STATUS  mandatory
        DESCRIPTION
            "Indicator specifying whether the field 'originatingApplication'
            should be included in the validationRequest or not.
            By default, the field is not included."
        ::= { externalConditionEntry 53 }

    externalConditionIncludeRecipientAddressField OBJECT-TYPE
        SYNTAX  Boolean
        ACCESS  read-write
        STATUS  mandatory
        DESCRIPTION
            "Indicator specifying whether the field 'recipientAddress'
            should be included in the validationRequest or not.
            By default, the field is not included."
        ::= { externalConditionEntry 54 }

    externalConditionIncludeRecipientImsiField OBJECT-TYPE
        SYNTAX  Boolean
        ACCESS  read-write
        STATUS  mandatory
        DESCRIPTION
            "Indicator specifying whether the field 'recipientImsi'
            should be included in the validationRequest or not.
            By default, the field is not included."
        ::= { externalConditionEntry 55 }

    externalConditionIncludeOriginalSubmitTimeField OBJECT-TYPE
        SYNTAX  Boolean
        ACCESS  read-write
        STATUS  mandatory
        DESCRIPTION
            "Indicator specifying whether the field 'originalSubmitTime'
            should be included in the validationRequest or not.
            By default, the field is not included."
        ::= { externalConditionEntry 56 }

    externalConditionIncludeUniqueSubmitTimeField OBJECT-TYPE
        SYNTAX  Boolean
        ACCESS  read-write
        STATUS  mandatory
        DESCRIPTION
            "Indicator specifying whether the field 'uniqueSubmitTime'
            should be included in the validationRequest or not.
            By default, the field is not included."
        ::= { externalConditionEntry 57 }

    externalConditionIncludeLengthOfMessageField OBJECT-TYPE
        SYNTAX  Boolean
        ACCESS  read-write
        STATUS  mandatory
        DESCRIPTION
            "Indicator specifying whether the field 'lengthOfMessage'
            should be included in the validationRequest or not.
            By default, the field is not included."
        ::= { externalConditionEntry 58 }

    externalConditionIncludePriorityIndicatorField OBJECT-TYPE
        SYNTAX  Boolean
        ACCESS  read-write
        STATUS  mandatory
        DESCRIPTION
            "Indicator specifying whether the field 'priotityIndicator'
            should be included in the validationRequest or not.
            By default, the field is not included."
        ::= { externalConditionEntry 59 }

    externalConditionIncludeUserDataHeaderIndicatorField OBJECT-TYPE
        SYNTAX  Boolean
        ACCESS  read-write
        STATUS  mandatory
        DESCRIPTION
            "Indicator specifying whether the field 'userDataHeaderIndicator'
            should be included in the validationRequest or not.
            By default, the field is not included."
        ::= { externalConditionEntry 60 }

    externalConditionIncludeMoreMessagesToSendIndicatorField OBJECT-TYPE
        SYNTAX  Boolean
        ACCESS  read-write
        STATUS  mandatory
        DESCRIPTION
            "Indicator specifying whether the field
            'moreMessagesToSendIndicator' should be included in the
            validationRequest or not.
            By default, the field is not included."
        ::= { externalConditionEntry 61 }

    externalConditionIncludeSingleShotIndicatorField OBJECT-TYPE
        SYNTAX  Boolean
        ACCESS  read-write
        STATUS  mandatory
        DESCRIPTION
            "Indicator specifying whether the field 'singleShotIndicator'
            should be included in the validationRequest or not.
            By default, the field is not included."
        ::= { externalConditionEntry 62 }

    externalConditionIncludeReplyPathIndicatorField OBJECT-TYPE
        SYNTAX  Boolean
        ACCESS  read-write
        STATUS  mandatory
        DESCRIPTION
            "Indicator specifying whether the field 'replyPathIndicator'
            should be included in the validationRequest or not.
            By default, the field is not included."
        ::= { externalConditionEntry 63 }

    externalConditionIncludeNotificationRequestField OBJECT-TYPE
        SYNTAX  Boolean
        ACCESS  read-write
        STATUS  mandatory
        DESCRIPTION
            "Indicator specifying whether the field 'notificationRequest'
            should be included in the validationRequest or not.
            By default, the field is not included."
        ::= { externalConditionEntry 64 }

    externalConditionIncludeValidityPeriodField OBJECT-TYPE
        SYNTAX  Boolean
        ACCESS  read-write
        STATUS  mandatory
        DESCRIPTION
            "Indicator specifying whether the field 'validityPeriod'
            should be included in the validationRequest or not.
            By default, the field is not included."
        ::= { externalConditionEntry 65 }

    externalConditionIncludeDeferPeriodField OBJECT-TYPE
        SYNTAX  Boolean
        ACCESS  read-write
        STATUS  mandatory
        DESCRIPTION
            "Indicator specifying whether the field 'deferPerid'
            should be included in the validationRequest or not.
            By default, the field is not included."
        ::= { externalConditionEntry 66 }

    externalConditionIncludeCalledPartyAddressField OBJECT-TYPE
        SYNTAX  Boolean
        ACCESS  read-write
        STATUS  mandatory
        DESCRIPTION
            "Indicator specifying whether the field 'calledPartyAddress'
            should be included in the validationRequest or not.
            By default, the field is not included."
        ::= { externalConditionEntry 67 }

    externalConditionIncludeDestinationPointCodeField OBJECT-TYPE
        SYNTAX  Boolean
        ACCESS  read-write
        STATUS  mandatory
        DESCRIPTION
            "Indicator specifying whether the field 'destinationPointCode'
            should be included in the validationRequest or not.
            By default, the field is not included."
        ::= { externalConditionEntry 68 }

    externalConditionIncludeCallingPartyAddressField OBJECT-TYPE
        SYNTAX  Boolean
        ACCESS  read-write
        STATUS  mandatory
        DESCRIPTION
            "Indicator specifying whether the field 'callingPartyAddress'
            should be included in the validationRequest or not.
            By default, the field is not included."
        ::= { externalConditionEntry 69 }

    externalConditionIncludeOriginatingPointCodeField OBJECT-TYPE
        SYNTAX  Boolean
        ACCESS  read-write
        STATUS  mandatory
        DESCRIPTION
            "Indicator specifying whether the field 'originatingPointCode'
            should be included in the validationRequest or not.
            By default, the field is not included."
        ::= { externalConditionEntry 70 }

    externalConditionIncludeProtocolIdField OBJECT-TYPE
        SYNTAX  Boolean
        ACCESS  read-write
        STATUS  mandatory
        DESCRIPTION
            "Indicator specifying whether the field 'protocolId'
            should be included in the validationRequest or not.
            By default, the field is not included."
        ::= { externalConditionEntry 71 }

    externalConditionIncludeConsolidationField OBJECT-TYPE
        SYNTAX  Boolean
        ACCESS  read-write
        STATUS  mandatory
        DESCRIPTION
            "Indicator specifying whether the field 'consolidation'
            should be included in the validationRequest or not.
            By default, the field is not included."
        ::= { externalConditionEntry 72 }

    externalConditionIncludeBillingIdentifierField OBJECT-TYPE
        SYNTAX  Boolean
        ACCESS  read-write
        STATUS  mandatory
        DESCRIPTION
            "Indicator specifying whether the field 'billingIdentifier'
            should be included in the validationRequest or not.
            By default, the field is not included."
        ::= { externalConditionEntry 73 }

    externalConditionIncludeCmReferenceNumberField OBJECT-TYPE
        SYNTAX  Boolean
        ACCESS  read-write
        STATUS  mandatory
        DESCRIPTION
            "Indicator specifying whether the field 'cmReferenceNumber'
            should be included in the validationRequest or not.
            By default, the field is not included."
        ::= { externalConditionEntry 74 }

    externalConditionIncludeCmCurrentSegmentField OBJECT-TYPE
        SYNTAX  Boolean
        ACCESS  read-write
        STATUS  mandatory
        DESCRIPTION
            "Indicator specifying whether the field 'cmCurrentSegment'
            should be included in the validationRequest or not.
            By default, the field is not included."
        ::= { externalConditionEntry 75 }

    externalConditionIncludeCmTotalSegmentsField OBJECT-TYPE
        SYNTAX  Boolean
        ACCESS  read-write
        STATUS  mandatory
        DESCRIPTION
            "Indicator specifying whether the field 'cmTotalSegments'
            should be included in the validationRequest or not.
            By default, the field is not included."
        ::= { externalConditionEntry 76 }

    externalConditionIncludeTariffClassField OBJECT-TYPE
        SYNTAX  Boolean
        ACCESS  read-write
        STATUS  mandatory
        DESCRIPTION
            "Indicator specifying whether the field 'tariffClass'
            should be included in the validationRequest or not.
            By default, the field is not included."
        ::= { externalConditionEntry 77 }

    externalConditionIncludeServiceDescriptionField OBJECT-TYPE
        SYNTAX  Boolean
        ACCESS  read-write
        STATUS  mandatory
        DESCRIPTION
            "Indicator specifying whether the field 'serviceDescription'
            should be included in the validationRequest or not.
            By default, the field is not included."
        ::= { externalConditionEntry 78 }

    externalConditionIncludeDataCodingSchemeField OBJECT-TYPE
        SYNTAX  Boolean
        ACCESS  read-write
        STATUS  mandatory
        DESCRIPTION
            "Indicator specifying whether the field 'dataCodingScheme'
            should be included in the validationRequest or not.
            By default, the field is not included."
        ::= { externalConditionEntry 79 }

    externalConditionIncludeUserDataField OBJECT-TYPE
        SYNTAX  Boolean
        ACCESS  read-write
        STATUS  mandatory
        DESCRIPTION
            "Indicator specifying whether the field 'userData'
            should be included in the validationRequest or not.
            By default, the field is not included."
        ::= { externalConditionEntry 80 }

    externalConditionIncludeUserDataHeaderField OBJECT-TYPE
        SYNTAX  Boolean
        ACCESS  read-write
        STATUS  mandatory

        DESCRIPTION
            "Indicator specifying whether the field 'userDataHeader'
            should be included in the validationRequest or not.
            By default, the field is not included."
        ::= { externalConditionEntry 81 }

    externalConditionIncludeDeliveryStatusField OBJECT-TYPE
        SYNTAX  Boolean
        ACCESS  read-write
        STATUS  mandatory
        DESCRIPTION
            "Indicator specifying whether the field 'deliveryStatus'
            should be included in the validationRequest or not.
            By default, the field is not included."
        ::= { externalConditionEntry 82 }

    externalConditionIncludeNotificationAddressField OBJECT-TYPE
        SYNTAX  Boolean
        ACCESS  read-write
        STATUS  mandatory
        DESCRIPTION
            "Indicator specifying whether the field 'notificationAddress'
            should be included in the validationRequest or not.
            By default, the field is not included."
        ::= { externalConditionEntry 84 }

    externalConditionIncludeNotificationPidField OBJECT-TYPE
        SYNTAX  Boolean
        ACCESS  read-write
        STATUS  mandatory
        DESCRIPTION
            "Indicator specifying whether the field 'notificationPid'
            should be included in the validationRequest or not.
            By default, the field is not included."
        ::= { externalConditionEntry 85 }

    externalConditionIncludeNotificationTypeField OBJECT-TYPE
        SYNTAX  Boolean
        ACCESS  read-write
        STATUS  mandatory
        DESCRIPTION
            "Indicator specifying whether the field 'notificationType'
            should be included in the validationRequest or not.
            By default, the field is not included."
        ::= { externalConditionEntry 86 }

    externalConditionIncludeDeliveryTimeField OBJECT-TYPE
        SYNTAX  Boolean
        ACCESS  read-write
        STATUS  mandatory
        DESCRIPTION
            "Indicator specifying whether the field 'deliveryTime'
            should be included in the validationRequest or not.
            By default, the field is not included."
        ::= { externalConditionEntry 87 }

     externalConditionIncludeSmscAddressField OBJECT-TYPE
        SYNTAX  Boolean
        ACCESS  read-write
        STATUS  mandatory
        DESCRIPTION
            "Indicator specifying whether the field 'smscAddress'
            should be included in the validationRequest or not.
            By default, the field is not included."
        ::= { externalConditionEntry 88 }

     externalConditionIncludeMscAddressField OBJECT-TYPE
        SYNTAX  Boolean
        ACCESS  read-write
        STATUS  mandatory
        DESCRIPTION
            "Indicator specifying whether the field 'mscAddress'
            should be included in the validationRequest or not.
            By default, the field is not included."
        ::= { externalConditionEntry 89 }

     externalConditionIncludeSgsnAddressField OBJECT-TYPE
        SYNTAX  Boolean
        ACCESS  read-write
        STATUS  mandatory
        DESCRIPTION
            "Indicator specifying whether the field 'sgsnAddress'
            should be included in the validationRequest or not.
            By default, the field is not included."
        ::= { externalConditionEntry 90 }

     externalConditionIncludeTcapTransactionIdField OBJECT-TYPE
        SYNTAX  Boolean
        ACCESS  read-write
        STATUS  mandatory
        DESCRIPTION
            "Indicator specifying whether the field 'tcapTransactionId'
            should be included in the validationRequest or not.
            By default, the field is not included."
        ::= { externalConditionEntry 91 }

     externalConditionIncludeLmsiField OBJECT-TYPE
        SYNTAX  Boolean
        ACCESS  read-write
        STATUS  mandatory
        DESCRIPTION
            "Indicator specifying whether the field 'lmsi'
            should be included in the validationRequest or not.
            By default, the field is not included."
        ::= { externalConditionEntry 92 }

     externalConditionIncludeMwStatusField OBJECT-TYPE
        SYNTAX  Boolean
        ACCESS  read-write
        STATUS  mandatory
        DESCRIPTION
            "Indicator specifying whether the field 'mwStatus'
            should be included in the validationRequest or not.
            By default, the field is not included."
        ::= { externalConditionEntry 93 }

     externalConditionIncludeHlrErrorField OBJECT-TYPE
        SYNTAX  Boolean
        ACCESS  read-write
        STATUS  mandatory
        DESCRIPTION
            "Indicator specifying whether the field 'hlrError'
            should be included in the validationRequest or not.
            By default, the field is not included."
        ::= { externalConditionEntry 94 }

     externalConditionIncludeSelectedExternalConditionRuleField OBJECT-TYPE
        SYNTAX  Boolean
        ACCESS  read-write
        STATUS  mandatory
        DESCRIPTION
            "Indicator specifying whether the field
            'selectedExternalConditionRule' should be included in the
            validationRequest or not.
            By default, the field is not included."
        ::= { externalConditionEntry 96 }

     externalConditionIncludeAlphanumericOriginatorField OBJECT-TYPE
        SYNTAX  Boolean
        ACCESS  read-write
        STATUS  mandatory
        DESCRIPTION
            "Indicator specifying whether the field 'alphanumericOriginator'
            should be included in the validationRequest or not.
            By default, the field is not included."
        ::= { externalConditionEntry 97 }

     externalConditionIncludeAlphanumericRecipientField OBJECT-TYPE
        SYNTAX  Boolean
        ACCESS  read-write
        STATUS  mandatory
        DESCRIPTION
            "Indicator specifying whether the field 'alphanumericRecipient'
            should be included in the validationRequest or not.
            By default, the field is not included."
        ::= { externalConditionEntry 98 }

    externalConditionIncludeStatusReportInfoField OBJECT-TYPE
        SYNTAX  Boolean
        ACCESS  read-write
        STATUS  mandatory
        DESCRIPTION
            "Indicator specifying whether the field 'statusReportInfo'
            should be included in the validationRequest or not.
            By default, the field is not included."
        ::= { externalConditionEntry 99 }


    externalConditionIncludeSmppMessageIdField OBJECT-TYPE
        SYNTAX  Boolean
        ACCESS  read-write
        STATUS  mandatory
        DESCRIPTION
            "Indicator specifying whether the field 'smppMessageInfo'
            should be included in the validationRequest or not.
            By default, the field is not included."
        ::= { externalConditionEntry 100 }

    externalConditionIncludeBillingInfoField OBJECT-TYPE
        SYNTAX  Boolean
        ACCESS  read-write
        STATUS  mandatory
        DESCRIPTION
            "Indicator specifying whether the field 'billingInfo'
            should be included in the evaluationRequest or not.
            By default, the field is not included."
        ::= { externalConditionEntry 101 }

    externalConditionIncludeApplicationProtocolField OBJECT-TYPE
        SYNTAX  Boolean
        ACCESS  read-write
        STATUS  mandatory
        DESCRIPTION
            "Indicator specifying whether the field 'applicationProtocol'
            should be included in the evaluationRequest or not.
            By default, the field is not included."
        ::= { externalConditionEntry 102 }

    externalConditionIncludeApplicationPortField OBJECT-TYPE
        SYNTAX  Boolean
        ACCESS  read-write
        STATUS  mandatory
        DESCRIPTION
            "Indicator specifying whether the field 'applicationPort'
            should be included in the evaluationRequest or not.
            By default, the field is not included."
        ::= { externalConditionEntry 103 }

    externalConditionIncludeChargeIndicationField OBJECT-TYPE
        SYNTAX  Boolean
        ACCESS  read-write
        STATUS  mandatory
        DESCRIPTION
            "Indicator specifying whether the field 'chargeIndication'
            should be included in the evaluationRequest or not.
            By default, the field is not included."
        ::= { externalConditionEntry 104 }

    externalConditionIncludeExternalAttributesField OBJECT-TYPE
        SYNTAX  Boolean
        ACCESS  read-write
        STATUS  mandatory
        DESCRIPTION
            "Indicator specifying whether the field 'externalAttributes'
            should be included in the evaluationRequest or not.
            By default, the field is not included."
        ::= { externalConditionEntry 105 }

    externalConditionIncludeRecipientRoutingNumberField OBJECT-TYPE
        SYNTAX  Boolean
        ACCESS  read-write
        STATUS  mandatory
        DESCRIPTION
            "Indicator specifying whether the field 'recipientRoutingNumber'
            should be included in the evaluationRequest or not.
            By default, the field is not included."
        ::= { externalConditionEntry 106 }

    externalConditionIncludeContentRatingField OBJECT-TYPE
        SYNTAX  Boolean
        ACCESS  read-write
        STATUS  mandatory
        DESCRIPTION
            "Indicator specifying whether the field 'contentRating'
            should be included in the evaluationRequest or not.
            By default, the field is not included."
        ::= { externalConditionEntry 107 }

    externalConditionIncludeTerminatingApplicationField OBJECT-TYPE
        SYNTAX  Boolean
        ACCESS  read-write
        STATUS  mandatory
        DESCRIPTION
            "Indicator specifying whether the field 'terminatingApplication'
            should be included in the evaluationRequest or not.
            By default, the field is not included."
        ::= { externalConditionEntry 108 }
        
    externalConditionIncludeOriginatorApplicationChargingUnitsField OBJECT-TYPE
        SYNTAX  Boolean
        ACCESS  read-write
        STATUS  mandatory
        DESCRIPTION
            "Indicator specifying whether the field 
            'applicationOriginatorChargingUnits'
            should be included in the evaluationRequest or not.
            By default, the field is not included."
        ::= { externalConditionEntry 109 }

    externalConditionIncludeRecipientApplicationChargingUnitsField OBJECT-TYPE
        SYNTAX  Boolean
        ACCESS  read-write
        STATUS  mandatory
        DESCRIPTION
            "Indicator specifying whether the field 
            'applicationRecipientChargingUnits'
            should be included in the evaluationRequest or not.
            By default, the field is not included."
        ::= { externalConditionEntry 110 }

    externalConditionIncludeXsServiceIndicatorField OBJECT-TYPE
        SYNTAX  Boolean
        ACCESS  read-write
        STATUS  mandatory
        DESCRIPTION
            "Indicator specifying whether the field 
            'XsServiceIndicator' 
            should be included in the evaluationRequest or not.
            By default, the field is not included."
        ::= { externalConditionEntry 111 }


    externalConditionAttributeTable OBJECT-TYPE
        SYNTAX  SEQUENCE OF ExternalConditionAttributeEntry
        ACCESS  not-accessible
        STATUS  mandatory
        DESCRIPTION
            "A table containing the name and counters 
            for the external condition attributes."
        ::= { sms 72 }

    externalConditionAttributeEntry OBJECT-TYPE
        SYNTAX  ExternalConditionAttributeEntry
        ACCESS  not-accessible
        STATUS  mandatory
        DESCRIPTION
            "Table entry specifying a single external condition attribute."
        INDEX   { externalConditionAttributeIndex }
        ::= { externalConditionAttributeTable 1 }

    ExternalConditionAttributeEntry ::=
        SEQUENCE {
            externalConditionAttributeIndex       ExternalConditionAttributeTableIndex,
            externalConditionAttributeName        NameString,
            externalConditionAttributeSetCounter  Counter,
            externalConditionAttributeResetCounter Counter
        }

    externalConditionAttributeIndex OBJECT-TYPE
        SYNTAX  ExternalConditionAttributeTableIndex
        ACCESS  read-write
        STATUS  mandatory
        DESCRIPTION
            "Index of entry in the external condition attribute table."
        ::= { externalConditionAttributeEntry 1 }

    externalConditionAttributeName OBJECT-TYPE
        SYNTAX  NameString
        ACCESS  read-write
        STATUS  mandatory
        DESCRIPTION
            "Name of this attribute."
        ::= { externalConditionAttributeEntry 2 }

    externalConditionAttributeSetCounter OBJECT-TYPE
        SYNTAX  Counter
        ACCESS  read-write
        STATUS  mandatory
        DESCRIPTION
            "Counter for set operations applied to this attribute."
        ::= { externalConditionAttributeEntry 3 }

    externalConditionAttributeResetCounter OBJECT-TYPE
        SYNTAX  Counter
        ACCESS  read-write
        STATUS  mandatory
        DESCRIPTION
            "Counter for reset operations applied to this attribute."
        ::= { externalConditionAttributeEntry 4 }

        -- externalConditionMessageTable
    
    externalConditionMessageTable OBJECT-TYPE
        SYNTAX  SEQUENCE OF ExternalConditionMessageEntry
        ACCESS  not-accessible
        STATUS  mandatory
        DESCRIPTION
            "A table containing text templates for notification messages
            to be generated based on a certain evaluation response of an
            EC application (external condition)."
        ::= { sms 73 }

    externalConditionMessageEntry OBJECT-TYPE
        SYNTAX  ExternalConditionMessageEntry
        ACCESS  not-accessible
        STATUS  mandatory
        DESCRIPTION
            "Table entry defining a single externalConditionMessage."
        INDEX   { externalConditionMessageIndex }
        ::= { externalConditionMessageTable 1 }

    ExternalConditionMessageEntry ::=
        SEQUENCE {
            externalConditionMessageIndex         ExternalConditionMessageTableIndex,
            externalConditionMessageAdminState    AdminState,
            externalConditionMessageField         ExternalConditionMessageField,
            externalConditionMessageCode          INTEGER,
            externalConditionMessageCodeMatching  CodeMatchMode,
            externalConditionMessageEcAppRef      ExternalConditionRef,
            externalConditionMessageResultFilter  BooleanResultFilter,
            externalConditionMessageMsgTypeFilter MessageTypeFilter,
            externalConditionMessageTemplate      MessageTemplate,
            externalConditionMessageOriginator    AddressString,
            externalConditionMessageRecipient     RecipientSelector,
            externalConditionMessageSuppressStatusReport Boolean,
            externalConditionMessageCounter       Counter
        }

    externalConditionMessageIndex OBJECT-TYPE
        SYNTAX  ExternalConditionMessageTableIndex
        ACCESS  read-write
        STATUS  mandatory
        DESCRIPTION
            "Index of entry in externalConditionMessage table."
        ::= { externalConditionMessageEntry 1 }

    externalConditionMessageAdminState OBJECT-TYPE
        SYNTAX  AdminState
        ACCESS  read-write
        STATUS  mandatory
        DESCRIPTION
            "Administrative state of the externalConditionMessage.

            Activation of the entry is only possible when:

            1) the field must be valid.
            2) the message type filter must not be empty.
            3) the EC application reference must point to an active EC
               application.

            Deactivation of an entry is possible at any time.

            For details, refer to the comment on the AdminState type."
        ::= { externalConditionMessageEntry 2 }

    externalConditionMessageField OBJECT-TYPE
        SYNTAX  ExternalConditionMessageField
        ACCESS  read-write
        STATUS  mandatory
        DESCRIPTION
            "The field against which the 'code' is checked to see
            whether or not a message shall be generated. By default,
            this object is set to 'noFieldSelected'."
        ::= { externalConditionMessageEntry 11 }

    externalConditionMessageCode OBJECT-TYPE
        SYNTAX  INTEGER
        ACCESS  read-write
        STATUS  mandatory
        DESCRIPTION
            "The code that is checked to see whether or not a message
            shall be generated. By default, this object is set to 0."
        ::= { externalConditionMessageEntry 12 }

    externalConditionMessageCodeMatching OBJECT-TYPE
        SYNTAX  CodeMatchMode
        ACCESS  read-write
        STATUS  mandatory
        DESCRIPTION
            "Flag specifying whether the 'field' and 'code' objects should
            be checked or not. Default is 'matchSpecificCode'. When set to 
            'matchAnyCode', the external condition message is generated
            irrespective of the field-code constraint. Templates with this
            flag set to 'matchAnyCode' have lower matching precedence than
            messages with a specific field-code constraint."
        ::= { externalConditionMessageEntry 13 }

    externalConditionMessageEcAppRef OBJECT-TYPE
        SYNTAX  ExternalConditionRef
        ACCESS  read-write
        STATUS  mandatory
        DESCRIPTION
            "May Refer to an EC application (external condition). If so,
            the message is only generated if the ECI response comes from
            that EC application. By default, this field is set to 0, which
            means that any EC application can trigger the generation of
            this message."
        ::= { externalConditionMessageEntry 14 }

    externalConditionMessageResultFilter OBJECT-TYPE
        SYNTAX  BooleanResultFilter
        ACCESS  read-write
        STATUS  mandatory
        DESCRIPTION
            "This object is a filter on the ECI evaluation result, which
            is a boolean. By default, the message can be generated
            irrespective of the evaluation result."
        ::= { externalConditionMessageEntry 15 }

    externalConditionMessageMsgTypeFilter OBJECT-TYPE
        SYNTAX  MessageTypeFilter
        ACCESS  read-write
        STATUS  mandatory
        DESCRIPTION
            "This object is a filter on the type of the original message.
            A external condition message can only be generated if this is
            enabled for the type of the original message. By default, no
            message type is enabled."
        ::= { externalConditionMessageEntry 16 }

    externalConditionMessageTemplate OBJECT-TYPE
        SYNTAX  MessageTemplate
        ACCESS  read-write
        STATUS  mandatory
        DESCRIPTION
            "This is a template for the to-be-generated message. It supports
            the interpolation of the following 'variables':

            $(SCTS) - Service Centre Timestamp formatted as specified
            with smsPropSctsFormatOfPhase1StatusReport object
            $(DESTINATION) - Address of recipient of MO/SM.
            $(SOURCE) - Address of originator of MO/SM.
            $(CODE) - Value for the code.

            This field supports a maximum length of 480 bytes or 160 unicode
            characters, whichever is hit first.

            By default, no template is specified."
        ::= { externalConditionMessageEntry 21 }

    externalConditionMessageOriginator OBJECT-TYPE
        SYNTAX  AddressString
        ACCESS  read-write
        STATUS  mandatory
        DESCRIPTION
            "This object specifies the originator address to be used
            for the generated message. The originator can be numeric
            (up to 20 digits), or alphanumeric (up to 11 GSM default
            alphabet characters). If the field is left empty, the
            router will use its common global title."
        ::= { externalConditionMessageEntry 22 }

    externalConditionMessageRecipient OBJECT-TYPE
        SYNTAX  RecipientSelector
        ACCESS  read-write
        STATUS  mandatory
        DESCRIPTION
            "This object selects the recipient of the generated message.
            By default, this is the originator of the original message."
        ::= { externalConditionMessageEntry 23 }

    externalConditionMessageSuppressStatusReport OBJECT-TYPE
        SYNTAX  Boolean
        ACCESS  read-write
        STATUS  mandatory
        DESCRIPTION
            "This flag controls whether or not a MT status report (or
            AT notification) is to be suppressed when an external condition
            message has been generated for the original message based on
            this table entry, prior to the generation of the status report
            or notification. By default, the flag is set to 'false', such
            that suppression does not take place."
        ::= { externalConditionMessageEntry 24 }

    externalConditionMessageCounter OBJECT-TYPE
        SYNTAX  Counter
        ACCESS  read-write
        STATUS  mandatory
        DESCRIPTION
            "This object counts how many times this template has been used
            to generate an external condition message."
        ::= { externalConditionMessageEntry 31 }

    externalConditionIPTable OBJECT-TYPE
        SYNTAX  SEQUENCE OF ExternalConditionIPEntry
        ACCESS  not-accessible
        STATUS  mandatory
        DESCRIPTION
            "Table with allowed IP address for an EC Application. If no IP
             address is provisioned for a EC application, 
             all addresses are allowed."
    ::= { sms 74 }

    externalConditionIPEntry OBJECT-TYPE
        SYNTAX  ExternalConditionIPEntry
        ACCESS  not-accessible
        STATUS  mandatory
        DESCRIPTION
            "Table entry for allowed IP address of an EC application.
             If no IP address is provisioned for an EC application, all
             IP addresses are allowed."
        INDEX   { externalConditionIPExternalConditionIndex,
                  externalConditionIPIndex }
    ::= { externalConditionIPTable 1 }

    ExternalConditionIPEntry ::=
        SEQUENCE {
            externalConditionIPExternalConditionIndex ExternalConditionTableIndex,
            externalConditionIPIndex                  ExternalConditionIPIndex,
            externalConditionIPAddress                IpAddress
        }

    externalConditionIPExternalConditionIndex OBJECT-TYPE
        SYNTAX  ExternalConditionTableIndex
        ACCESS  not-accessible
        STATUS  mandatory
        DESCRIPTION
            "Index for externalConditionIPTable.
            Its value is equal to the index of the corresponding
            externalConditionTable entry."
    ::= { externalConditionIPEntry 1}

    externalConditionIPIndex OBJECT-TYPE
        SYNTAX  ExternalConditionIPIndex
        ACCESS  not-accessible
        STATUS  mandatory
        DESCRIPTION
            "Index for externalConditionIPTable.
             This index identifies one specific IP address."
    ::= { externalConditionIPEntry 2}

    externalConditionIPAddress OBJECT-TYPE
        SYNTAX  IpAddress
        ACCESS  read-write
        STATUS  mandatory
        DESCRIPTION
            "Allowed IP address for an application. Setting it to
             255.255.255.255 will destroy this entry."
    ::= { externalConditionIPEntry 3}

    
    ----------------------------------------
    -- ExternalConditionClientTable
    ----------------------------------------
     
    externalConditionClientTable OBJECT-TYPE
        SYNTAX  SEQUENCE OF ExternalConditionClientEntry
        ACCESS  not-accessible
        STATUS  mandatory
        DESCRIPTION
            "The ECI client table represents all the ECI clients that are
            currently connected to the Router. An ECI client is identified
            uniquely by the combination of its external condition index
            (referring to the externalConditionTable entry) and the IP
            address from which the client connects to the Router."
        ::= { sms 75 }

    externalConditionClientEntry OBJECT-TYPE
        SYNTAX  ExternalConditionClientEntry
        ACCESS  not-accessible
        STATUS  mandatory
        DESCRIPTION
            "Table entry defining a single ExternalConditionClient."
        INDEX   { externalConditionClientIndex }
        ::= { externalConditionClientTable 1 }

    ExternalConditionClientEntry ::=
        SEQUENCE {
            externalConditionClientIndex                  ExternalConditionClientTableIndex,
            externalConditionClientExternalConditionIndex ExternalConditionTableIndex,
            externalConditionClientExternalConditionName  NameString,
            externalConditionClientIpAddress              IpAddress,

            externalConditionClientOpenSessions           Gauge,
            externalConditionClientTotalOpenedSessions    Counter,
            externalConditionClientTotalClosedSessions    Counter,
            
            externalConditionClientTotalMessagesSent      Counter,
            externalConditionClientTotalMessagesReceived  Counter
        }

    externalConditionClientIndex OBJECT-TYPE
        SYNTAX  ExternalConditionClientTableIndex
        ACCESS  read-only
        STATUS  mandatory
        DESCRIPTION
            "Index of entry in ExternalConditionClient table."
        ::= { externalConditionClientEntry 1 }

    externalConditionClientExternalConditionIndex OBJECT-TYPE
        SYNTAX  ExternalConditionTableIndex
        ACCESS  read-only
        STATUS  mandatory
        DESCRIPTION
            "Index of the externalConditionTable entry, which the client
            represents."
        ::= { externalConditionClientEntry 2 }

    externalConditionClientExternalConditionName OBJECT-TYPE
        SYNTAX  NameString
        ACCESS  read-only
        STATUS  mandatory
        DESCRIPTION
            "Name of the externalConditionTable entry, which the client
            represents. This is a shadow copy of the externalConditionName
            of the externalConditionTable entry specified by the
            externalConditionClientExternalConditionIndex."
        ::= { externalConditionClientEntry 3 }

    externalConditionClientIpAddress OBJECT-TYPE
        SYNTAX  IpAddress
        ACCESS  read-only
        STATUS  mandatory
        DESCRIPTION
            "IP address of the external condition client. Since this field
            must be unique per externalConditionTable entry, only a single
            instance of an EC application can exist per IP address. There is
            no principle limit on the number of sessions of a client,
            however."
        ::= { externalConditionClientEntry 4 }

    externalConditionClientOpenSessions OBJECT-TYPE
        SYNTAX  Gauge
        ACCESS  read-only
        STATUS  mandatory
        DESCRIPTION
            "Indicates the number of open sessions this client currently
            has. Only successfully logged-in sessions are counted."
        ::= { externalConditionClientEntry 21 }

    externalConditionClientTotalOpenedSessions OBJECT-TYPE
        SYNTAX  Counter
        ACCESS  read-write
        STATUS  mandatory
        DESCRIPTION
            "Total number of successfully established sessions."
        ::= { externalConditionClientEntry 31 }

    externalConditionClientTotalClosedSessions OBJECT-TYPE
        SYNTAX  Counter
        ACCESS  read-write
        STATUS  mandatory
        DESCRIPTION
            "Total number of closed sessions."
        ::= { externalConditionClientEntry 32 }

    externalConditionClientTotalMessagesSent OBJECT-TYPE
        SYNTAX  Counter
        ACCESS  read-write
        STATUS  mandatory
        DESCRIPTION
            "Total number of sent ECI messages."
        ::= { externalConditionClientEntry 41 }

    externalConditionClientTotalMessagesReceived OBJECT-TYPE
        SYNTAX  Counter
        ACCESS  read-write
        STATUS  mandatory
        DESCRIPTION
            "Total number of received ECI messages."
        ::= { externalConditionClientEntry 42 }

    ----------------------------------------
    -- AO Routing Rule Table
    ----------------------------------------
    
    aoRtgRuleTable OBJECT-TYPE
        SYNTAX  SEQUENCE OF AoRtgRuleEntry
        ACCESS  not-accessible
        STATUS  mandatory
        DESCRIPTION
            "A table containing properties, conditions, counters and action
            parameters for each AO routing rule.

            An AO routing rule matches when both of the following conditions
            are met:
            1) its administrative state is active;
            2) all its conditions do satisfy;

            In case multiple rules match, the priority of the AO routing rule
            determines which rule applies. When multiple rules have the same
            priority, the AO routing rule with the lowest index has
            precedence."
        ::= { sms 81 }

    aoRtgRuleEntry OBJECT-TYPE
        SYNTAX  AoRtgRuleEntry
        ACCESS  not-accessible
        STATUS  mandatory
        DESCRIPTION
            "Table entry specifying a single AO routing rule."
        INDEX   { aoRtgRuleIndex }
        ::= { aoRtgRuleTable 1 }

    AoRtgRuleEntry ::=
        SEQUENCE {
            aoRtgRuleIndex                        AoRtgRuleTableIndex,
            aoRtgRuleAdminState                   AdminState,
            aoRtgRuleName                         NameString,
            aoRtgRulePriority                     Priority,
            aoRtgRuleAppliedCounter               Counter,
            aoRtgRuleFallbackAppliedCounter       Counter,
            aoRtgRuleThroughputLimitHitCounter    Counter,
            aoRtgRuleSuccessOnPrimaryCounter      Counter,
            aoRtgRuleFailureOnPrimaryCounter      Counter,
            aoRtgRuleSuccessOnFallbackCounter     Counter,
            aoRtgRuleFailureOnFallbackCounter     Counter,
            aoRtgRuleFallbackNotAppliedDueToPermanentErrorOnPrimaryCounter Counter,
            aoRtgRuleFallbackNotAppliedDueToUnavailabilityCounter Counter,
            aoRtgRuleAction                       AoAction,
            aoRtgRuleModifier                     AoModifierRef,
            aoRtgRuleModifiedSourceApplication    ApplicationTableIndex,
            aoRtgRuleLoadBalancingGroup           LoadBalancingGroupReference,
            aoRtgRuleThroughputMax                Throughput,
            aoRtgRuleThroughputCommitted          Throughput,
            aoRtgRuleAmsQueue                     AmsQueueIndex,
            aoRtgRuleSmscGroupIndex               SmscGroupIndex,
            aoRtgRuleApplicationCondition         ConditionSpec,
            aoRtgRuleApplicationGroupCondition    ConditionSpec,
            aoRtgRuleApplicationCategoryCondition ConditionSpec,
            aoRtgRuleServiceClassCondition        ConditionSpec,
            aoRtgRuleProtocolCondition            ConditionSpec,
            aoRtgRuleOperationCondition           ConditionSpec,
            aoRtgRuleOriginatorCondition          ConditionSpec,
            aoRtgRuleOriginatorTonCondition       ConditionSpec,
            aoRtgRuleOriginatorNpiCondition       ConditionSpec,
            aoRtgRuleRecipientCondition           ConditionSpec,
            aoRtgRuleRecipientTonCondition        ConditionSpec,
            aoRtgRuleRecipientNpiCondition        ConditionSpec,
            aoRtgRuleUserDataCondition            ConditionSpec,
            aoRtgRuleUserDataHeaderIndicationCondition ConditionSpec,
            aoRtgRuleUserDataHeaderCondition      ConditionSpec,
            aoRtgRuleReplyPathCondition           ConditionSpec,
            aoRtgRuleNotificationAddressCondition ConditionSpec,
            aoRtgRuleNotificationRequestCondition ConditionSpec,
            aoRtgRuleNotificationTypeCondition    ConditionSpec,
            aoRtgRuleSingleShotIndicatorCondition ConditionSpec,
            aoRtgRuleMoreMessagesToSendCondition  ConditionSpec,
            aoRtgRulePriorityCondition            ConditionSpec,
            aoRtgRuleProtocolIdCondition          ConditionSpec,
            aoRtgRuleDataCodingSchemeCondition    ConditionSpec,
            aoRtgRuleConcatenatedMessageSegmentsCondition ConditionSpec,
            aoRtgRuleUcpAuthenticationCodeCondition ConditionSpec,
            aoRtgRuleNotificationPidCondition     ConditionSpec,
            aoRtgRuleLastResortAddressCondition   ConditionSpec,
            aoRtgRuleLastResortRequestCondition   ConditionSpec,
            aoRtgRuleLastResortPidCondition       ConditionSpec,
            aoRtgRuleCimdTariffClassCondition     ConditionSpec,
            aoRtgRuleCimdServiceDescriptionCondition ConditionSpec,
            aoRtgRuleValidityPeriodCondition      ConditionSpec,
            aoRtgRuleDeferredDeliveryTimeCondition ConditionSpec,
            aoRtgRuleSubmitTimeCondition          ConditionSpec,
            aoRtgRuleExternalAttributesCondition  ConditionSpec,
            aoRtgRuleRecipientRoutingNumberGroupCondition ConditionSpec,
            aoRtgRuleBilProfileForSubmission      BilProfile,
            aoRtgRuleBilProfileForSuccessfulDelivery BilProfile,
            aoRtgRuleBilProfileForFailedDelivery  BilProfile,
            aoRtgRuleBilProfileForSuccessfulDeliveryOnFallback BilProfile,
            aoRtgRuleBilProfileForFailedDeliveryOnFallback BilProfile,
            aoRtgRuleBilProfileForDeliveryNotification BilProfile,
            aoRtgRuleLogProfile                   LogProfile,
            aoRtgRuleApplication                  ApplicationTableIndex
        }

    aoRtgRuleIndex OBJECT-TYPE
        SYNTAX  AoRtgRuleTableIndex
        ACCESS  read-write
        STATUS  mandatory
        DESCRIPTION
            "Index of entry in AO routing rule table."
        ::= { aoRtgRuleEntry 1 }

    aoRtgRuleAdminState OBJECT-TYPE
        SYNTAX  AdminState
        ACCESS  read-write
        STATUS  mandatory
        DESCRIPTION
            "Administrative state of the AO routing rule.

            Transition from 'inactive' to 'active' is only possible when:
            1) name has been supplied;
            2) name is not already in use by another rule;
            3) conditions of rule specifying a network refer to an 'active'
               country and an 'active' network;
            4) conditions of rule specifying a country refer to an 'active'
               country;
            5) conditions of rule specifying an application refer to an
               'active' application;
            6) in case routing to application, application being referred to
               exists;
            7) in case modifier specified, modifier being referred to exists.
            8) in case applicationGroupCondition specified, all referred
               groups should exists;
            9) in case applicationCategoryCondition specified, all referred
               categories should exists;
            10) in case serviceClassCondition specified, all referred service
                classes should exists;

            For details, refer to the comment on the AdminState type."
        ::= { aoRtgRuleEntry 2 }

    aoRtgRuleName OBJECT-TYPE
        SYNTAX  NameString
        ACCESS  read-write
        STATUS  mandatory
        DESCRIPTION
            "Name of the AO routing rule."
        ::= { aoRtgRuleEntry 3 }

    aoRtgRulePriority OBJECT-TYPE
        SYNTAX  Priority
        ACCESS  read-write
        STATUS  mandatory
        DESCRIPTION
            "Priority of the SMS routing rule.

            For details, refer to the comment on the Priority type."
        ::= { aoRtgRuleEntry 4 }

    aoRtgRuleAppliedCounter OBJECT-TYPE
        SYNTAX  Counter
        ACCESS  read-write
        STATUS  mandatory
        DESCRIPTION
            "Counter specifying the number of times that the routing rule
            has been applied."
        ::= { aoRtgRuleEntry 11 }

    aoRtgRuleFallbackAppliedCounter OBJECT-TYPE
        SYNTAX  Counter
        ACCESS  read-write
        STATUS  mandatory
        DESCRIPTION
            "Counter specifying the number of times that the fallback
            destination of the routing rule has been applied."
        ::= { aoRtgRuleEntry 12 }

    aoRtgRuleThroughputLimitHitCounter OBJECT-TYPE
        SYNTAX  Counter
        ACCESS  read-write
        STATUS  mandatory
        DESCRIPTION
            "Counter specifying the number of times that the throughput
            limit as set for the rule has been hit."
        ::= { aoRtgRuleEntry 20 }

    aoRtgRuleSuccessOnPrimaryCounter OBJECT-TYPE
        SYNTAX  Counter
        ACCESS  read-write
        STATUS  mandatory
        DESCRIPTION
            "Counter specifying the number of times that an AO/SM has been
            successfully routed to the primary destination of the routing
            rule."
        ::= { aoRtgRuleEntry 13 }

    aoRtgRuleFailureOnPrimaryCounter OBJECT-TYPE
        SYNTAX  Counter
        ACCESS  read-write
        STATUS  mandatory
        DESCRIPTION
            "Counter specifying the number of times that an AO/SM has not
            been successfully routed to the primary destination of the
            routing rule."
        ::= { aoRtgRuleEntry 14 }

    aoRtgRuleSuccessOnFallbackCounter OBJECT-TYPE
        SYNTAX  Counter
        ACCESS  read-write
        STATUS  mandatory
        DESCRIPTION
            "Counter specifying the number of times that an AO/SM has been
            successfully routed to the fallback destination of the routing
            rule."
        ::= { aoRtgRuleEntry 15 }

    aoRtgRuleFailureOnFallbackCounter OBJECT-TYPE
        SYNTAX  Counter
        ACCESS  read-write
        STATUS  mandatory
        DESCRIPTION
            "Counter specifying the number of times that an AO/SM has not
            been successfully routed to the fallback destination of the
            routing rule."
        ::= { aoRtgRuleEntry 16 }

    aoRtgRuleFallbackNotAppliedDueToPermanentErrorOnPrimaryCounter OBJECT-TYPE
        SYNTAX  Counter
        ACCESS  read-write
        STATUS  mandatory
        DESCRIPTION
            "Counter specifying the number of times that routing an AO/SM has
            failed on the primary destination with a permanent error."
        ::= { aoRtgRuleEntry 17 }

    aoRtgRuleFallbackNotAppliedDueToUnavailabilityCounter OBJECT-TYPE
        SYNTAX  Counter
        ACCESS  read-write
        STATUS  mandatory
        DESCRIPTION
            "Counter specifying the number of times that routing an AO/SM to
            the fallback destination was not possible because of
            unavailability of the fallback destination."
        ::= { aoRtgRuleEntry 18 }

    aoRtgRuleAction OBJECT-TYPE
        SYNTAX  AoAction
        ACCESS  read-write
        STATUS  mandatory
        DESCRIPTION
            "Action to execute when the AO routing rule applies.

            For details, refer to the comments on the AoAction type."
        ::= { aoRtgRuleEntry 21 }

    aoRtgRuleModifier OBJECT-TYPE
        SYNTAX  AoModifierRef
        ACCESS  read-write
        STATUS  mandatory
        DESCRIPTION
            "Reference to a modifier which is carried out when AO routing rule
            applies."
        ::= { aoRtgRuleEntry 22 }

    aoRtgRuleModifiedSourceApplication OBJECT-TYPE
        SYNTAX  ApplicationTableIndex
        ACCESS  read-write
        STATUS  mandatory
        DESCRIPTION
            "Reference to an application table entry to be used as source
            application when forwarding an AO message as AO to an SMSC.
            A value of 0 means that no application table entry is referenced.
            An AO rule referencing a modified source application can only
            be activated if the routing path is set to one of the following
            AO routing actions:

                'routeToMsFallbackToSmsc' (AO-MT-AO),
                'routeToSmsc' (AO-AO),
                'routeToSmscFallbackToStorage' (AO-AO-Store),
                'storeForForwardingAsAo' (AO-Store-AO),

            and if the SMSC group index refers to an SMSC group (is not 0).
            By default, this parameter is set to 0."
        ::= { aoRtgRuleEntry 23 }

    aoRtgRuleLoadBalancingGroup OBJECT-TYPE
        SYNTAX  LoadBalancingGroupReference
        ACCESS  read-write
        STATUS  mandatory
        DESCRIPTION
            "Reference to a load balancing group. Currently, this parameter
            is only supported for AT-related routing actions such as
            'routeToApplication', 'routeToApplicationFallbackToStorage' and
            'storeForDeliveryToApplication'. Therefore, the load balancing
            group referred to must be of type 'application'.
            When both this field and the application parameter are specified,
            the application parameter overrides this field.
            By default, this parameter is set to 0."
        ::= { aoRtgRuleEntry 24 }

    aoRtgRuleThroughputMax OBJECT-TYPE
        SYNTAX  Throughput
        ACCESS  read-write
        STATUS  mandatory
        DESCRIPTION
            "Maximum throughput in terms of SM's routed per second for the
            primary destination of the AO routing rule."
        ::= { aoRtgRuleEntry 27 }

    aoRtgRuleThroughputCommitted OBJECT-TYPE
        SYNTAX  Throughput
        ACCESS  read-write
        STATUS  mandatory
        DESCRIPTION
            "Committed throughput in terms of SM's routed per second for the
            primary destination of the AO routing rule. Committed throughput
            applies in cases of congestion."
        ::= { aoRtgRuleEntry 28 }

    aoRtgRuleAmsQueue OBJECT-TYPE
        SYNTAX  AmsQueueIndex
        ACCESS  read-write
        STATUS  mandatory
        DESCRIPTION
            "Specifier of an AMS queue.

            Only applicable and mandatory when action of AO routing rule is
            routeToMsFallbackToStorage, routeToApplicationFallbackToStorage,
            routeToSmscFallbackToStorage, storeForDeliveryToMs,
            storeForDeliveryToApplication or storeForForwardingAsAo."
        ::= { aoRtgRuleEntry 31 }

    aoRtgRuleSmscGroupIndex OBJECT-TYPE
        SYNTAX  SmscGroupIndex
        ACCESS  read-write
        STATUS  mandatory
        DESCRIPTION
            "Specifier of an SMSC group. 
            
            The type of the SMSC group should be 'ao'.

            Mandatory if the routing action is routeToSmscFallbackToStorage
            or storeForForwardingAsAo.
            Optional when action of AO routing rule is routeToSmsc or
            routeToMsFallbackToSmsc."
        ::= { aoRtgRuleEntry 32 }

    aoRtgRuleApplicationCondition OBJECT-TYPE
        SYNTAX  ConditionSpec
        ACCESS  read-write
        STATUS  mandatory
        DESCRIPTION
            "Condition pertaining to the application originating the SM. For
            the specification for this condition, the following formats
            apply:

            1) NONE
            2) APPLICATION

            For details on these formats, refer to the comment on the
            ConditionSpec type."
        ::= { aoRtgRuleEntry 41 }


    aoRtgRuleApplicationGroupCondition OBJECT-TYPE
        SYNTAX  ConditionSpec
        ACCESS  read-write
        STATUS  mandatory
        DESCRIPTION
            "Condition pertaining to the application group associated with
            the application originating the SM. For the specification for
            this condition, the following formats apply:

            1) NONE
            2) BITSTRING

            When the format is BITSTRING, the relating bit string specifies
            which application groups apply. Each bit in the bit string
            relates to a specific application group. If the bit is 1, the
            application group applies. Otherwise, if the bit is 0, the
            application group does not apply. Up to 1000 application
            groups can be defined. As such, the bit string consists of 1000
            bits with the least significant bit indicating whether application
            group with SNMP index 1 applies and the most significant bit
            indicating whether application group with SNMP index 1000 applies.

            For further details on these formats, refer to the comment on the
            ConditionSpec type."
        ::= { aoRtgRuleEntry 42 }


    aoRtgRuleApplicationCategoryCondition OBJECT-TYPE
        SYNTAX  ConditionSpec
        ACCESS  read-write
        STATUS  mandatory
        DESCRIPTION
            "Condition pertaining to the application categories associated
            with the application originating the SM. For the specification
            for this condition, the following formats apply:

            1) NONE
            2) BITSTRING

            When the format is BITSTRING, the relating bit string specifies
            which application categories apply. Each bit in the bit string
            relates to a specific application category. If the bit is 1, the
            application category applies. Otherwise, if the bit is 0, the
            application category does not apply. Up to 1000 application
            categories can be defined. As such, the bit string consists of
            1000 bits with the least significant bit indicating whether
            application category with SNMP index 1 applies and the most
            significant bit indicating whether application category with SNMP
            index 1000 applies.

            For further details on these formats, refer to the comment on the
            ConditionSpec type."
        ::= { aoRtgRuleEntry 43 }


    aoRtgRuleServiceClassCondition OBJECT-TYPE
        SYNTAX  ConditionSpec
        ACCESS  read-write
        STATUS  mandatory
        DESCRIPTION
            "Condition pertaining to the service class associated with the
            application originating the SM. For the specification for this
            condition, the following formats apply:

            1) NONE
            2) BITSTRING

            When the format is BITSTRING, the relating bit string specifies
            which service classes apply. Each bit in the bit string relates
            to a specific service class. If the bit is 1, the service class
            applies.
            Otherwise, if the bit is 0, the service class does not apply. Up
            to 1000 service classes can be defined. As such, the bit string
            consists of 1000 bits with the least significant bit indicating
            whether service class with SNMP index 1 applies and the most
            significant bit indicating whether service class with SNMP index
            1000 applies.

            For further details on these formats, refer to the comment on the
            ConditionSpec type."
        ::= { aoRtgRuleEntry 44 }


    aoRtgRuleProtocolCondition OBJECT-TYPE
        SYNTAX  ConditionSpec
        ACCESS  read-write
        STATUS  mandatory
        DESCRIPTION
            "Condition pertaining to the protocol used by the originating
            application to submit the SM. For the specification for this
            condition, the following formats apply:

            1) NONE
            2) BITSTRING

            When the format is BITSTRING, the relating bit string specifies
            which protocols apply. Each bit in the bit string relates to a
            specific protocol. If the bit is 1, the protocol applies.
            Otherwise, if the bit is 0, the protocol does not apply. Three
            protocols are used by applications to submit an SM. These
            protocols are UCP, SMPP and CIMD. As such, the bit string
            consists of 3 bits with
            - bit 0 indicating whether the UCP protocol applies,
            - bit 1 indicating whether the SMPP protocol applies, and
            - bit 2 indicating whether the CIMD protocol applies.
            Note that bit 0 is the least significant bit and bit 2 the most
            significant bit.

            For further details on these formats, refer to the comment on the
            ConditionSpec type."
        ::= { aoRtgRuleEntry 45 }


    aoRtgRuleOperationCondition OBJECT-TYPE
        SYNTAX  ConditionSpec
        ACCESS  read-write
        STATUS  mandatory
        DESCRIPTION
            "Condition pertaining to the operation used by the originating
            application to submit the SM. For the specification for this
            condition, the following formats apply:

            1) NONE
            2) BITSTRING

            When the format is BITSTRING, the relating bit string specifies
            which operations apply. Not all bits of the bit string are used.
            Each bit in the bit string that is used relates to a specific
            operation. If the bit is 1, the operation applies. Otherwise, if
            the bit is 0, the operation does not apply. The bit string
            consists of 32 bits and has the following mapping:

              ---------------------------------------------------------------
              bit  operation
              ---------------------------------------------------------------
               0   UCP Call input operation -01
               1   UCP Multiple address call input operation -02
               2   UCP Call input with supplementary services operation -03
               3   UCP MS message transfer operation -30
               4   UCP Submit Short Message operation -51
               9   UCP operation other than the ones above
               10  SMPP SubmitSm
               12  SMPP SubmitMulti
               13  SMPP DataSm
               19  SMPP operation other than the ones above
               20  CIMD SubmitMessage
               29  CIMD operation other than the ones above
               30  operation from another protocol than UCP, SMPP and CIMD
              --------------------------------------------------------------

            Note that bit 0 is the least significant bit and bit 2 the most
            significant bit.

            For further details on these formats, refer to the comment on the
            ConditionSpec type."
        ::= { aoRtgRuleEntry 46 }


    aoRtgRuleOriginatorCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST

            For details on these formats, refer to the comment on the
            ConditionSpec type."
        ::= { aoRtgRuleEntry 47 }


    aoRtgRuleOriginatorTonCondition OBJECT-TYPE
        SYNTAX  ConditionSpec
        ACCESS  read-write
        STATUS  mandatory
        DESCRIPTION
            "Condition pertaining to the type of number (TON) specified for
            the originator of the SM. For the specification for this
            condition, the following formats apply:

            1) NONE
            2) BITSTRING

            When the format is BITSTRING, the relating bit string specifies
            which values for the TON apply. Each bit in the bit string
            relates to a TON value. If the bit is 1, the relating TON value
            applies.  Otherwise, if the bit is 0, the relating TON value does
            not apply.  The range of value for the TON is 0-7. As such, the
            bit string consists of 8 bits with the least significant bit
            indicating whether TON value 0 applies and the most significant
            bit indicating whether TON value 7 applies.

            For further details on these formats, refer to the comment on the
            ConditionSpec type.

            For details on the values supported for the TON, refer to GSM
            03.40."
        ::= { aoRtgRuleEntry 48 }


    aoRtgRuleOriginatorNpiCondition OBJECT-TYPE
        SYNTAX  ConditionSpec
        ACCESS  read-write
        STATUS  mandatory
        DESCRIPTION
            "Condition pertaining to the numbering plan identification (NPI)
            specified for the originator of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not
            apply.  The range of value for the NPI is 0-15. As such, the bit
            string consists of 16 bits with the least significant bit
            indicating whether NPI value 0 applies and the most significant
            bit indicating whether NPI value 15 applies.

            For further details on these formats, refer to the comment on the
            ConditionSpec type.

            For details on the values supported for the NPI, refer to GSM
            03.40."
        ::= { aoRtgRuleEntry 49 }


    aoRtgRuleRecipientCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            7) APPLICATION
            8) LIST

            For details on these formats, refer to the comment on the
            ConditionSpec type."
        ::= { aoRtgRuleEntry 50 }


    aoRtgRuleRecipientTonCondition OBJECT-TYPE
        SYNTAX  ConditionSpec
        ACCESS  read-write
        STATUS  mandatory
        DESCRIPTION
            "Condition pertaining to the type of number (TON) specified for
            the recipient of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not
            apply.  The range of value for the TON is 0-7. As such, the bit
            string consists of 8 bits with the least significant bit
            indicating whether TON value 0 applies and the most significant
            bit indicating whether TON value 7 applies.

            For further details on these formats, refer to the comment on the
            ConditionSpec type.

            For details on the values supported for the TON, refer to GSM
            03.40."
        ::= { aoRtgRuleEntry 51 }


    aoRtgRuleRecipientNpiCondition OBJECT-TYPE
        SYNTAX  ConditionSpec
        ACCESS  read-write
        STATUS  mandatory
        DESCRIPTION
            "Condition pertaining to the numbering plan identification (NPI)
            specified for the recipient of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { aoRtgRuleEntry 52 }


    aoRtgRuleUserDataCondition OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT
            5) TEXTLENGTH

            For details on these formats, refer to the comment on the
            ConditionSpec type."
        ::= { aoRtgRuleEntry 53 }


    aoRtgRuleUserDataHeaderIndicationCondition OBJECT-TYPE
        SYNTAX  ConditionSpec
        ACCESS  read-write
        STATUS  mandatory
        DESCRIPTION
            "Condition pertaining to the user data header indication specified
            in the SM. For the specification for this condition, the following
            formats apply:

            1) NONE
            2) BITVALUE

            For details on these formats, refer to the comment on the
            ConditionSpec type."
        ::= { aoRtgRuleEntry 54 }


    aoRtgRuleUserDataHeaderCondition OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to GSM 03.40. The
            values for most common information element identifiers are:

            00 hex - Concatenated short message
            01 hex - Special SMS Message Indication
            04 hex - application port addressing scheme, 8 bit address
            05 hex - application port addressing scheme, 16 bit address
            06 hex - SMSC Control Parameters
            07 hex - UDH Source Indicator "
        ::= { aoRtgRuleEntry 55 }


    aoRtgRuleReplyPathCondition OBJECT-TYPE
        SYNTAX  ConditionSpec
        ACCESS  read-write
        STATUS  mandatory
        DESCRIPTION
            "Condition pertaining to the reply path indication specified in
            the SM. For the specification for this condition, the following
            formats apply:

            1) NONE
            2) BITVALUE

            For details on these formats, refer to the comment on the
            ConditionSpec type."
        ::= { aoRtgRuleEntry 56 }


    aoRtgRuleNotificationAddressCondition OBJECT-TYPE
        SYNTAX  ConditionSpec
        ACCESS  read-write
        STATUS  mandatory
        DESCRIPTION
            "Condition pertaining to the notification address that is
            specified in the SM. For the specification for this condition,
            the following formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) SINGLETCPIPADDRESS
            12) SINGLEX121ADDRESS
            13) LIST

            For details on these formats, refer to the comment on the
            ConditionSpec type."
        ::= { aoRtgRuleEntry 57 }


    aoRtgRuleNotificationRequestCondition OBJECT-TYPE
        SYNTAX  ConditionSpec
        ACCESS  read-write
        STATUS  mandatory
        DESCRIPTION
            "Condition pertaining to the notification request indication
            specified in the SM. For the specification for this condition, the
            following formats apply:

            1) NONE
            2) BITVALUE

            For details on these formats, refer to the comment on the
            ConditionSpec type."
        ::= { aoRtgRuleEntry 58 }


    aoRtgRuleNotificationTypeCondition OBJECT-TYPE
        SYNTAX  ConditionSpec
        ACCESS  read-write
        STATUS  mandatory
        DESCRIPTION
            "Condition pertaining to the notification type specified in
            the SM. For the specification for this condition, the following
            formats apply:

            1) NONE
            2) BITSTRING

            When the format is BITSTRING, the relating bit string specifies
            which notification types apply. Each bit in the bit string
            relates to a specific notification type. If the bit is 1, the
            notification type applies. Otherwise, if the bit is 0, the
            notification type does not apply. Three notification types exist.
            notification type. These notification types are 'delivered', 'not
            delivered', and 'buffered'.
            As such, the bit string consists of 3 bits with
            - bit 0 indicating 'delivered' ,
            - bit 1 indicating 'not delivered', and
            - bit 2 indicating 'buffered'.
            Note that bit 0 is the least significant bit and bit 2 the most
            significant bit.

            For further details on these formats, refer to the comment on the
            ConditionSpec type."
        ::= { aoRtgRuleEntry 59 }


    aoRtgRuleSingleShotIndicatorCondition OBJECT-TYPE
        SYNTAX  ConditionSpec
        ACCESS  read-write
        STATUS  mandatory
        DESCRIPTION
            "Condition pertaining to the single shot indicator specified in
            the SM. For the specification for this condition, the following
            formats apply:

            1) NONE
            2) BITVALUE

            For details on these formats, refer to the comment on the
            ConditionSpec type."
        ::= { aoRtgRuleEntry 60 }


    aoRtgRuleMoreMessagesToSendCondition OBJECT-TYPE
        SYNTAX  ConditionSpec
        ACCESS  read-write
        STATUS  mandatory
        DESCRIPTION
            "Condition pertaining to the more message to send indicator
            specified in the SM. For the specification for this condition, the
            following formats apply:

            1) NONE
            2) BITVALUE

            For details on these formats, refer to the comment on the
            ConditionSpec type."
        ::= { aoRtgRuleEntry 61 }


    aoRtgRulePriorityCondition OBJECT-TYPE
        SYNTAX  ConditionSpec
        ACCESS  read-write
        STATUS  mandatory
        DESCRIPTION
            "Condition pertaining to the priority level that is specified in
            the SM. For the specification for this condition, the following
            formats apply:

            1) NONE
            2) BITSTRING

            When the format is BITSTRING, the relating bit string specifies
            which priority levels apply. Not all bits of the bit string are
            used. Each bit in the bit string that is used relates to a
            specific priority level. If the bit is 1, the priority level
            applies.  Otherwise, if the bit is 0, the priority level does not
            apply. The bit string consists of 32 bits and has the following
            mapping:

              ---------------------------------------------------------------
              bit  operation
              ---------------------------------------------------------------
               0   UCP no priority requested
               1   UCP priority requested
               10  SMPP no priority requested
               11  SMPP priority requested
               20  CIMD priority level 1 (most urgent)
               21  CIMD priority level 2
               22  CIMD priority level 3
               23  CIMD priority level 4
               24  CIMD priority level 5
               25  CIMD priority level 6
               26  CIMD priority level 7
               27  CIMD priority level 8
               28  CIMD priority level 9
              --------------------------------------------------------------

            Note that bit 0 is the least significant bit and bit 2 the most
            significant bit.

            For further details on these formats, refer to the comment on the
            ConditionSpec type."
        ::= { aoRtgRuleEntry 62 }


    aoRtgRuleProtocolIdCondition OBJECT-TYPE
        SYNTAX  ConditionSpec
        ACCESS  read-write
        STATUS  mandatory
        DESCRIPTION
            "Condition pertaining to the protocol ID specified in the SM. For
            the specification for this condition, the following formats apply:

            1) NONE
            2) BYTEVALUE

            For details on these formats, refer to the comment on the
            ConditionSpec type.

            For details on the values supported for the protocol ID, refer to
            GSM 03.40."
        ::= { aoRtgRuleEntry 63 }


    aoRtgRuleDataCodingSchemeCondition OBJECT-TYPE
        SYNTAX  ConditionSpec
        ACCESS  read-write
        STATUS  mandatory
        DESCRIPTION
            "Condition pertaining to the data coding scheme specified in the
            SM. For the specification for this condition, the following
            formats apply:

            1) NONE
            2) BYTEVALUE

            For details on these formats, refer to the comment on the
            ConditionSpec type.

            For details on the values supported for the data coding scheme,
            refer to GSM 03.38."
        ::= { aoRtgRuleEntry 64 }


    aoRtgRuleConcatenatedMessageSegmentsCondition OBJECT-TYPE
        SYNTAX  ConditionSpec
        ACCESS  read-write
        STATUS  mandatory
        DESCRIPTION
            "Condition pertaining to the segment sequence number of a
            concatenated SM. For the specification for this condition, the
            following formats apply:

            1) NONE
            2) BITSTRING

            When the format is BITSTRING, the relating bit string specifies
            which concatenated message segments apply. Each bit in the bit
            string relates to a specific segment of a concatenated message. If
            the bit is 1, the segment applies. Otherwise, if the bit is 0, the
            segment does not apply. The segments are distinguished in three
            groups. As such, the bit string consists of 3 bits with
            - bit 0 indicating whether the segment is the first of the
              concatenated message,
            - bit 1 indicating whether the segment is the last of the
              concatenated message,
            - bit 2 indicating whether the segment is not the first nor the
              last of the concatenated message,
            Note that bit 0 is the least significant bit and bit 2 the most
            significant bit.

            For further details on these formats, refer to the comment on the
            ConditionSpec type."
        ::= { aoRtgRuleEntry 65 }


    aoRtgRuleUcpAuthenticationCodeCondition OBJECT-TYPE
        SYNTAX  ConditionSpec
        ACCESS  read-write
        STATUS  mandatory
        DESCRIPTION
            "Condition pertaining to the authentication code that is specified
            in the SM. For the specification for this condition, the following
            formats apply:

            1) NONE
            2) DIGITSTRING

            For details on these formats, refer to the comment on the
            ConditionSpec type."
        ::= { aoRtgRuleEntry 66 }


    aoRtgRuleNotificationPidCondition OBJECT-TYPE
        SYNTAX  ConditionSpec
        ACCESS  read-write
        STATUS  mandatory
        DESCRIPTION
            "Condition pertaining to the notification PID that is specified in
            the SM. For the specification for this condition, the following
            formats apply:

            1) NONE
            2) BITSTRING

            When the format is BITSTRING, the relating bit string specifies
            which address PIDs apply. Each bit in the bit string relates to a
            specific address PID. If the bit is 1, the address PID applies.
            Otherwise, if the bit is 0, the address PIDs does not apply.
            The bit string consists of 8 bits and has the following mapping:

              ---------------------------------------------------------------
              bit  address PID
              ---------------------------------------------------------------
               0   Mobile Station
               1   Fax Group 3
               2   Menu over PSTN
               3   PC application over PSTN
               4   PC application over ISDN
               5   PC application over TCP/IP
               6   PC application over X25
               7   Unknown
              --------------------------------------------------------------

            Note that bit 0 is the least significant bit and bit 2 the most
            significant bit.

            For further details on these formats, refer to the comment on the
            ConditionSpec type."
        ::= { aoRtgRuleEntry 67 }


    aoRtgRuleLastResortAddressCondition OBJECT-TYPE
        SYNTAX  ConditionSpec
        ACCESS  read-write
        STATUS  mandatory
        DESCRIPTION
            "Condition pertaining to the last resort address that is specified
            in the SM. For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) SINGLETCPIPADDRESS
            12) SINGLEX121ADDRESS
            13) LIST

            For details on these formats, refer to the comment on the
            ConditionSpec type."
        ::= { aoRtgRuleEntry 68 }


    aoRtgRuleLastResortRequestCondition OBJECT-TYPE
        SYNTAX  ConditionSpec
        ACCESS  read-write
        STATUS  mandatory
        DESCRIPTION
            "Condition pertaining to the last resort request indicator
            specified in the SM. For the specification for this condition, the
            following formats apply:

            1) NONE
            2) BITVALUE

            For details on these formats, refer to the comment on the
            ConditionSpec type."
        ::= { aoRtgRuleEntry 69 }


    aoRtgRuleLastResortPidCondition OBJECT-TYPE
        SYNTAX  ConditionSpec
        ACCESS  read-write
        STATUS  mandatory
        DESCRIPTION
            "Condition pertaining to the last resort PID that is specified in
            the SM. For the specification for this condition, the following
            formats apply:

            1) NONE
            2) BITSTRING

            When the format is BITSTRING, the relating bit string specifies
            which address PIDs apply. Each bit in the bit string relates to a
            specific address PID. If the bit is 1, the address PID applies.
            Otherwise, if the bit is 0, the address PIDs does not apply.
            The bit string consists of 8 bits and has the following mapping:

              ---------------------------------------------------------------
              bit  address PID
              ---------------------------------------------------------------
               0   Mobile Station
               1   Fax Group 3
               2   Menu over PSTN
               3   PC application over PSTN
               4   PC application over ISDN
               5   PC application over TCP/IP
               6   PC application over X25
               7   Unknown
              --------------------------------------------------------------

            Note that bit 0 is the least significant bit and bit 2 the most
            significant bit.

            For further details on these formats, refer to the comment on the
            ConditionSpec type."
        ::= { aoRtgRuleEntry 70 }


    aoRtgRuleCimdTariffClassCondition OBJECT-TYPE
        SYNTAX  ConditionSpec
        ACCESS  read-write
        STATUS  mandatory
        DESCRIPTION
            "Condition pertaining to the CIMD tariff class specified in the
            SM.  For the specification for this condition, the following
            formats apply:

            1) NONE
            2) BITSTRING

            When the format is BITSTRING, the relating bit string specifies
            which values for the tariff class apply. Each bit in the bit
            string relates to a tariff class. If the bit is 1, the relating
            tariff class applies. Otherwise, if the bit is 0, the relating
            tariff class does not apply. The range of values for the tariff
            class is 0-99. As such, the bit string consists of 100 bits with
            the least significant bit indicating whether tariff class 0
            applies and the most significant bit indicating whether tariff
            class 99 applies.

            For further details on these formats, refer to the comment on the
            ConditionSpec type."
        ::= { aoRtgRuleEntry 71 }


    aoRtgRuleCimdServiceDescriptionCondition OBJECT-TYPE
        SYNTAX  ConditionSpec
        ACCESS  read-write
        STATUS  mandatory
        DESCRIPTION
            "Condition pertaining to the CIMD service description specified in
            the SM.  For the specification for this condition, the following
            formats apply:

            1) NONE
            2) BITSTRING

            When the format is BITSTRING, the relating bit string specifies
            which values for the service description apply. Each bit in the
            bit string relates to a service description. If the bit is 1, the
            relating service description applies. Otherwise, if the bit is 0,
            the relating service description does not apply. The range of
            values for the service description is 0-99. As such, the bit
            string consists of 100 bits with the least significant bit
            indicating whether service description 0 applies and the most
            significant bit indicating whether service description 99
            applies.

            For further details on these formats, refer to the comment on the
            ConditionSpec type."
        ::= { aoRtgRuleEntry 72 }


    aoRtgRuleValidityPeriodCondition OBJECT-TYPE
        SYNTAX  ConditionSpec
        ACCESS  read-write
        STATUS  mandatory
        DESCRIPTION
            "Condition pertaining to the validity period that is specified in
            the SM. For the specification for this condition, the following
            formats apply:

            1) NONE
            2) RELATIVETIME

            For details on these formats, refer to the comment on the
            ConditionSpec type."
        ::= { aoRtgRuleEntry 73 }


    aoRtgRuleDeferredDeliveryTimeCondition OBJECT-TYPE
        SYNTAX  ConditionSpec
        ACCESS  read-write
        STATUS  mandatory
        DESCRIPTION
            "Condition pertaining to the deferred dlivery time that is
            specified in the SM. For the specification for this condition,
            the following formats apply:

            1) NONE
            2) RELATIVETIME

            For details on these formats, refer to the comment on the
            ConditionSpec type."
        ::= { aoRtgRuleEntry 74 }

    aoRtgRuleSubmitTimeCondition OBJECT-TYPE
        SYNTAX  ConditionSpec
        ACCESS  read-write
        STATUS  mandatory
        DESCRIPTION
            "Condition on the submit-time of the message. For the
            specification for this condition, the following formats apply:

            1) NONE
            2) TIMESPEC

            For further details on these formats, refer to the comment on the
            ConditionSpec type."
        ::= { aoRtgRuleEntry 75 }

    aoRtgRuleExternalAttributesCondition OBJECT-TYPE
        SYNTAX  ConditionSpec
        ACCESS  read-write
        STATUS  mandatory
        DESCRIPTION
            "Condition on the 32 boolean atributes that can be set by an 
            external approval application. For the specification for this 
            condition, the following formats apply:

            1) NONE
            2) EXTERNALATTRIBUTES

            When the format is EXTERNALATTRIBUTES, the relating bit mask
            string specifies which external attributes apply and the relating
            bit value string specifies the values for the external
            attributes.          Each bit in the bit strings relates to a
            specific attribute. The bit strings consist of 32 bits. The least
            significant bit corresponds to attribute 0. The most significant
            bit corresponds to attribute 31. 
            A bit with value 1 in the bit mask string indicates that the
            relating attribute applies and needs to be checked. A bit with
            value 0 in the bit mask string indicates that the relating
            attribute does not apply and does not need to be checked. 
            A bit with value 1 in the bit value string indicates that the
            relating attribute should be TRUE. A bit with value 0 in the bit
            value string indicates that the relating attribute should be
            FALSE. 

            For further details on these formats, refer to the comment on the
            ConditionSpec type."
        ::= { aoRtgRuleEntry 76 }

    aoRtgRuleRecipientRoutingNumberGroupCondition OBJECT-TYPE
        SYNTAX  ConditionSpec
        ACCESS  read-write
        STATUS  mandatory
        DESCRIPTION
            "Condition on the group to which the routing number associated
            with the recipient address belongs. For the specification for
            this condition, the following formats apply:

            1) NONE
            2) SNMPINDEX

            When the format is SNMPINDEX, the SNMP index will refer to the
            routingNumberGroupTable. The (non-inverted) condition will
            never match if either the routing number group referred to by
            the condition is not active, or if no routing number has been
            determined for the recipient of the message under consideration.
            The RoutingNumberGroupIndex determines the range of valid numbers
            for the SNMP index."
        ::= { aoRtgRuleEntry 77 }

    aoRtgRuleBilProfileForSubmission OBJECT-TYPE
        SYNTAX  BilProfile
        ACCESS  read-write
        STATUS  mandatory
        DESCRIPTION
            "Identifier specifying which billing profile should be used for
            submission records. Default is 0 (i.e none).
            This attribute applies to all routing actions."
        ::= { aoRtgRuleEntry 101 }

    aoRtgRuleBilProfileForSuccessfulDelivery OBJECT-TYPE
        SYNTAX  BilProfile
        ACCESS  read-write
        STATUS  mandatory
        DESCRIPTION
            "Identifier specifying which billing profile should be used for
            delivery records in case the routing action succeeds. Default is 0
            (i.e. 'none').
            This attribute is applicable if the routing action is equal to
            routeToSmsc, routeToMs, routeToMsFallbackToSmsc, discardWithAck, 
            routeToApplication, or routeToSmscFallbackToStorage.
            When the routing action is routeToMsFallbackToSmsc, this
            identifier pertains to the case that the routing action to the MS
            succeeds."
        ::= { aoRtgRuleEntry 102 }

    aoRtgRuleBilProfileForFailedDelivery OBJECT-TYPE
        SYNTAX  BilProfile
        ACCESS  read-write
        STATUS  mandatory
        DESCRIPTION
            "Identifier specifying which billing profile should be used for
            delivery records in case the routing action fails. Default is 0
            (i.e. 'none').
            This attribute is applicable if the routing action is equal to
            routeToMs, routeToSmsc or routeToMsFallbackToSmsc.
            In the routeToSmsc scenario, the identifier pertains to the case
            where final delivery CDRs should be created based on the SMSC's
            notification that the message delivery failed.
            In the other scenarios, the identifier pertains to the case where
            the AO message has been acknowledged, but the MT delivery failed
            such that the message had to be discarded."
        ::= { aoRtgRuleEntry 103 }

    aoRtgRuleBilProfileForSuccessfulDeliveryOnFallback OBJECT-TYPE
        SYNTAX  BilProfile
        ACCESS  read-write
        STATUS  mandatory
        DESCRIPTION
            "Identifier specifying which billing profile should be used for
            delivery records in case the routing action on the fallback leg
            succeeds. Default is 0 (i.e. 'none').
            This attribute is applicable if the routing action is equal to
            routeToMsFallbackToSmsc."
        ::= { aoRtgRuleEntry 104 }

    aoRtgRuleBilProfileForFailedDeliveryOnFallback OBJECT-TYPE
        SYNTAX  BilProfile
        ACCESS  read-write
        STATUS  mandatory
        DESCRIPTION
            "Identifier specifying which billing profile should be used for
            delivery records in case the routing action on the fallback leg
            fails. Default is 0 (i.e. 'none').
            This attribute is applicable if the routing action is equal to
            routeToMsFallbackToSmsc."
        ::= { aoRtgRuleEntry 105 }

    aoRtgRuleBilProfileForDeliveryNotification OBJECT-TYPE
        SYNTAX  BilProfile
        ACCESS  read-write
        STATUS  mandatory
        DESCRIPTION
            "Identifier specifying which billing profile should be used for
            delivery notification. Default is 0 (i.e. 'none').
            This attribute is applicable if the routing action is equal to
            routeToSmsc, routeToMs, routeToMsFallbackToSmsc, discardWithAck
            or routeToApplication."
        ::= { aoRtgRuleEntry 106 }

    aoRtgRuleLogProfile OBJECT-TYPE
        SYNTAX  LogProfile
        ACCESS  read-write
        STATUS  mandatory
        DESCRIPTION
            "Identifier specifying which logging profile should be used.
            Default is 0 (i.e. 'none')."
        ::= { aoRtgRuleEntry 111 }

    aoCntRuleTable OBJECT-TYPE
        SYNTAX  SEQUENCE OF AoCntRuleEntry
        ACCESS  not-accessible
        STATUS  mandatory
        DESCRIPTION
            "A table containing properties, conditions and counters for each
            AO counting rule.

            An AO counting rule matches when both of the following conditions
            are met:
            1) its administrative state is active;
            2) all its conditions do satisfy."
        ::= { sms 82 }

    aoCntRuleEntry OBJECT-TYPE
        SYNTAX  AoCntRuleEntry
        ACCESS  not-accessible
        STATUS  mandatory
        DESCRIPTION
            "Table entry specifying a single AO counting rule."
        INDEX   { aoCntRuleIndex }
        ::= { aoCntRuleTable 1 }

    AoCntRuleEntry ::=
        SEQUENCE {
            aoCntRuleIndex                        AoCntRuleTableIndex,
            aoCntRuleAdminState                   AdminState,
            aoCntRuleName                         NameString,
            aoCntRuleLogProfile                   LogProfile,
            aoCntRuleTotalCounter                 Counter,
            aoCntRuleSuccessfulSubmitOperationCounter Counter,
            aoCntRuleFailedSubmitOperationCounter Counter,
            aoCntRuleSuccessfulUnknownOperationCounter Counter,
            aoCntRuleFailedUnknownOperationCounter Counter,
            aoCntRuleApplicationCondition         ConditionSpec,
            aoCntRuleApplicationGroupCondition    ConditionSpec,
            aoCntRuleApplicationCategoryCondition ConditionSpec,
            aoCntRuleServiceClassCondition        ConditionSpec,
            aoCntRuleProtocolCondition            ConditionSpec,
            aoCntRuleOperationCondition           ConditionSpec,
            aoCntRuleOriginatorCondition          ConditionSpec,
            aoCntRuleOriginatorTonCondition       ConditionSpec,
            aoCntRuleOriginatorNpiCondition       ConditionSpec,
            aoCntRuleRecipientCondition           ConditionSpec,
            aoCntRuleRecipientTonCondition        ConditionSpec,
            aoCntRuleRecipientNpiCondition        ConditionSpec,
            aoCntRuleUserDataCondition            ConditionSpec,
            aoCntRuleUserDataHeaderIndicationCondition ConditionSpec,
            aoCntRuleUserDataHeaderCondition      ConditionSpec,
            aoCntRuleReplyPathCondition           ConditionSpec,
            aoCntRuleNotificationAddressCondition ConditionSpec,
            aoCntRuleNotificationRequestCondition ConditionSpec,
            aoCntRuleNotificationTypeCondition    ConditionSpec,
            aoCntRuleSingleShotIndicatorCondition ConditionSpec,
            aoCntRuleMoreMessagesToSendCondition  ConditionSpec,
            aoCntRulePriorityCondition            ConditionSpec,
            aoCntRuleProtocolIdCondition          ConditionSpec,
            aoCntRuleDataCodingSchemeCondition    ConditionSpec,
            aoCntRuleConcatenatedMessageSegmentsCondition ConditionSpec,
            aoCntRuleUcpAuthenticationCodeCondition ConditionSpec,
            aoCntRuleNotificationPidCondition     ConditionSpec,
            aoCntRuleLastResortAddressCondition   ConditionSpec,
            aoCntRuleLastResortRequestCondition   ConditionSpec,
            aoCntRuleLastResortPidCondition       ConditionSpec,
            aoCntRuleCimdTariffClassCondition     ConditionSpec,
            aoCntRuleCimdServiceDescriptionCondition ConditionSpec,
            aoCntRuleValidityPeriodCondition      ConditionSpec,
            aoCntRuleDeferredDeliveryTimeCondition ConditionSpec,
            aoCntRuleSubmitTimeCondition          ConditionSpec,
            aoCntRuleExternalAttributesCondition  ConditionSpec,
            aoCntRuleRecipientRoutingNumberGroupCondition ConditionSpec
        }

    aoCntRuleIndex OBJECT-TYPE
        SYNTAX  AoCntRuleTableIndex
        ACCESS  read-write
        STATUS  mandatory
        DESCRIPTION
            "Index of entry in AO counting rule table."
        ::= { aoCntRuleEntry 1 }

    aoCntRuleAdminState OBJECT-TYPE
        SYNTAX  AdminState
        ACCESS  read-write
        STATUS  mandatory
        DESCRIPTION
            "Administrative state of the AO counting rule.

            Transition from 'inactive' to 'active' is only possible when:
            1) name has been supplied;
            2) name is not already in use by another rule;
            3) conditions of rule specifying a network refer to an 'active'
               country and an 'active' network;
            4) conditions of rule specifying a country refer to an 'active'
               country;
            5) conditions of rule specifying an application refer to an
               'active' application;
            6) in case applicationGroupCondition specified, all referred
               groups should exists;
            7) in case applicationCategoryCondition specified, all referred
               categories should exists;
            8) in case serviceClassCondition specified, all referred service
               classes should exists;

            For details, refer to the comment on the AdminState type."
        ::= { aoCntRuleEntry 2 }

    aoCntRuleName OBJECT-TYPE
        SYNTAX  NameString
        ACCESS  read-write
        STATUS  mandatory
        DESCRIPTION
            "Name of the AO counting rule."
        ::= { aoCntRuleEntry 3 }

    aoCntRuleLogProfile OBJECT-TYPE
        SYNTAX  LogProfile
        ACCESS  read-write
        STATUS  mandatory
        DESCRIPTION
            "Identifier specifying which logging profile should be used.
            Default is 0 (i.e. 'none')."
        ::= { aoCntRuleEntry 4 }

    aoCntRuleTotalCounter OBJECT-TYPE
        SYNTAX  Counter
        ACCESS  read-write
        STATUS  mandatory
        DESCRIPTION
            "Counter specifying the number of times that an operation was
            originated from an application."
        ::= { aoCntRuleEntry 11 }

    aoCntRuleSuccessfulSubmitOperationCounter OBJECT-TYPE
        SYNTAX  Counter
        ACCESS  read-write
        STATUS  mandatory
        DESCRIPTION
            "Counter specifying the number of times that routing a submit
            operation originated from an application succeeded."
        ::= { aoCntRuleEntry 12 }

    aoCntRuleFailedSubmitOperationCounter OBJECT-TYPE
        SYNTAX  Counter
        ACCESS  read-write
        STATUS  mandatory
        DESCRIPTION
            "Counter specifying the number of times that routing a submit
            operation originated from an application failed."
        ::= { aoCntRuleEntry 13 }

    aoCntRuleSuccessfulUnknownOperationCounter OBJECT-TYPE
        SYNTAX  Counter
        ACCESS  read-write
        STATUS  mandatory
        DESCRIPTION
            "Counter specifying the number of times that routing an unknown
            operation originated from an application succeeded."
        ::= { aoCntRuleEntry 14 }

    aoCntRuleFailedUnknownOperationCounter OBJECT-TYPE
        SYNTAX  Counter
        ACCESS  read-write
        STATUS  mandatory
        DESCRIPTION
            "Counter specifying the number of times that routing an unknown
            operation originated from an application failed."
        ::= { aoCntRuleEntry 15 }

    aoCntRuleApplicationCondition OBJECT-TYPE
        SYNTAX  ConditionSpec
        ACCESS  read-write
        STATUS  mandatory
        DESCRIPTION
            "Condition pertaining to the application originating the SM. For
            the specification for this condition, the following formats
            apply:

            1) NONE
            2) APPLICATION

            For details on these formats, refer to the comment on the
            ConditionSpec type."
        ::= { aoCntRuleEntry 41 }

    aoCntRuleApplicationGroupCondition OBJECT-TYPE
        SYNTAX  ConditionSpec
        ACCESS  read-write
        STATUS  mandatory
        DESCRIPTION
            "Condition pertaining to the application group associated with
            the application originating the SM. For the specification for
            this condition, the following formats apply:

            1) NONE
            2) BITSTRING

            When the format is BITSTRING, the relating bit string specifies
            which application groups apply. Each bit in the bit string
            relates to a specific application group. If the bit is 1, the
            application group applies. Otherwise, if the bit is 0, the
            application group does not apply. Up to 1000 application
            groups can be defined. As such, the bit string consists of 1000
            bits with the least significant bit indicating whether application
            group with SNMP index 1 applies and the most significant bit
            indicating whether application group with SNMP index 1000 applies.

            For further details on these formats, refer to the comment on the
            ConditionSpec type."
        ::= { aoCntRuleEntry 42 }


    aoCntRuleApplicationCategoryCondition OBJECT-TYPE
        SYNTAX  ConditionSpec
        ACCESS  read-write
        STATUS  mandatory
        DESCRIPTION
            "Condition pertaining to the application categories associated
            with the application originating the SM. For the specification
            for this condition, the following formats apply:

            1) NONE
            2) BITSTRING

            When the format is BITSTRING, the relating bit string specifies
            which application categories apply. Each bit in the bit string
            relates to a specific application category. If the bit is 1, the
            application category applies. Otherwise, if the bit is 0, the
            application category does not apply. Up to 1000 application
            categories can be defined. As such, the bit string consists of
            1000 bits with the least significant bit indicating whether
            application category with SNMP index 1 applies and the most
            significant bit indicating whether application category with SNMP
            index 1000 applies.

            For further details on these formats, refer to the comment on the
            ConditionSpec type."
        ::= { aoCntRuleEntry 43 }


    aoCntRuleServiceClassCondition OBJECT-TYPE
        SYNTAX  ConditionSpec
        ACCESS  read-write
        STATUS  mandatory
        DESCRIPTION
            "Condition pertaining to the service class associated with the
            application originating the SM. For the specification for this
            condition, the following formats apply:

            1) NONE
            2) BITSTRING

            When the format is BITSTRING, the relating bit string specifies
            which service classes apply. Each bit in the bit string relates
            to a specific service class. If the bit is 1, the service class
            applies.
            Otherwise, if the bit is 0, the service class does not apply. Up
            to 1000 service classes can be defined. As such, the bit string
            consists of 1000 bits with the least significant bit indicating
            whether service class with SNMP index 1 applies and the most
            significant bit indicating whether service class with SNMP index
            1000 applies.

            For further details on these formats, refer to the comment on the
            ConditionSpec type."
        ::= { aoCntRuleEntry 44 }


    aoCntRuleProtocolCondition OBJECT-TYPE
        SYNTAX  ConditionSpec
        ACCESS  read-write
        STATUS  mandatory
        DESCRIPTION
            "Condition pertaining to the protocol used by the originating
            application to submit the SM. For the specification for this
            condition, the following formats apply:

            1) NONE
            2) BITSTRING

            When the format is BITSTRING, the relating bit string specifies
            which protocols apply. Each bit in the bit string relates to a
            specific protocol. If the bit is 1, the protocol applies.
            Otherwise, if the bit is 0, the protocol does not apply. Three
            protocols are used by applications to submit an SM. These
            protocols are UCP, SMPP and CIMD. As such, the bit string
            consists of 3 bits with
            - bit 0 indicating whether the UCP protocol applies,
            - bit 1 indicating whether the SMPP protocol applies, and
            - bit 2 indicating whether the CIMD protocol applies.
            Note that bit 0 is the least significant bit and bit 2 the most
            significant bit.

            For further details on these formats, refer to the comment on the
            ConditionSpec type."
        ::= { aoCntRuleEntry 45 }


    aoCntRuleOperationCondition OBJECT-TYPE
        SYNTAX  ConditionSpec
        ACCESS  read-write
        STATUS  mandatory
        DESCRIPTION
            "Condition pertaining to the operation used by the originating
            application to submit the SM. For the specification for this
            condition, the following formats apply:

            1) NONE
            2) BITSTRING

            When the format is BITSTRING, the relating bit string specifies
            which operations apply. Not all bits of the bit string are used.
            Each bit in the bit string that is used relates to a specific
            operation. If the bit is 1, the operation applies. Otherwise, if
            the bit is 0, the operation does not apply. The bit string
            consists of 32 bits and has the following mapping:

              ---------------------------------------------------------------
              bit  operation
              ---------------------------------------------------------------
               0   UCP Call input operation -01
               1   UCP Multiple address call input operation -02
               2   UCP Call input with supplementary services operation -03
               3   UCP MS message transfer operation -30
               4   UCP Submit Short Message operation -51
               9   UCP operation other than the ones above
               10  SMPP SubmitSm
               12  SMPP SubmitMulti
               13  SMPP DataSm
               19  SMPP operation other than the ones above
               20  CIMD SubmitMessage
               29  CIMD operation other than the ones above
               30  operation from another protocol than UCP, SMPP and CIMD
              --------------------------------------------------------------

            Note that bit 0 is the least significant bit and bit 2 the most
            significant bit.

            For further details on these formats, refer to the comment on the
            ConditionSpec type."
        ::= { aoCntRuleEntry 46 }


    aoCntRuleOriginatorCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST

            For details on these formats, refer to the comment on the
            ConditionSpec type."
        ::= { aoCntRuleEntry 47 }


    aoCntRuleOriginatorTonCondition OBJECT-TYPE
        SYNTAX  ConditionSpec
        ACCESS  read-write
        STATUS  mandatory
        DESCRIPTION
            "Condition pertaining to the type of number (TON) specified for
            the originator of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { aoCntRuleEntry 48 }


    aoCntRuleOriginatorNpiCondition OBJECT-TYPE
        SYNTAX  ConditionSpec
        ACCESS  read-write
        STATUS  mandatory
        DESCRIPTION
            "Condition pertaining to the numbering plan identification (NPI)
            specified for the originator of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not
            apply.  The range of value for the NPI is 0-15. As such, the bit
            string consists of 16 bits with the least significant bit
            indicating whether NPI value 0 applies and the most significant
            bit indicating whether NPI value 15 applies.

            For further details on these formats, refer to the comment on the
            ConditionSpec type.

            For details on the values supported for the NPI, refer to GSM
            03.40."
        ::= { aoCntRuleEntry 49 }


    aoCntRuleRecipientCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) APPLICATION
            8) LIST

            For details on these formats, refer to the comment on the
            ConditionSpec type."
        ::= { aoCntRuleEntry 50 }


    aoCntRuleRecipientTonCondition OBJECT-TYPE
        SYNTAX  ConditionSpec
        ACCESS  read-write
        STATUS  mandatory
        DESCRIPTION
            "Condition pertaining to the type of number (TON) specified for
            the recipient of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not
            apply.  The range of value for the TON is 0-7. As such, the bit
            string consists of 8 bits with the least significant bit
            indicating whether TON value 0 applies and the most significant
            bit indicating whether TON value 7 applies.

            For further details on these formats, refer to the comment on the
            ConditionSpec type.

            For details on the values supported for the TON, refer to GSM
            03.40."
        ::= { aoCntRuleEntry 51 }


    aoCntRuleRecipientNpiCondition OBJECT-TYPE
        SYNTAX  ConditionSpec
        ACCESS  read-write
        STATUS  mandatory
        DESCRIPTION
            "Condition pertaining to the numbering plan identification (NPI)
            specified for the recipient of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { aoCntRuleEntry 52 }


    aoCntRuleUserDataCondition OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT
            5) TEXTLENGTH

            For details on these formats, refer to the comment on the
            ConditionSpec type."
        ::= { aoCntRuleEntry 53 }


    aoCntRuleUserDataHeaderIndicationCondition OBJECT-TYPE
        SYNTAX  ConditionSpec
        ACCESS  read-write
        STATUS  mandatory
        DESCRIPTION
            "Condition pertaining to the user data header indication specified
            in the SM. For the specification for this condition, the following
            formats apply:

            1) NONE
            2) BITVALUE

            For details on these formats, refer to the comment on the
            ConditionSpec type."
        ::= { aoCntRuleEntry 54 }


    aoCntRuleUserDataHeaderCondition OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to GSM 03.40. The
            values for most common information element identifiers are:

            00 hex - Concatenated short message
            01 hex - Special SMS Message Indication
            04 hex - application port addressing scheme, 8 bit address
            05 hex - application port addressing scheme, 16 bit address
            06 hex - SMSC Control Parameters
            07 hex - UDH Source Indicator "
        ::= { aoCntRuleEntry 55 }


    aoCntRuleReplyPathCondition OBJECT-TYPE
        SYNTAX  ConditionSpec
        ACCESS  read-write
        STATUS  mandatory
        DESCRIPTION
            "Condition pertaining to the reply path indication specified in
            the SM. For the specification for this condition, the following
            formats apply:

            1) NONE
            2) BITVALUE

            For details on these formats, refer to the comment on the
            ConditionSpec type."
        ::= { aoCntRuleEntry 56 }


    aoCntRuleNotificationAddressCondition OBJECT-TYPE
        SYNTAX  ConditionSpec
        ACCESS  read-write
        STATUS  mandatory
        DESCRIPTION
            "Condition pertaining to the notification address that is
            specified in the SM. For the specification for this condition,
            the following formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) SINGLETCPIPADDRESS
            12) SINGLEX121ADDRESS
            13) LIST

            For details on these formats, refer to the comment on the
            ConditionSpec type."
        ::= { aoCntRuleEntry 57 }


    aoCntRuleNotificationRequestCondition OBJECT-TYPE
        SYNTAX  ConditionSpec
        ACCESS  read-write
        STATUS  mandatory
        DESCRIPTION
            "Condition pertaining to the notification request indication
            specified in the SM. For the specification for this condition, the
            following formats apply:

            1) NONE
            2) BITVALUE

            For details on these formats, refer to the comment on the
            ConditionSpec type."
        ::= { aoCntRuleEntry 58 }


    aoCntRuleNotificationTypeCondition OBJECT-TYPE
        SYNTAX  ConditionSpec
        ACCESS  read-write
        STATUS  mandatory
        DESCRIPTION
            "Condition pertaining to the notification type specified in
            the SM. For the specification for this condition, the following
            formats apply:

            1) NONE
            2) BITSTRING

            When the format is BITSTRING, the relating bit string specifies
            which notification types apply. Each bit in the bit string
            relates to a specific notification type. If the bit is 1, the
            notification type applies. Otherwise, if the bit is 0, the
            notification type does not apply. Three notification types exist.
            notification type. These notification types are 'delivered', 'not
            delivered', and 'buffered'.
            As such, the bit string consists of 3 bits with
            - bit 0 indicating 'delivered' ,
            - bit 1 indicating 'not delivered', and
            - bit 2 indicating 'buffered'.
            Note that bit 0 is the least significant bit and bit 2 the most
            significant bit.

            For further details on these formats, refer to the comment on the
            ConditionSpec type."
        ::= { aoCntRuleEntry 59 }


    aoCntRuleSingleShotIndicatorCondition OBJECT-TYPE
        SYNTAX  ConditionSpec
        ACCESS  read-write
        STATUS  mandatory
        DESCRIPTION
            "Condition pertaining to the single shot indicator specified in
            the SM. For the specification for this condition, the following
            formats apply:

            1) NONE
            2) BITVALUE

            For details on these formats, refer to the comment on the
            ConditionSpec type."
        ::= { aoCntRuleEntry 60 }


    aoCntRuleMoreMessagesToSendCondition OBJECT-TYPE
        SYNTAX  ConditionSpec
        ACCESS  read-write
        STATUS  mandatory
        DESCRIPTION
            "Condition pertaining to the more message to send indicator
            specified in the SM. For the specification for this condition, the
            following formats apply:

            1) NONE
            2) BITVALUE

            For details on these formats, refer to the comment on the
            ConditionSpec type."
        ::= { aoCntRuleEntry 61 }


    aoCntRulePriorityCondition OBJECT-TYPE
        SYNTAX  ConditionSpec
        ACCESS  read-write
        STATUS  mandatory
        DESCRIPTION
            "Condition pertaining to the priority level that is specified in
            the SM. For the specification for this condition, the following
            formats apply:

            1) NONE
            2) BITSTRING

            When the format is BITSTRING, the relating bit string specifies
            which priority levels apply. Not all bits of the bit string are
            used. Each bit in the bit string that is used relates to a
            specific priority level. If the bit is 1, the priority level
            applies.
            Otherwise, if the bit is 0, the priority level does not apply.
            The bit string consists of 32 bits and has the following mapping:

              ---------------------------------------------------------------
              bit  operation
              ---------------------------------------------------------------
               0   UCP no priority requested
               1   UCP priority requested
               10  SMPP no priority requested
               11  SMPP priority requested
               20  CIMD priority level 1 (most urgent)
               21  CIMD priority level 2
               22  CIMD priority level 3
               23  CIMD priority level 4
               24  CIMD priority level 5
               25  CIMD priority level 6
               26  CIMD priority level 7
               27  CIMD priority level 8
               28  CIMD priority level 9
              --------------------------------------------------------------

            Note that bit 0 is the least significant bit and bit 2 the most
            significant bit.

            For further details on these formats, refer to the comment on the
            ConditionSpec type."
        ::= { aoCntRuleEntry 62 }


    aoCntRuleProtocolIdCondition OBJECT-TYPE
        SYNTAX  ConditionSpec
        ACCESS  read-write
        STATUS  mandatory
        DESCRIPTION
            "Condition pertaining to the protocol ID specified in the SM. For
            the specification for this condition, the following formats apply:

            1) NONE
            2) BYTEVALUE

            For details on these formats, refer to the comment on the
            ConditionSpec type.

            For details on the values supported for the protocol ID, refer to
            GSM 03.40."
        ::= { aoCntRuleEntry 63 }


    aoCntRuleDataCodingSchemeCondition OBJECT-TYPE
        SYNTAX  ConditionSpec
        ACCESS  read-write
        STATUS  mandatory
        DESCRIPTION
            "Condition pertaining to the data coding scheme specified in the
            SM. For the specification for this condition, the following
            formats apply:

            1) NONE
            2) BYTEVALUE

            For details on these formats, refer to the comment on the
            ConditionSpec type.

            For details on the values supported for the data coding scheme,
            refer to GSM 03.38."
        ::= { aoCntRuleEntry 64 }


    aoCntRuleConcatenatedMessageSegmentsCondition OBJECT-TYPE
        SYNTAX  ConditionSpec
        ACCESS  read-write
        STATUS  mandatory
        DESCRIPTION
            "Condition pertaining to the segment sequence number of a
            concatenated SM. For the specification for this condition, the
            following formats apply:

            1) NONE
            2) BITSTRING

            When the format is BITSTRING, the relating bit string specifies
            which concatenated message segments apply. Each bit in the bit
            string relates to a specific segment of a concatenated message. If
            the bit is 1, the segment applies. Otherwise, if the bit is 0, the
            segment does not apply. The segments are distinguished in three
            groups. As such, the bit string consists of 3 bits with
            - bit 0 indicating whether the segment is the first of the
              concatenated message,
            - bit 1 indicating whether the segment is the last of the
              concatenated message,
            - bit 2 indicating whether the segment is not the first nor the
              last of the concatenated message,
            Note that bit 0 is the least significant bit and bit 2 the most
            significant bit.

            For further details on these formats, refer to the comment on the
            ConditionSpec type."
        ::= { aoCntRuleEntry 65 }


    aoCntRuleUcpAuthenticationCodeCondition OBJECT-TYPE
        SYNTAX  ConditionSpec
        ACCESS  read-write
        STATUS  mandatory
        DESCRIPTION
            "Condition pertaining to the authentication code that is specified
            in the SM. For the specification for this condition, the following
            formats apply:

            1) NONE
            2) DIGITSTRING

            For details on these formats, refer to the comment on the
            ConditionSpec type."
        ::= { aoCntRuleEntry 66 }


    aoCntRuleNotificationPidCondition OBJECT-TYPE
        SYNTAX  ConditionSpec
        ACCESS  read-write
        STATUS  mandatory
        DESCRIPTION
            "Condition pertaining to the notification PID that is specified in
            the SM. For the specification for this condition, the following
            formats apply:

            1) NONE
            2) BITSTRING

            When the format is BITSTRING, the relating bit string specifies
            which address PIDs apply. Each bit in the bit string relates to a
            specific address PID. If the bit is 1, the address PID applies.
            Otherwise, if the bit is 0, the address PIDs does not apply.
            The bit string consists of 8 bits and has the following mapping:

              ---------------------------------------------------------------
              bit  address PID
              ---------------------------------------------------------------
               0   Mobile Station
               1   Fax Group 3
               2   Menu over PSTN
               3   PC application over PSTN
               4   PC application over ISDN
               5   PC application over TCP/IP
               6   PC application over X25
               7   Unknown
              --------------------------------------------------------------

            Note that bit 0 is the least significant bit and bit 2 the most
            significant bit.

            For further details on these formats, refer to the comment on the
            ConditionSpec type."
        ::= { aoCntRuleEntry 67 }


    aoCntRuleLastResortAddressCondition OBJECT-TYPE
        SYNTAX  ConditionSpec
        ACCESS  read-write
        STATUS  mandatory
        DESCRIPTION
            "Condition pertaining to the last resort address that is specified
            in the SM. For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) SINGLETCPIPADDRESS
            12) SINGLEX121ADDRESS
            13) LIST

            For details on these formats, refer to the comment on the
            ConditionSpec type."
        ::= { aoCntRuleEntry 68 }


    aoCntRuleLastResortRequestCondition OBJECT-TYPE
        SYNTAX  ConditionSpec
        ACCESS  read-write
        STATUS  mandatory
        DESCRIPTION
            "Condition pertaining to the last resort request indicator
            specified in the SM. For the specification for this condition, the
            following formats apply:

            1) NONE
            2) BITVALUE

            For details on these formats, refer to the comment on the
            ConditionSpec type."
        ::= { aoCntRuleEntry 69 }


    aoCntRuleLastResortPidCondition OBJECT-TYPE
        SYNTAX  ConditionSpec
        ACCESS  read-write
        STATUS  mandatory
        DESCRIPTION
            "Condition pertaining to the last resort PID that is specified in
            the SM. For the specification for this condition, the following
            formats apply:

            1) NONE
            2) BITSTRING

            When the format is BITSTRING, the relating bit string specifies
            which address PIDs apply. Each bit in the bit string relates to a
            specific address PID. If the bit is 1, the address PID applies.
            Otherwise, if the bit is 0, the address PIDs does not apply.
            The bit string consists of 8 bits and has the following mapping:

              ---------------------------------------------------------------
              bit  address PID
              ---------------------------------------------------------------
               0   Mobile Station
               1   Fax Group 3
               2   Menu over PSTN
               3   PC application over PSTN
               4   PC application over ISDN
               5   PC application over TCP/IP
               6   PC application over X25
               7   Unknown
              --------------------------------------------------------------

            Note that bit 0 is the least significant bit and bit 2 the most
            significant bit.

            For further details on these formats, refer to the comment on the
            ConditionSpec type."
        ::= { aoCntRuleEntry 70 }


    aoCntRuleCimdTariffClassCondition OBJECT-TYPE
        SYNTAX  ConditionSpec
        ACCESS  read-write
        STATUS  mandatory
        DESCRIPTION
            "Condition pertaining to the CIMD tariff class specified in the 
            SM.
            For the specification for this condition, the following formats
            apply:

            1) NONE
            2) BITSTRING

            When the format is BITSTRING, the relating bit string specifies
            which values for the tariff class apply. Each bit in the bit
            string relates to a tariff class. If the bit is 1, the relating
            tariff class applies. Otherwise, if the bit is 0, the relating
            tariff class does not apply. The range of values for the tariff
            class is 0-99. As such, the bit string consists of 100 bits with
            the least significant bit indicating whether tariff class 0
            applies and the most significant bit indicating whether tariff
            class 99 applies.

            For further details on these formats, refer to the comment on the
            ConditionSpec type."
        ::= { aoCntRuleEntry 71 }


    aoCntRuleCimdServiceDescriptionCondition OBJECT-TYPE
        SYNTAX  ConditionSpec
        ACCESS  read-write
        STATUS  mandatory
        DESCRIPTION
            "Condition pertaining to the CIMD service description specified in
            the SM.  For the specification for this condition, the following
            formats apply:

            1) NONE
            2) BITSTRING

            When the format is BITSTRING, the relating bit string specifies
            which values for the service description apply. Each bit in the
            bit string relates to a service description. If the bit is 1, the
            relating service description applies. Otherwise, if the bit is 0,
            the relating service description does not apply. The range of
            values for the service description is 0-99. As such, the bit
            string consists of 100 bits with the least significant bit
            indicating whether service description 0 applies and the most
            significant bit indicating whether service description 99
            applies.

            For further details on these formats, refer to the comment on the
            ConditionSpec type."
        ::= { aoCntRuleEntry 72 }


    aoCntRuleValidityPeriodCondition OBJECT-TYPE
        SYNTAX  ConditionSpec
        ACCESS  read-write
        STATUS  mandatory
        DESCRIPTION
            "Condition pertaining to the validity period that is specified in
            the SM. For the specification for this condition, the following
            formats apply:

            1) NONE
            2) RELATIVETIME

            For details on these formats, refer to the comment on the
            ConditionSpec type."
        ::= { aoCntRuleEntry 73 }


    aoCntRuleDeferredDeliveryTimeCondition OBJECT-TYPE
        SYNTAX  ConditionSpec
        ACCESS  read-write
        STATUS  mandatory
        DESCRIPTION
            "Condition pertaining to the deferred dlivery time that is
            specified in the SM. For the specification for this condition,
            the following formats apply:

            1) NONE
            2) RELATIVETIME

            For details on these formats, refer to the comment on the
            ConditionSpec type."
        ::= { aoCntRuleEntry 74 }

    aoCntRuleSubmitTimeCondition OBJECT-TYPE
        SYNTAX  ConditionSpec
        ACCESS  read-write
        STATUS  mandatory
        DESCRIPTION
            "Condition on the submit-time of the message. For the
            specification for this condition, the following formats apply:

            1) NONE
            2) TIMESPEC

            For further details on these formats, refer to the comment on the
            ConditionSpec type."
        ::= { aoCntRuleEntry 75 }

    aoCntRuleExternalAttributesCondition  OBJECT-TYPE
        SYNTAX  ConditionSpec
        ACCESS  read-write
        STATUS  mandatory
        DESCRIPTION
            "Condition on the 32 boolean atributes that can be set by an 
            external approval application. For the specification for this 
            condition, the following formats apply:

            1) NONE
            2) EXTERNALATTRIBUTES

            When the format is EXTERNALATTRIBUTES, the relating bit mask
            string specifies which external attributes apply and the relating
            bit value string specifies the values for the external
            attributes.          
            Each bit in the bit strings relates to a specific attribute. The
            bit strings consist of 32 bits. The least significant bit
            corresponds to attribute 0. The most significant bit corresponds
            to attribute 31. 
            A bit with value 1 in the bit mask string indicates that the
            relating attribute applies and needs to be checked. A bit with
            value 0 in the bit mask string indicates that the relating
            attribute does not apply and does not need to be checked. 
            A bit with value 1 in the bit value string indicates that the
            relating attribute should be TRUE. A bit with value 0 in the bit
            value string indicates that the relating attribute should be
            FALSE. 

            For further details on these formats, refer to the comment on the
            ConditionSpec type."
        ::= { aoCntRuleEntry 76 }

    aoCntRuleRecipientRoutingNumberGroupCondition OBJECT-TYPE
        SYNTAX  ConditionSpec
        ACCESS  read-write
        STATUS  mandatory
        DESCRIPTION
            "Condition on the group to which the routing number associated
            with the recipient address belongs. For the specification for
            this condition, the following formats apply:

            1) NONE
            2) SNMPINDEX

            When the format is SNMPINDEX, the SNMP index will refer to the
            routingNumberGroupTable. The (non-inverted) condition will
            never match if either the routing number group referred to by
            the condition is not active, or if no routing number has been
            determined for the recipient of the message under consideration.
            The RoutingNumberGroupIndex determines the range of valid numbers
            for the SNMP index."
        ::= { aoCntRuleEntry 77 }

    aoExtCondRuleTable OBJECT-TYPE
        SYNTAX  SEQUENCE OF AoExtCondRuleEntry
        ACCESS  not-accessible
        STATUS  mandatory
        DESCRIPTION
            "A table containing properties, conditions, counters and action
            parameters for each AO ExternalCondition rule.

            An AO ExternalCondition rule matches when all of the following
            conditions are met:
            1) its administrative state is active;
            2) all its (internal) conditions do satisfy;

            In case multiple rules match, all matching rules are applied in
            order of priority of the rules.
            For each matching rule, the specified ExternalCondition is
            evaluated by sending a validationRequest to the ExternalCondition
            application, which will return a evaluationResponse.
            When the ExternalCondition evaluates to True, the next rule will
            be processed. When all matching ExternalCondition rules evaluate
            to True, the AO SM will be routed according to the AO routing
            rules.
            When during the processing of an ExternalCondition rule a rule
            evaluates to False, the FailureAction of that rule will be
            exectuted and further processing of the ExternalCondition rules
            is stopped for this SM."
        ::= { sms 83 }

    aoExtCondRuleEntry OBJECT-TYPE
        SYNTAX  AoExtCondRuleEntry
        ACCESS  not-accessible
        STATUS  mandatory
        DESCRIPTION
            "Table entry specifying a single AO ExternalCondition."
        INDEX   { aoExtCondRuleIndex }
        ::= { aoExtCondRuleTable 1 }

    AoExtCondRuleEntry ::=
        SEQUENCE {
            aoExtCondRuleIndex                        AoExtCondRuleTableIndex,
            aoExtCondRuleAdminState                   AdminState,
            aoExtCondRuleName                         NameString,
            aoExtCondRulePriority                     EciPriority,
            aoExtCondRuleLogProfile                   LogProfile,
            aoExtCondRuleTotalAppliedCounter          Counter,
            aoExtCondRulePassedSubmitOperationCounter Counter,
            aoExtCondRuleBlockedSubmitOperationCounter Counter,
            aoExtCondRulePassedUnknownOperationCounter Counter,
            aoExtCondRuleBlockedUnknownOperationCounter Counter,
            aoExtCondRuleFailureAction                ExtCondAoAction,
            aoExtCondRuleExternalCondition            ConditionSpec,
            aoExtCondRuleApplicationCondition         ConditionSpec,
            aoExtCondRuleApplicationGroupCondition    ConditionSpec,
            aoExtCondRuleApplicationCategoryCondition ConditionSpec,
            aoExtCondRuleServiceClassCondition        ConditionSpec,
            aoExtCondRuleProtocolCondition            ConditionSpec,
            aoExtCondRuleOperationCondition           ConditionSpec,
            aoExtCondRuleOriginatorCondition          ConditionSpec,
            aoExtCondRuleOriginatorTonCondition       ConditionSpec,
            aoExtCondRuleOriginatorNpiCondition       ConditionSpec,
            aoExtCondRuleRecipientCondition           ConditionSpec,
            aoExtCondRuleRecipientTonCondition        ConditionSpec,
            aoExtCondRuleRecipientNpiCondition        ConditionSpec,
            aoExtCondRuleUserDataCondition            ConditionSpec,
            aoExtCondRuleUserDataHeaderIndicationCondition ConditionSpec,
            aoExtCondRuleUserDataHeaderCondition      ConditionSpec,
            aoExtCondRuleReplyPathCondition           ConditionSpec,
            aoExtCondRuleNotificationAddressCondition ConditionSpec,
            aoExtCondRuleNotificationRequestCondition ConditionSpec,
            aoExtCondRuleNotificationTypeCondition    ConditionSpec,
            aoExtCondRuleSingleShotIndicatorCondition ConditionSpec,
            aoExtCondRuleMoreMessagesToSendCondition  ConditionSpec,
            aoExtCondRulePriorityCondition            ConditionSpec,
            aoExtCondRuleProtocolIdCondition          ConditionSpec,
            aoExtCondRuleDataCodingSchemeCondition    ConditionSpec,
            aoExtCondRuleConcatenatedMessageSegmentsCondition ConditionSpec,
            aoExtCondRuleUcpAuthenticationCodeCondition ConditionSpec,
            aoExtCondRuleNotificationPidCondition     ConditionSpec,
            aoExtCondRuleLastResortAddressCondition   ConditionSpec,
            aoExtCondRuleLastResortRequestCondition   ConditionSpec,
            aoExtCondRuleLastResortPidCondition       ConditionSpec,
            aoExtCondRuleCimdTariffClassCondition     ConditionSpec,
            aoExtCondRuleCimdServiceDescriptionCondition ConditionSpec,
            aoExtCondRuleValidityPeriodCondition      ConditionSpec,
            aoExtCondRuleDeferredDeliveryTimeCondition ConditionSpec,
            aoExtCondRuleSubmitTimeCondition          ConditionSpec,
            aoExtCondRuleExternalAttributesCondition  ConditionSpec,
            aoExtCondRuleRecipientRoutingNumberGroupCondition ConditionSpec
        }

    aoExtCondRuleIndex OBJECT-TYPE
        SYNTAX  AoExtCondRuleTableIndex
        ACCESS  read-write
        STATUS  mandatory
        DESCRIPTION
            "Index of entry in AO ExternalCondition table."
        ::= { aoExtCondRuleEntry 1 }

    aoExtCondRuleAdminState OBJECT-TYPE
        SYNTAX  AdminState
        ACCESS  read-write
        STATUS  mandatory
        DESCRIPTION
            "Administrative state of the AO ExternalCondition.

            Transition from 'inactive' to 'active' is only possible when:
            1) name has been supplied;
            2) name is not already in use by another rule;
            3) conditions of rule specifying a network refer to an 'active'
               country and an 'active' network;
            4) conditions of rule specifying a country refer to an 'active'
               country;
            5) conditions of rule specifying an application refer to an
               'active' application;
            6) in case applicationGroupCondition specified, all referred
               groups should exists;
            7) in case applicationCategoryCondition specified, all referred
               categories should exists;
            8) in case serviceClassCondition specified, all referred service
                classes should exists;

            For details, refer to the comment on the AdminState type."
        ::= { aoExtCondRuleEntry 2 }

    aoExtCondRuleName OBJECT-TYPE
        SYNTAX  NameString
        ACCESS  read-write
        STATUS  mandatory
        DESCRIPTION
            "Name of the AO ExternalCondition."
        ::= { aoExtCondRuleEntry 3 }

    aoExtCondRulePriority OBJECT-TYPE
        SYNTAX  EciPriority
        ACCESS  read-write
        STATUS  mandatory
        DESCRIPTION
            "Priority of the AO ExternalCondition rule.
            For details, refer to the comment on the EciPriority type."
        ::= { aoExtCondRuleEntry 4 }

    aoExtCondRuleLogProfile OBJECT-TYPE
        SYNTAX  LogProfile
        ACCESS  read-write
        STATUS  mandatory
        DESCRIPTION
            "Identifier specifying which logging profile should be used. 
            Default is 0 (i.e. 'none')."
        ::= { aoExtCondRuleEntry 5 }
        
    aoExtCondRuleTotalAppliedCounter OBJECT-TYPE
        SYNTAX  Counter
        ACCESS  read-write
        STATUS  mandatory
        DESCRIPTION
            "Counter specifying the number of times that the ExternalCondition
            rule has been applied."
        ::= { aoExtCondRuleEntry 11 }

    aoExtCondRulePassedSubmitOperationCounter OBJECT-TYPE
        SYNTAX  Counter
        ACCESS  read-write
        STATUS  mandatory
        DESCRIPTION
            "Counter specifying the number of times that the ExternalCondition
            rule has been applied to a submit operation with result 'pass'."
        ::= { aoExtCondRuleEntry 12 }

    aoExtCondRuleBlockedSubmitOperationCounter OBJECT-TYPE
        SYNTAX  Counter
        ACCESS  read-write
        STATUS  mandatory
        DESCRIPTION
            "Counter specifying the number of times that the ExternalCondition
            rule has been applied to a submit operation with result 'block'."
        ::= { aoExtCondRuleEntry 13 }

    aoExtCondRulePassedUnknownOperationCounter OBJECT-TYPE
        SYNTAX  Counter
        ACCESS  read-write
        STATUS  mandatory
        DESCRIPTION
            "Counter specifying the number of times that the ExternalCondition
            rule has been applied to an unknown operation with result 'pass'."
        ::= { aoExtCondRuleEntry 14 }

    aoExtCondRuleBlockedUnknownOperationCounter OBJECT-TYPE
        SYNTAX  Counter
        ACCESS  read-write
        STATUS  mandatory
        DESCRIPTION
            "Counter specifying the number of times that the
            ExternalCondition rule has been applied to an unknown operation
            with result 'block'."
        ::= { aoExtCondRuleEntry 15 }

    aoExtCondRuleFailureAction OBJECT-TYPE
        SYNTAX  ExtCondAoAction
        ACCESS  read-write
        STATUS  mandatory
        DESCRIPTION
            "Action to execute when the AO ExternalCondition rule matches,
            but the ExternalCondition evaluates to False.
            For details, refer to the comments on the ExtCondAoAction type."
        ::= { aoExtCondRuleEntry 21 }

    aoExtCondRuleExternalCondition OBJECT-TYPE
        SYNTAX  ConditionSpec
        ACCESS  read-write
        STATUS  mandatory
        DESCRIPTION
            "Condition refering to an external condition application
            which has to validate this rule.
            The following formats apply:
            1) EXTERNALCONDITION

            For details, refer to the ConditionSpec type."
        ::= { aoExtCondRuleEntry 22 }

    aoExtCondRuleApplicationCondition OBJECT-TYPE
        SYNTAX  ConditionSpec
        ACCESS  read-write
        STATUS  mandatory
        DESCRIPTION
            "Condition pertaining to the application originating the SM. For
            the specification for this condition, the following formats
            apply:

            1) NONE
            2) APPLICATION

            For details on these formats, refer to the comment on the
            ConditionSpec type."
        ::= { aoExtCondRuleEntry 41 }

    aoExtCondRuleApplicationGroupCondition OBJECT-TYPE
        SYNTAX  ConditionSpec
        ACCESS  read-write
        STATUS  mandatory
        DESCRIPTION
            "Condition pertaining to the application group associated with
            the application originating the SM. For the specification for
            this condition, the following formats apply:

            1) NONE
            2) BITSTRING

            When the format is BITSTRING, the relating bit string specifies
            which application groups apply. Each bit in the bit string
            relates to a specific application group. If the bit is 1, the
            application group applies. Otherwise, if the bit is 0, the
            application group does not apply. Up to 1000 application
            groups can be defined. As such, the bit string consists of 1000
            bits with the least significant bit indicating whether application
            group with SNMP index 1 applies and the most significant bit
            indicating whether application group with SNMP index 1000 applies.

            For further details on these formats, refer to the comment on the
            ConditionSpec type."
        ::= { aoExtCondRuleEntry 42 }


    aoExtCondRuleApplicationCategoryCondition OBJECT-TYPE
        SYNTAX  ConditionSpec
        ACCESS  read-write
        STATUS  mandatory
        DESCRIPTION
            "Condition pertaining to the application categories associated
            with the application originating the SM. For the specification
            for this condition, the following formats apply:

            1) NONE
            2) BITSTRING

            When the format is BITSTRING, the relating bit string specifies
            which application categories apply. Each bit in the bit string
            relates to a specific application category. If the bit is 1, the
            application category applies. Otherwise, if the bit is 0, the
            application category does not apply. Up to 1000 application
            categories can be defined. As such, the bit string consists of
            1000 bits with the least significant bit indicating whether
            application category with SNMP index 1 applies and the most
            significant bit indicating whether application category with SNMP
            index 1000 applies.

            For further details on these formats, refer to the comment on the
            ConditionSpec type."
        ::= { aoExtCondRuleEntry 43 }


    aoExtCondRuleServiceClassCondition OBJECT-TYPE
        SYNTAX  ConditionSpec
        ACCESS  read-write
        STATUS  mandatory
        DESCRIPTION
            "Condition pertaining to the service class associated with the
            application originating the SM. For the specification for this
            condition, the following formats apply:

            1) NONE
            2) BITSTRING

            When the format is BITSTRING, the relating bit string specifies
            which service classes apply. Each bit in the bit string relates
            to a specific service class. If the bit is 1, the service class
            applies.
            Otherwise, if the bit is 0, the service class does not apply. Up
            to 1000 service classes can be defined. As such, the bit string
            consists of 1000 bits with the least significant bit indicating
            whether service class with SNMP index 1 applies and the most
            significant bit indicating whether service class with SNMP index
            1000 applies.

            For further details on these formats, refer to the comment on the
            ConditionSpec type."
        ::= { aoExtCondRuleEntry 44 }


    aoExtCondRuleProtocolCondition OBJECT-TYPE
        SYNTAX  ConditionSpec
        ACCESS  read-write
        STATUS  mandatory
        DESCRIPTION
            "Condition pertaining to the protocol used by the originating
            application to submit the SM. For the specification for this
            condition, the following formats apply:

            1) NONE
            2) BITSTRING

            When the format is BITSTRING, the relating bit string specifies
            which protocols apply. Each bit in the bit string relates to a
            specific protocol. If the bit is 1, the protocol applies.
            Otherwise, if the bit is 0, the protocol does not apply. Three
            protocols are used by applications to submit an SM. These
            protocols are UCP, SMPP and CIMD. As such, the bit string
            consists of 3 bits with
            - bit 0 indicating whether the UCP protocol applies,
            - bit 1 indicating whether the SMPP protocol applies, and
            - bit 2 indicating whether the CIMD protocol applies.
            Note that bit 0 is the least significant bit and bit 2 the most
            significant bit.

            For further details on these formats, refer to the comment on the
            ConditionSpec type."
        ::= { aoExtCondRuleEntry 45 }


    aoExtCondRuleOperationCondition OBJECT-TYPE
        SYNTAX  ConditionSpec
        ACCESS  read-write
        STATUS  mandatory
        DESCRIPTION
            "Condition pertaining to the operation used by the originating
            application to submit the SM. For the specification for this
            condition, the following formats apply:

            1) NONE
            2) BITSTRING

            When the format is BITSTRING, the relating bit string specifies
            which operations apply. Not all bits of the bit string are used.
            Each bit in the bit string that is used relates to a specific
            operation. If the bit is 1, the operation applies. Otherwise, if
            the bit is 0, the operation does not apply. The bit string
            consists of 32 bits and has the following mapping:

              ---------------------------------------------------------------
              bit  operation
              ---------------------------------------------------------------
               0   UCP Call input operation -01
               1   UCP Multiple address call input operation -02
               2   UCP Call input with supplementary services operation -03
               3   UCP MS message transfer operation -30
               4   UCP Submit Short Message operation -51
               9   UCP operation other than the ones above
               10  SMPP SubmitSm
               12  SMPP SubmitMulti
               13  SMPP DataSm
               19  SMPP operation other than the ones above
               20  CIMD SubmitMessage
               29  CIMD operation other than the ones above
               30  operation from another protocol than UCP, SMPP and CIMD
              --------------------------------------------------------------

            Note that bit 0 is the least significant bit and bit 2 the most
            significant bit.

            For further details on these formats, refer to the comment on the
            ConditionSpec type."
        ::= { aoExtCondRuleEntry 46 }


    aoExtCondRuleOriginatorCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST

            For details on these formats, refer to the comment on the
            ConditionSpec type."
        ::= { aoExtCondRuleEntry 47 }


    aoExtCondRuleOriginatorTonCondition OBJECT-TYPE
        SYNTAX  ConditionSpec
        ACCESS  read-write
        STATUS  mandatory
        DESCRIPTION
            "Condition pertaining to the type of number (TON) specified for
            the originator of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { aoExtCondRuleEntry 48 }


    aoExtCondRuleOriginatorNpiCondition OBJECT-TYPE
        SYNTAX  ConditionSpec
        ACCESS  read-write
        STATUS  mandatory
        DESCRIPTION
            "Condition pertaining to the numbering plan identification (NPI)
            specified for the originator of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { aoExtCondRuleEntry 49 }


    aoExtCondRuleRecipientCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) APPLICATION
            8) LIST

            For details on these formats, refer to the comment on the
            ConditionSpec type."
        ::= { aoExtCondRuleEntry 50 }


    aoExtCondRuleRecipientTonCondition OBJECT-TYPE
        SYNTAX  ConditionSpec
        ACCESS  read-write
        STATUS  mandatory
        DESCRIPTION
            "Condition pertaining to the type of number (TON) specified for
            the recipient of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { aoExtCondRuleEntry 51 }


    aoExtCondRuleRecipientNpiCondition OBJECT-TYPE
        SYNTAX  ConditionSpec
        ACCESS  read-write
        STATUS  mandatory
        DESCRIPTION
            "Condition pertaining to the numbering plan identification (NPI)
            specified for the recipient of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { aoExtCondRuleEntry 52 }


    aoExtCondRuleUserDataCondition OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT
            5) TEXTLENGTH

            For details on these formats, refer to the comment on the
            ConditionSpec type."
        ::= { aoExtCondRuleEntry 53 }


    aoExtCondRuleUserDataHeaderIndicationCondition OBJECT-TYPE
        SYNTAX  ConditionSpec
        ACCESS  read-write
        STATUS  mandatory
        DESCRIPTION
            "Condition pertaining to the user data header indication specified
            in the SM. For the specification for this condition, the following
            formats apply:

            1) NONE
            2) BITVALUE

            For details on these formats, refer to the comment on the
            ConditionSpec type."
        ::= { aoExtCondRuleEntry 54 }


    aoExtCondRuleUserDataHeaderCondition OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to GSM 03.40. The
            values for most common information element identifiers are:

            00 hex - Concatenated short message
            01 hex - Special SMS Message Indication
            04 hex - application port addressing scheme, 8 bit address
            05 hex - application port addressing scheme, 16 bit address
            06 hex - SMSC Control Parameters
            07 hex - UDH Source Indicator "
        ::= { aoExtCondRuleEntry 55 }


    aoExtCondRuleReplyPathCondition OBJECT-TYPE
        SYNTAX  ConditionSpec
        ACCESS  read-write
        STATUS  mandatory
        DESCRIPTION
            "Condition pertaining to the reply path indication specified in
            the SM. For the specification for this condition, the following
            formats apply:

            1) NONE
            2) BITVALUE

            For details on these formats, refer to the comment on the
            ConditionSpec type."
        ::= { aoExtCondRuleEntry 56 }


    aoExtCondRuleNotificationAddressCondition OBJECT-TYPE
        SYNTAX  ConditionSpec
        ACCESS  read-write
        STATUS  mandatory
        DESCRIPTION
            "Condition pertaining to the notification address that is
            specified in the SM. For the specification for this condition,
            the following formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) SINGLETCPIPADDRESS
            12) SINGLEX121ADDRESS
            13) LIST

            For details on these formats, refer to the comment on the
            ConditionSpec type."
        ::= { aoExtCondRuleEntry 57 }


    aoExtCondRuleNotificationRequestCondition OBJECT-TYPE
        SYNTAX  ConditionSpec
        ACCESS  read-write
        STATUS  mandatory
        DESCRIPTION
            "Condition pertaining to the notification request indication
            specified in the SM. For the specification for this condition, the
            following formats apply:

            1) NONE
            2) BITVALUE

            For details on these formats, refer to the comment on the
            ConditionSpec type."
        ::= { aoExtCondRuleEntry 58 }


    aoExtCondRuleNotificationTypeCondition OBJECT-TYPE
        SYNTAX  ConditionSpec
        ACCESS  read-write
        STATUS  mandatory
        DESCRIPTION
            "Condition pertaining to the notification type specified in
            the SM. For the specification for this condition, the following
            formats apply:

            1) NONE
            2) BITSTRING

            When the format is BITSTRING, the relating bit string specifies
            which notification types apply. Each bit in the bit string
            relates to a specific notification type. If the bit is 1, the
            notification type applies. Otherwise, if the bit is 0, the
            notification type does not apply. Three notification types exist.
            notification type. These notification types are 'delivered', 'not
            delivered', and 'buffered'.
            As such, the bit string consists of 3 bits with
            - bit 0 indicating 'delivered' ,
            - bit 1 indicating 'not delivered', and
            - bit 2 indicating 'buffered'.
            Note that bit 0 is the least significant bit and bit 2 the most
            significant bit.

            For further details on these formats, refer to the comment on the
            ConditionSpec type."
        ::= { aoExtCondRuleEntry 59 }


    aoExtCondRuleSingleShotIndicatorCondition OBJECT-TYPE
        SYNTAX  ConditionSpec
        ACCESS  read-write
        STATUS  mandatory
        DESCRIPTION
            "Condition pertaining to the single shot indicator specified in
            the SM. For the specification for this condition, the following
            formats apply:

            1) NONE
            2) BITVALUE

            For details on these formats, refer to the comment on the
            ConditionSpec type."
        ::= { aoExtCondRuleEntry 60 }


    aoExtCondRuleMoreMessagesToSendCondition OBJECT-TYPE
        SYNTAX  ConditionSpec
        ACCESS  read-write
        STATUS  mandatory
        DESCRIPTION
            "Condition pertaining to the more message to send indicator
            specified in the SM. For the specification for this condition, the
            following formats apply:

            1) NONE
            2) BITVALUE

            For details on these formats, refer to the comment on the
            ConditionSpec type."
        ::= { aoExtCondRuleEntry 61 }


    aoExtCondRulePriorityCondition OBJECT-TYPE
        SYNTAX  ConditionSpec
        ACCESS  read-write
        STATUS  mandatory
        DESCRIPTION
            "Condition pertaining to the priority level that is specified in
            the SM. For the specification for this condition, the following
            formats apply:

            1) NONE
            2) BITSTRING

            When the format is BITSTRING, the relating bit string specifies
            which priority levels apply. Not all bits of the bit string are
            used. Each bit in the bit string that is used relates to a
            specific priority level. If the bit is 1, the priority level
            applies.
            Otherwise, if the bit is 0, the priority level does not apply. The
            bit string consists of 32 bits and has the following mapping:

              ---------------------------------------------------------------
              bit  operation
              ---------------------------------------------------------------
               0   UCP no priority requested
               1   UCP priority requested
               10  SMPP no priority requested
               11  SMPP priority requested
               20  CIMD priority level 1 (most urgent)
               21  CIMD priority level 2
               22  CIMD priority level 3
               23  CIMD priority level 4
               24  CIMD priority level 5
               25  CIMD priority level 6
               26  CIMD priority level 7
               27  CIMD priority level 8
               28  CIMD priority level 9
              --------------------------------------------------------------

            Note that bit 0 is the least significant bit and bit 2 the most
            significant bit.

            For further details on these formats, refer to the comment on the
            ConditionSpec type."
        ::= { aoExtCondRuleEntry 62 }


    aoExtCondRuleProtocolIdCondition OBJECT-TYPE
        SYNTAX  ConditionSpec
        ACCESS  read-write
        STATUS  mandatory
        DESCRIPTION
            "Condition pertaining to the protocol ID specified in the SM. For
            the specification for this condition, the following formats apply:

            1) NONE
            2) BYTEVALUE

            For details on these formats, refer to the comment on the
            ConditionSpec type.

            For details on the values supported for the protocol ID, refer to
            GSM 03.40."
        ::= { aoExtCondRuleEntry 63 }


    aoExtCondRuleDataCodingSchemeCondition OBJECT-TYPE
        SYNTAX  ConditionSpec
        ACCESS  read-write
        STATUS  mandatory
        DESCRIPTION
            "Condition pertaining to the data coding scheme specified in the
            SM. For the specification for this condition, the following
            formats apply:

            1) NONE
            2) BYTEVALUE

            For details on these formats, refer to the comment on the
            ConditionSpec type.

            For details on the values supported for the data coding scheme,
            refer to GSM 03.38."
        ::= { aoExtCondRuleEntry 64 }


    aoExtCondRuleConcatenatedMessageSegmentsCondition OBJECT-TYPE
        SYNTAX  ConditionSpec
        ACCESS  read-write
        STATUS  mandatory
        DESCRIPTION
            "Condition pertaining to the segment sequence number of a
            concatenated SM. For the specification for this condition, the
            following formats apply:

            1) NONE
            2) BITSTRING

            When the format is BITSTRING, the relating bit string specifies
            which concatenated message segments apply. Each bit in the bit
            string relates to a specific segment of a concatenated message. If
            the bit is 1, the segment applies. Otherwise, if the bit is 0, the
            segment does not apply. The segments are distinguished in three
            groups. As such, the bit string consists of 3 bits with
            - bit 0 indicating whether the segment is the first of the
              concatenated message,
            - bit 1 indicating whether the segment is the last of the
              concatenated message,
            - bit 2 indicating whether the segment is not the first nor the
              last of the concatenated message,
            Note that bit 0 is the least significant bit and bit 2 the most
            significant bit.

            For further details on these formats, refer to the comment on the
            ConditionSpec type."
        ::= { aoExtCondRuleEntry 65 }


    aoExtCondRuleUcpAuthenticationCodeCondition OBJECT-TYPE
        SYNTAX  ConditionSpec
        ACCESS  read-write
        STATUS  mandatory
        DESCRIPTION
            "Condition pertaining to the authentication code that is specified
            in the SM. For the specification for this condition, the following
            formats apply:

            1) NONE
            2) DIGITSTRING

            For details on these formats, refer to the comment on the
            ConditionSpec type."
        ::= { aoExtCondRuleEntry 66 }


    aoExtCondRuleNotificationPidCondition OBJECT-TYPE
        SYNTAX  ConditionSpec
        ACCESS  read-write
        STATUS  mandatory
        DESCRIPTION
            "Condition pertaining to the notification PID that is specified in
            the SM. For the specification for this condition, the following
            formats apply:

            1) NONE
            2) BITSTRING

            When the format is BITSTRING, the relating bit string specifies
            which address PIDs apply. Each bit in the bit string relates to a
            specific address PID. If the bit is 1, the address PID applies.
            Otherwise, if the bit is 0, the address PIDs does not apply.
            The bit string consists of 8 bits and has the following mapping:

              ---------------------------------------------------------------
              bit  address PID
              ---------------------------------------------------------------
               0   Mobile Station
               1   Fax Group 3
               2   Menu over PSTN
               3   PC application over PSTN
               4   PC application over ISDN
               5   PC application over TCP/IP
               6   PC application over X25
               7   Unknown
              --------------------------------------------------------------

            Note that bit 0 is the least significant bit and bit 2 the most
            significant bit.

            For further details on these formats, refer to the comment on the
            ConditionSpec type."
        ::= { aoExtCondRuleEntry 67 }


    aoExtCondRuleLastResortAddressCondition OBJECT-TYPE
        SYNTAX  ConditionSpec
        ACCESS  read-write
        STATUS  mandatory
        DESCRIPTION
            "Condition pertaining to the last resort address that is specified
            in the SM. For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) SINGLETCPIPADDRESS
            12) SINGLEX121ADDRESS
            13) LIST

            For details on these formats, refer to the comment on the
            ConditionSpec type."
        ::= { aoExtCondRuleEntry 68 }


    aoExtCondRuleLastResortRequestCondition OBJECT-TYPE
        SYNTAX  ConditionSpec
        ACCESS  read-write
        STATUS  mandatory
        DESCRIPTION
            "Condition pertaining to the last resort request indicator
            specified in the SM. For the specification for this condition, the
            following formats apply:

            1) NONE
            2) BITVALUE

            For details on these formats, refer to the comment on the
            ConditionSpec type."
        ::= { aoExtCondRuleEntry 69 }


    aoExtCondRuleLastResortPidCondition OBJECT-TYPE
        SYNTAX  ConditionSpec
        ACCESS  read-write
        STATUS  mandatory
        DESCRIPTION
            "Condition pertaining to the last resort PID that is specified in
            the SM. For the specification for this condition, the following
            formats apply:

            1) NONE
            2) BITSTRING

            When the format is BITSTRING, the relating bit string specifies
            which address PIDs apply. Each bit in the bit string relates to a
            specific address PID. If the bit is 1, the address PID applies.
            Otherwise, if the bit is 0, the address PIDs does not apply.
            The bit string consists of 8 bits and has the following mapping:

              ---------------------------------------------------------------
              bit  address PID
              ---------------------------------------------------------------
               0   Mobile Station
               1   Fax Group 3
               2   Menu over PSTN
               3   PC application over PSTN
               4   PC application over ISDN
               5   PC application over TCP/IP
               6   PC application over X25
               7   Unknown
              --------------------------------------------------------------

            Note that bit 0 is the least significant bit and bit 2 the most
            significant bit.

            For further details on these formats, refer to the comment on the
            ConditionSpec type."
        ::= { aoExtCondRuleEntry 70 }


    aoExtCondRuleCimdTariffClassCondition OBJECT-TYPE
        SYNTAX  ConditionSpec
        ACCESS  read-write
        STATUS  mandatory
        DESCRIPTION
            "Condition pertaining to the CIMD tariff class specified in the
            SM.  For the specification for this condition, the following
            formats apply:

            1) NONE
            2) BITSTRING

            When the format is BITSTRING, the relating bit string specifies
            which values for the tariff class apply. Each bit in the bit
            string relates to a tariff class. If the bit is 1, the relating
            tariff class applies. Otherwise, if the bit is 0, the relating
            tariff class does not apply. The range of values for the tariff
            class is 0-99. As such, the bit string consists of 100 bits with
            the least significant bit indicating whether tariff class 0
            applies and the most significant bit indicating whether tariff
            class 99 applies.

            For further details on these formats, refer to the comment on the
            ConditionSpec type."
        ::= { aoExtCondRuleEntry 71 }


    aoExtCondRuleCimdServiceDescriptionCondition OBJECT-TYPE
        SYNTAX  ConditionSpec
        ACCESS  read-write
        STATUS  mandatory
        DESCRIPTION
            "Condition pertaining to the CIMD service description specified in
            the SM. For the specification for this condition, the following
            formats apply:

            1) NONE
            2) BITSTRING

            When the format is BITSTRING, the relating bit string specifies
            which values for the service description apply. Each bit in the
            bit string relates to a service description. If the bit is 1, the
            relating service description applies. Otherwise, if the bit is 0,
            the relating service description does not apply. The range of
            values for the service description is 0-99. As such, the bit
            string consists of 100 bits with the least significant bit
            indicating whether service description 0 applies and the most
            significant bit indicating whether service description 99
            applies.

            For further details on these formats, refer to the comment on the
            ConditionSpec type."
        ::= { aoExtCondRuleEntry 72 }


    aoExtCondRuleValidityPeriodCondition OBJECT-TYPE
        SYNTAX  ConditionSpec
        ACCESS  read-write
        STATUS  mandatory
        DESCRIPTION
            "Condition pertaining to the validity period that is specified in
            the SM. For the specification for this condition, the following
            formats apply:

            1) NONE
            2) RELATIVETIME

            For details on these formats, refer to the comment on the
            ConditionSpec type."
        ::= { aoExtCondRuleEntry 73 }


    aoExtCondRuleDeferredDeliveryTimeCondition OBJECT-TYPE
        SYNTAX  ConditionSpec
        ACCESS  read-write
        STATUS  mandatory
        DESCRIPTION
            "Condition pertaining to the deferred dlivery time that is
            specified in the SM. For the specification for this condition,
            the following formats apply:

            1) NONE
            2) RELATIVETIME

            For details on these formats, refer to the comment on the
            ConditionSpec type."
        ::= { aoExtCondRuleEntry 74 }

    aoExtCondRuleSubmitTimeCondition OBJECT-TYPE
        SYNTAX  ConditionSpec
        ACCESS  read-write
        STATUS  mandatory
        DESCRIPTION
            "Condition on the submit-time of the message. For the
            specification for this condition, the following formats apply:

            1) NONE
            2) TIMESPEC

            For further details on these formats, refer to the comment on the
            ConditionSpec type."
        ::= { aoExtCondRuleEntry 76 }

    aoExtCondRuleExternalAttributesCondition  OBJECT-TYPE
        SYNTAX  ConditionSpec
        ACCESS  read-write
        STATUS  mandatory
        DESCRIPTION
            "Condition on the 32 boolean atributes that can be set by an 
            external approval application. For the specification for this 
            condition, the following formats apply:

            1) NONE
            2) EXTERNALATTRIBUTES

            When the format is EXTERNALATTRIBUTES, the relating bit mask 
            string  specifies which external attributes apply and the relating 
            bit value string specifies the values for the external attributes.          
            Each bit in the bit strings relates to a specific attribute. The 
            bit strings consist of 32 bits. The least significant bit 
            corresponds to attribute 0. The most significant bit corresponds 
            to attribute 31. 
            A bit with value 1 in the bit mask string indicates that the 
            relating attribute applies and needs to be checked. A bit with 
            value 0 in the bit mask string indicates that the relating 
            attribute does not apply and does not need to be checked. 
            A bit with value 1 in the bit value string indicates that the 
            relating attribute should be TRUE. A bit with value 0 in the bit 
            value string indicates that the relating attribute should be 
            FALSE. 

            For further details on these formats, refer to the comment on the
            ConditionSpec type."
        ::= { aoExtCondRuleEntry 77 }

    aoExtCondRuleRecipientRoutingNumberGroupCondition OBJECT-TYPE
        SYNTAX  ConditionSpec
        ACCESS  read-write
        STATUS  mandatory
        DESCRIPTION
            "Condition on the group to which the routing number associated
            with the recipient address belongs. For the specification for
            this condition, the following formats apply:

            1) NONE
            2) SNMPINDEX

            When the format is SNMPINDEX, the SNMP index will refer to the
            routingNumberGroupTable. The (non-inverted) condition will
            never match if either the routing number group referred to by
            the condition is not active, or if no routing number has been
            determined for the recipient of the message under consideration.
            The RoutingNumberGroupIndex determines the range of valid numbers
            for the SNMP index."
        ::= { aoExtCondRuleEntry 78 }

    -- aoModifierTable

    aoModifierTable OBJECT-TYPE
        SYNTAX  SEQUENCE OF AoModifierEntry
        ACCESS  not-accessible
        STATUS  mandatory
        DESCRIPTION
            "A list of AO modifier entries."
        ::= { sms 84 }

    aoModifierEntry OBJECT-TYPE
        SYNTAX  AoModifierEntry
        ACCESS  not-accessible
        STATUS  mandatory
        DESCRIPTION
            "Table entry specifying a single AO modifier."
        INDEX   { aoModifierIndex }
        ::= { aoModifierTable 1 }

    AoModifierEntry ::=
        SEQUENCE {
            aoModifierIndex                      AoModifierTableIndex,
            aoModifierAdminState                 AdminState,
            aoModifierName                       NameString,
            aoModifierSingleShotIndicator        BitValueModifier,
            aoModifierValidityPeriod             RelativeTime,
            aoModifierDeliveryNotification       BitValueModifier,
            aoModifierNonDeliveryNotification    BitValueModifier,
            aoModifierBufferedNotification       BitValueModifier,
            aoModifierReplaceIfPresent           BitValueModifier,
            aoModifierNotificationAddress        GsmAddress,
            aoModifierNotificationProtocolId     NotificationProtocolModifier,
            aoModifierPriority                   DeliveryPriority,
            aoModifierDeferredDeliveryTime       RelativeTime,
            aoModifierProtocolId                 ByteValueModifier
        }

    aoModifierIndex OBJECT-TYPE
        SYNTAX  AoModifierTableIndex
        ACCESS  not-accessible
        STATUS  mandatory
        DESCRIPTION
            "Index of entry in AO modifier table."
        ::= { aoModifierEntry 1 }

    aoModifierAdminState OBJECT-TYPE
        SYNTAX  AdminState
        ACCESS  read-write
        STATUS  mandatory
        DESCRIPTION
            "Administrative state of the AO modifier.

            Transition from 'inactive' to 'active' is only possible when:
            1) name supplied and not already in use by another AO modifier;

            Transition from 'active' to 'inactive' is only possible when:
            1) AO modifier is not being referred.

            For details, refer to the comment on the AdminState type."
        ::= { aoModifierEntry 2 }

    aoModifierName OBJECT-TYPE
        SYNTAX  NameString
        ACCESS  read-write
        STATUS  mandatory
        DESCRIPTION
            "Name of the AO modifier."
        ::= { aoModifierEntry 3 }

    aoModifierValidityPeriod OBJECT-TYPE
        SYNTAX  RelativeTime
        ACCESS  read-write
        STATUS  mandatory
        DESCRIPTION
            "Modify the validity period. If the value specified is
            0, this means to remove the field if present. If the
            value is -1, this means to leave the field unchanged. Any
            other value is interpreted as seconds in the future.
            Default value is -1."
        ::= { aoModifierEntry 4 }

    aoModifierDeliveryNotification OBJECT-TYPE
        SYNTAX  BitValueModifier
        ACCESS  read-write
        STATUS  mandatory
        DESCRIPTION
            "Indicator specifying if and how to modify the request for a
            delivery notification. By default, this object is set to -1
            (no modification)."
        ::= { aoModifierEntry 5 }

    aoModifierNonDeliveryNotification OBJECT-TYPE
        SYNTAX  BitValueModifier
        ACCESS  read-write
        STATUS  mandatory
        DESCRIPTION
            "Indicator specifying if and how to modify the request for a
            non-delivery notification. By default, this object is set to
            -1 (no modification)."
        ::= { aoModifierEntry 6 }

    aoModifierBufferedNotification OBJECT-TYPE
        SYNTAX  BitValueModifier
        ACCESS  read-write
        STATUS  mandatory
        DESCRIPTION
            "Indicator specifying if and how to modify the request for a
            buffered notification. By default, this object is set to -1
            (no modification)."
        ::= { aoModifierEntry 7 }

    aoModifierReplaceIfPresent OBJECT-TYPE
        SYNTAX  BitValueModifier
        ACCESS  read-write
        STATUS  mandatory
        DESCRIPTION
            "Indicator specifying if and how to modify the
            replace-if-present flag. By default, this object is set to
            -1 (no modification)."
        ::= { aoModifierEntry 8 }

    aoModifierNotificationAddress OBJECT-TYPE
        SYNTAX  GsmAddress
        ACCESS  read-write
        STATUS  mandatory
        DESCRIPTION
            "Used to change the notification address of the SM. An
            empty value means to delete the notification address field.
            A value of IGNORE means to leave the field unchanged.
            Default is IGNORE."
        ::= { aoModifierEntry 9 }

    aoModifierNotificationProtocolId OBJECT-TYPE
        SYNTAX  NotificationProtocolModifier
        ACCESS  read-write
        STATUS  mandatory
        DESCRIPTION
            "Value that the modifier uses to change the protocol ID of
            the SM. The value -1 means no change. This setting applies
            only to messages of protocol. UCP-51 Default is noChange(-1)."
        ::= { aoModifierEntry 10 }

    aoModifierPriority OBJECT-TYPE
        SYNTAX  DeliveryPriority
        ACCESS  read-write
        STATUS  mandatory
        DESCRIPTION
            "Modify the priority flag. If the value is unChanged(-1), this
            means to leave the field unchanged. Values bulk(1),
            low(2)/normal(3)/interactive(4), medium(5)/urgent(6),
            high(7)/emergency(8) and background(0) correspond to the SMPP
            priority levels 0 through 4 respectively. Values normal(3) and
            below correspond to GSM non-priority deliveries. The CIMD priority
            is set numerically to 9 minus the provisioned value of
            aoModifierPriority. Default value is unChanged(-1)."
        ::= { aoModifierEntry 12 }

    aoModifierDeferredDeliveryTime OBJECT-TYPE
        SYNTAX  RelativeTime
        ACCESS  read-write
        STATUS  mandatory
        DESCRIPTION
            "Modify the first-delivery-time field (CIMD),
            schedule-delivery-time field (SMPP), or deferred-delivery-time
            (UCP). If the value specified is 0, this means to remove the field
            if present. If the value is -1, this means to leave the field
            unchanged. Any other value is interpreted as seconds in the
            future. This modifier is applied up front for AO-MT, meaning that
            a deferred-delivery-time that is modified from a positive value to
            zero will make an AO-MT routing path possible (the message would
            normally be dropped). Default value is -1."
        ::= { aoModifierEntry 13 }

    aoModifierProtocolId OBJECT-TYPE
        SYNTAX  ByteValueModifier
        ACCESS  read-write
        STATUS  mandatory
        DESCRIPTION
            "Value that the modifier uses to change the protocol ID of
            the SM. The value -1 means no change. Default is noChange(-1)."
        ::= { aoModifierEntry 14 }

    aoModifierSingleShotIndicator OBJECT-TYPE
        SYNTAX  BitValueModifier
        ACCESS  read-write
        STATUS  mandatory
        DESCRIPTION
            "Value that the AO modifier uses to change the single shot 
            indicator of the SM.

            If not specified or -1 is specified, the AO modifier does not
            affect the single shot indicator of the SM."
        ::= { aoModifierEntry 60 }

    atRtgRuleTable OBJECT-TYPE
        SYNTAX  SEQUENCE OF AtRtgRuleEntry
        ACCESS  not-accessible
        STATUS  mandatory
        DESCRIPTION
            "A table containing properties, conditions, counters and action
            parameters for each AT routing rule.

            An AT routing rule matches when both of the following conditions
            are met:
            1) its administrative state is active;
            2) all its conditions do satisfy;

            In case multiple rules match, the priority of the AT routing rule
            determines which rule applies. When multiple rules have the same
            priority, the AT routing rule with the lowest index has
            precedence."
        ::= { sms 86 }

    atRtgRuleEntry OBJECT-TYPE
        SYNTAX  AtRtgRuleEntry
        ACCESS  not-accessible
        STATUS  mandatory
        DESCRIPTION
            "Table entry specifying a single AT routing rule."
        INDEX   { atRtgRuleIndex }
        ::= { atRtgRuleTable 1 }

    AtRtgRuleEntry ::=
        SEQUENCE {
            atRtgRuleIndex                        AtRtgRuleTableIndex,
            atRtgRuleAdminState                   AdminState,
            atRtgRuleName                         NameString,
            atRtgRulePriority                     Priority,
            atRtgRuleAppliedCounter               Counter,
            atRtgRuleAction                       AtAction,
            atRtgRuleModifier                     AtModifierRef,
            atRtgRuleThroughput                   Throughput,
            atRtgRuleApplicationCondition         ConditionSpec,
            atRtgRuleApplicationGroupCondition    ConditionSpec,
            atRtgRuleApplicationCategoryCondition ConditionSpec,
            atRtgRuleServiceClassCondition        ConditionSpec,
            atRtgRuleProtocolCondition            ConditionSpec,
            atRtgRuleOperationCondition           ConditionSpec,
            atRtgRuleOriginatorCondition          ConditionSpec,
            atRtgRuleOriginatorTonCondition       ConditionSpec,
            atRtgRuleOriginatorNpiCondition       ConditionSpec,
            atRtgRuleOriginatorImsiCondition      ConditionSpec,
            atRtgRuleRecipientCondition           ConditionSpec,
            atRtgRuleRecipientTonCondition        ConditionSpec,
            atRtgRuleRecipientNpiCondition        ConditionSpec,
            atRtgRuleMscOrSgsnCondition           ConditionSpec,
            atRtgRuleSmscCondition                ConditionSpec,
            atRtgRuleUserDataCondition            ConditionSpec,
            atRtgRuleUserDataHeaderIndicationCondition ConditionSpec,
            atRtgRuleUserDataHeaderCondition      ConditionSpec,
            atRtgRuleMoreMessagesToSendCondition  ConditionSpec,
            atRtgRulePriorityCondition            ConditionSpec,
            atRtgRuleProtocolIdCondition          ConditionSpec,
            atRtgRuleDataCodingSchemeCondition    ConditionSpec,
            atRtgRuleConcatenatedMessageSegmentsCondition ConditionSpec,
            atRtgRuleScTimestampCondition         ConditionSpec,
            atRtgRuleDeliveryStatusCondition      ConditionSpec,
            atRtgRuleDeliveryTimestampCondition   ConditionSpec,
            atRtgRuleExternalAttributesCondition  ConditionSpec,
            atRtgRuleXsMessageTypeCondition       ConditionSpec,
            atRtgRuleBilProfileForSubmission      BilProfile,
            atRtgRuleBilProfileForSuccessfulDelivery BilProfile,
            atRtgRuleBilProfileForFailedDelivery  BilProfile,
            atRtgRuleBilProfileForBlockedDelivery BilProfile,
            atRtgRuleBilProfileForDeliveryNotification BilProfile,
            atRtgRuleLogProfile                   LogProfile
        }

    atRtgRuleIndex OBJECT-TYPE
        SYNTAX  AtRtgRuleTableIndex
        ACCESS  read-write
        STATUS  mandatory
        DESCRIPTION
            "Index of entry in AT routing rule table."
        ::= { atRtgRuleEntry 1 }

    atRtgRuleAdminState OBJECT-TYPE
        SYNTAX  AdminState
        ACCESS  read-write
        STATUS  mandatory
        DESCRIPTION
            "Administrative state of the AT routing rule.

            Transition from 'inactive' to 'active' is only possible when:
            1) name has been supplied;
            2) name is not already in use by another rule;
            3) conditions of rule specifying a network refer to an 'active'
               country and an 'active' network;
            4) conditions of rule specifying a country refer to an 'active'
               country;
            5) conditions of rule specifying an application refer to an
               'active' application;
            6) in case routing to application, application being referred to
               exists;
            7) in case modifier specified, modifier being referred to exists.
            8) in case applicationGroupCondition specified, all referred
               groups should exists;
            9) in case applicationCategoryCondition specified, all referred
               categories should exists;
            10) in case serviceClassCondition specified, all referred service
                classes should exists;

            For details, refer to the comment on the AdminState type."
        ::= { atRtgRuleEntry 2 }

    atRtgRuleName OBJECT-TYPE
        SYNTAX  NameString
        ACCESS  read-write
        STATUS  mandatory
        DESCRIPTION
            "Name of the AT routing rule."
        ::= { atRtgRuleEntry 3 }

    atRtgRulePriority OBJECT-TYPE
        SYNTAX  Priority
        ACCESS  read-write
        STATUS  mandatory
        DESCRIPTION
            "Priority of the SMS routing rule.

            For details, refer to the comment on the Priority type."
        ::= { atRtgRuleEntry 4 }

    atRtgRuleAppliedCounter OBJECT-TYPE
        SYNTAX  Counter
        ACCESS  read-write
        STATUS  mandatory
        DESCRIPTION
            "Counter specifying the number of times that the routing rule
            has been applied."
        ::= { atRtgRuleEntry 11 }

    atRtgRuleAction OBJECT-TYPE
        SYNTAX  AtAction
        ACCESS  read-write
        STATUS  mandatory
        DESCRIPTION
            "Action to execute when the AT routing rule applies.

            For details, refer to the comments on the AtAction type."
        ::= { atRtgRuleEntry 21 }

    atRtgRuleModifier OBJECT-TYPE
        SYNTAX  AtModifierRef
        ACCESS  read-write
        STATUS  mandatory
        DESCRIPTION
            "Reference to a modifier which is carried out when AT routing rule
            applies and action of AT routing rule is equal to routeToSmsc,
            routeToApplication, routeToMS, or routeToMsFallbackToSmsc."
        ::= { atRtgRuleEntry 22 }

    atRtgRuleThroughput OBJECT-TYPE
        SYNTAX  Throughput
        ACCESS  read-write
        STATUS  mandatory
        DESCRIPTION
            "Maximum number of AT/SM's per second that are allowed before the
            AT routing rule is effective. Only applicable if AT routing rule
            matches."
        ::= { atRtgRuleEntry 27 }

    atRtgRuleApplicationCondition OBJECT-TYPE
        SYNTAX  ConditionSpec
        ACCESS  read-write
        STATUS  mandatory
        DESCRIPTION
            "Condition pertaining to the application terminating the SM. For
            the specification for this condition, the following formats
            apply:

            1) NONE
            2) APPLICATION

            For details on these formats, refer to the comment on the
            ConditionSpec type."
        ::= { atRtgRuleEntry 41 }

    atRtgRuleApplicationGroupCondition OBJECT-TYPE
        SYNTAX  ConditionSpec
        ACCESS  read-write
        STATUS  mandatory
        DESCRIPTION
            "Condition pertaining to the application group associated with
            the application terminating the SM. For the specification for
            this condition, the following formats apply:

            1) NONE
            2) BITSTRING

            When the format is BITSTRING, the relating bit string specifies
            which application groups apply. Each bit in the bit string
            relates to a specific application group. If the bit is 1, the
            application group applies. Otherwise, if the bit is 0, the
            application group does not apply. Up to 1000 application
            groups can be defined. As such, the bit string consists of 1000
            bits with the least significant bit indicating whether application
            group with SNMP index 1 applies and the most significant bit
            indicating whether application group with SNMP index 1000 applies.

            For further details on these formats, refer to the comment on the
            ConditionSpec type."
        ::= { atRtgRuleEntry 42 }


    atRtgRuleApplicationCategoryCondition OBJECT-TYPE
        SYNTAX  ConditionSpec
        ACCESS  read-write
        STATUS  mandatory
        DESCRIPTION
            "Condition pertaining to the application categories associated
            with the application terminating the SM. For the specification
            for this condition, the following formats apply:

            1) NONE
            2) BITSTRING

            When the format is BITSTRING, the relating bit string specifies
            which application categories apply. Each bit in the bit string
            relates to a specific application category. If the bit is 1, the
            application category applies. Otherwise, if the bit is 0, the
            application category does not apply. Up to 1000 application
            categories can be defined. As such, the bit string consists of
            1000 bits with the least significant bit indicating whether
            application category with SNMP index 1 applies and the most
            significant bit indicating whether application category with SNMP
            index 1000 applies.

            For further details on these formats, refer to the comment on the
            ConditionSpec type."
        ::= { atRtgRuleEntry 43 }


    atRtgRuleServiceClassCondition OBJECT-TYPE
        SYNTAX  ConditionSpec
        ACCESS  read-write
        STATUS  mandatory
        DESCRIPTION
            "Condition pertaining to the service class associated with the
            application terminating the SM. For the specification for this
            condition, the following formats apply:

            1) NONE
            2) BITSTRING

            When the format is BITSTRING, the relating bit string specifies
            which service classes apply. Each bit in the bit string relates
            to a specific service class. If the bit is 1, the service class
            applies.
            Otherwise, if the bit is 0, the service class does not apply. Up
            to 1000 service classes can be defined. As such, the bit string
            consists of 1000 bits with the least significant bit indicating
            whether service class with SNMP index 1 applies and the most
            significant bit indicating whether service class with SNMP index
            1000 applies.

            For further details on these formats, refer to the comment on the
            ConditionSpec type."
        ::= { atRtgRuleEntry 44 }


    atRtgRuleProtocolCondition OBJECT-TYPE
        SYNTAX  ConditionSpec
        ACCESS  read-write
        STATUS  mandatory
        DESCRIPTION
            "Condition pertaining to the protocol used to deliver the SM to
            the terminating application. For the specification for this
            condition, the following formats apply:

            1) NONE
            2) BITSTRING

            When the format is BITSTRING, the relating bit string specifies
            which protocols apply. Each bit in the bit string relates to a
            specific protocol. If the bit is 1, the protocol applies.
            Otherwise, if the bit is 0, the protocol does not apply. Three
            protocols are used to deliver an SM. These protocols are UCP,
            SMPP and CIMD. As such, the bit string consists of 3 bits with
            - bit 0 indicating whether the UCP protocol applies,
            - bit 1 indicating whether the SMPP protocol applies, and
            - bit 2 indicating whether the CIMD protocol applies.
            Note that bit 0 is the least significant bit and bit 2 the most
            significant bit.

            For further details on these formats, refer to the comment on the
            ConditionSpec type."
        ::= { atRtgRuleEntry 45 }


    atRtgRuleOperationCondition OBJECT-TYPE
        SYNTAX  ConditionSpec
        ACCESS  read-write
        STATUS  mandatory
        DESCRIPTION
            "Condition pertaining to the operation used to deliver the SM. For
            the specification for this condition, the following formats apply:

            1) NONE
            2) BITSTRING

            When the format is BITSTRING, the relating bit string specifies
            which operations apply. Not all bits of the bit string are used.
            Each bit in the bit string that is used relates to a specific
            operation. If the bit is 1, the operation applies. Otherwise, if
            the bit is 0, the operation does not apply. The bit string
            consists of 32 bits and has the following mapping:

              ---------------------------------------------------------------
              bit  operation
              ---------------------------------------------------------------
               0   UCP Call input operation -01
               5   UCP Deliver Short Message operation -52
               6   UCP Deliver Notification operation -53
               9   UCP operation other than the ones above
               11  SMPP DeliverSm
               13  SMPP DataSm
               19  SMPP operation other than the ones above
               21  CIMD DeliverMessage
               22  CIMD DeliverStatusReport
               29  CIMD operation other than the ones above
               30  operation from another protocol than UCP, SMPP and CIMD
              --------------------------------------------------------------

            Note that bit 0 is the least significant bit and bit 2 the most
            significant bit.

            For further details on these formats, refer to the comment on the
            ConditionSpec type."
        ::= { atRtgRuleEntry 46 }


    atRtgRuleOriginatorCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST

            For details on these formats, refer to the comment on the
            ConditionSpec type."
        ::= { atRtgRuleEntry 47 }


    atRtgRuleOriginatorTonCondition OBJECT-TYPE
        SYNTAX  ConditionSpec
        ACCESS  read-write
        STATUS  mandatory
        DESCRIPTION
            "Condition pertaining to the type of number (TON) specified for
            the originator of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { atRtgRuleEntry 48 }


    atRtgRuleOriginatorNpiCondition OBJECT-TYPE
        SYNTAX  ConditionSpec
        ACCESS  read-write
        STATUS  mandatory
        DESCRIPTION
            "Condition pertaining to the numbering plan identification (NPI)
            specified for the originator of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { atRtgRuleEntry 49 }


    atRtgRuleOriginatorImsiCondition OBJECT-TYPE
        SYNTAX  ConditionSpec
        ACCESS  read-write
        STATUS  mandatory
        DESCRIPTION
            "Condition pertaining to the IMSI specified for the originator of
            the SM. For the specification for this condition, the following
            formats apply:

            1) NONE
            2) SINGLEIMSI
            3) IMSIRANGE
            4) COUNTRY
            5) NETWORK
            6) LIST

            For further details on these formats, refer to the comment on the
            ConditionSpec type."
        ::= { atRtgRuleEntry 50 }


    atRtgRuleRecipientCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST
            12) ALPHANUMADDRESS

            For details on these formats, refer to the comment on the
            ConditionSpec type."
        ::= { atRtgRuleEntry 51 }


    atRtgRuleRecipientTonCondition OBJECT-TYPE
        SYNTAX  ConditionSpec
        ACCESS  read-write
        STATUS  mandatory
        DESCRIPTION
            "Condition pertaining to the type of number (TON) specified for
            the recipient of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { atRtgRuleEntry 52 }


    atRtgRuleRecipientNpiCondition OBJECT-TYPE
        SYNTAX  ConditionSpec
        ACCESS  read-write
        STATUS  mandatory
        DESCRIPTION
            "Condition pertaining to the numbering plan identification (NPI)
            specified for the recipient of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { atRtgRuleEntry 53 }

    atRtgRuleMscOrSgsnCondition OBJECT-TYPE
        SYNTAX  ConditionSpec
        ACCESS  read-write
        STATUS  mandatory
        DESCRIPTION
            "Condition pertaining to the MSC or SGSN serving the originator
            that is specified in the SM. For the specification for this
            condition, the following formats apply:

            1) NONE
            2) SINGLEMSISDN
            3) MSISDNRANGE
            4) MSISDNPREFIX
            5) COUNTRY
            6) NETWORK
            7) LIST

            For details on these formats, refer to the comment on the
            ConditionSpec type."
        ::= { atRtgRuleEntry 54 }


    atRtgRuleSmscCondition OBJECT-TYPE
        SYNTAX  ConditionSpec
        ACCESS  read-write
        STATUS  mandatory
        DESCRIPTION
            "Condition pertaining to the SMSC that is specified in the SM. For
            the specification for this condition, the following formats apply:

            1) NONE
            2) SINGLEMSISDN
            3) MSISDNRANGE
            4) MSISDNPREFIX
            5) COUNTRY
            6) NETWORK
            7) LIST

            For details on these formats, refer to the comment on the
            ConditionSpec type."
        ::= { atRtgRuleEntry 55 }


    atRtgRuleUserDataCondition OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT
            5) TEXTLENGTH

            For details on these formats, refer to the comment on the
            ConditionSpec type."
        ::= { atRtgRuleEntry 56 }


    atRtgRuleUserDataHeaderIndicationCondition OBJECT-TYPE
        SYNTAX  ConditionSpec
        ACCESS  read-write
        STATUS  mandatory
        DESCRIPTION
            "Condition pertaining to the user data header indication specified
            in the SM. For the specification for this condition, the following
            formats apply:

            1) NONE
            2) BITVALUE

            For details on these formats, refer to the comment on the
            ConditionSpec type."
        ::= { atRtgRuleEntry 57 }


    atRtgRuleUserDataHeaderCondition OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to GSM 03.40. The
            values for most common information element identifiers are:

            00 hex - Concatenated short message
            01 hex - Special SMS Message Indication
            04 hex - application port addressing scheme, 8 bit address
            05 hex - application port addressing scheme, 16 bit address
            06 hex - SMSC Control Parameters
            07 hex - UDH Source Indicator "
        ::= { atRtgRuleEntry 58 }


    atRtgRuleMoreMessagesToSendCondition OBJECT-TYPE
        SYNTAX  ConditionSpec
        ACCESS  read-write
        STATUS  mandatory
        DESCRIPTION
            "Condition pertaining to the more message to send indicator
            specified in the SM. For the specification for this condition, the
            following formats apply:

            1) NONE
            2) BITVALUE

            For details on these formats, refer to the comment on the
            ConditionSpec type."
        ::= { atRtgRuleEntry 59 }


    atRtgRulePriorityCondition OBJECT-TYPE
        SYNTAX  ConditionSpec
        ACCESS  read-write
        STATUS  mandatory
        DESCRIPTION
            "Condition pertaining to the priority level that is specified in
            the SM. For the specification for this condition, the following
            formats apply:

            1) NONE
            2) BITSTRING

            When the format is BITSTRING, the relating bit string specifies
            which priority levels apply. Not all bits of the bit string are
            used. Each bit in the bit string that is used relates to a
            specific priority level. If the bit is 1, the priority level
            applies.
            Otherwise, if the bit is 0, the priority level does not apply. The
            bit string consists of 32 bits and has the following mapping:

              ---------------------------------------------------------------
              bit  operation
              ---------------------------------------------------------------
               10  SMPP no priority requested
               11  SMPP priority requested
              --------------------------------------------------------------

            Note that bit 0 is the least significant bit and bit 2 the most
            significant bit.

            For further details on these formats, refer to the comment on the
            ConditionSpec type."
        ::= { atRtgRuleEntry 60 }


    atRtgRuleProtocolIdCondition OBJECT-TYPE
        SYNTAX  ConditionSpec
        ACCESS  read-write
        STATUS  mandatory
        DESCRIPTION
            "Condition pertaining to the protocol ID specified in the SM. For
            the specification for this condition, the following formats apply:

            1) NONE
            2) BYTEVALUE

            For details on these formats, refer to the comment on the
            ConditionSpec type.

            For details on the values supported for the protocol ID, refer to
            GSM 03.40."
        ::= { atRtgRuleEntry 61 }


    atRtgRuleDataCodingSchemeCondition OBJECT-TYPE
        SYNTAX  ConditionSpec
        ACCESS  read-write
        STATUS  mandatory
        DESCRIPTION
            "Condition pertaining to the data coding scheme specified in the
            SM. For the specification for this condition, the following
            formats apply:

            1) NONE
            2) BYTEVALUE

            For details on these formats, refer to the comment on the
            ConditionSpec type.

            For details on the values supported for the data coding scheme,
            refer to GSM 03.38."
        ::= { atRtgRuleEntry 62 }


    atRtgRuleConcatenatedMessageSegmentsCondition OBJECT-TYPE
        SYNTAX  ConditionSpec
        ACCESS  read-write
        STATUS  mandatory
        DESCRIPTION
            "Condition pertaining to the segment sequence number of a
            concatenated SM. For the specification for this condition, the
            following formats apply:

            1) NONE
            2) BITSTRING

            When the format is BITSTRING, the relating bit string specifies
            which concatenated message segments apply. Each bit in the bit
            string relates to a specific segment of a concatenated message. If
            the bit is 1, the segment applies. Otherwise, if the bit is 0, the
            segment does not apply. The segments are distinguished in three
            groups. As such, the bit string consists of 3 bits with
            - bit 0 indicating whether the segment is the first of the
              concatenated message,
            - bit 1 indicating whether the segment is the last of the
              concatenated message,
            - bit 2 indicating whether the segment is not the first nor the
              last of the concatenated message,
            Note that bit 0 is the least significant bit and bit 2 the most
            significant bit.

            For further details on these formats, refer to the comment on the
            ConditionSpec type."
        ::= { atRtgRuleEntry 63 }


    atRtgRuleScTimestampCondition OBJECT-TYPE
        SYNTAX  ConditionSpec
        ACCESS  read-write
        STATUS  mandatory
        DESCRIPTION
            "Condition pertaining to the SC timestamp that is specified in
            the SM. For the specification for this condition, the following
            formats apply:

            1) NONE
            2) RELATIVETIME

            For details on these formats, refer to the comment on the
            ConditionSpec type."
        ::= { atRtgRuleEntry 64 }


    atRtgRuleDeliveryStatusCondition OBJECT-TYPE
        SYNTAX  ConditionSpec
        ACCESS  read-write
        STATUS  mandatory
        DESCRIPTION
            "Condition pertaining to the delivery status that is specified in
            the notification. For the specification for this condition, the
            following formats apply:

            1) NONE
            2) BITSTRING

            When the format is BITSTRING, the relating bit string specifies
            which delivery statuses apply. Each bit in the bit string relates
            to a specific delivery status. If the bit is 1, the delivery
            status applies. Otherwise, if the bit is 0, the delivery status
            does not apply. The bit string consists of 32 bits and has the
            following mapping:

              ---------------------------------------------------------------
              bit  address PID
              ---------------------------------------------------------------
               0   UCP: in progress
               1   UCP: delivery failed
               2   UCP: delivery successful
              10   SMPP: no status available
              11   SMPP: in progress
              12   SMPP: validity period expired
              13   SMPP: delivery failed
              14   SMPP: delivery successful
              15   SMPP: deleted
              16   SMPP: deleted by cancel
              17   SMPP: scheduled
              18   SMPP: accepted
              19   SMPP: rejected
              20   CIMD: no status available
              21   CIMD: in progress
              22   CIMD: validity period expired
              23   CIMD: delivery failed
              24   CIMD: delivery successful
              25   CIMD: no response
              26   CIMD: last no response
              27   CIMD: cancelled
              28   CIMD: deleted
              29   CIMD: deleted by cancel
              --------------------------------------------------------------

            Note that bit 0 is the least significant bit and bit 2 the most
            significant bit.

            For further details on these formats, refer to the comment on the
            ConditionSpec type."
        ::= { atRtgRuleEntry 65 }

    atRtgRuleDeliveryTimestampCondition OBJECT-TYPE
        SYNTAX  ConditionSpec
        ACCESS  read-write
        STATUS  mandatory
        DESCRIPTION
            "Condition pertaining to the delivery timestamp that is specified
            in the notification. For the specification for this condition,
            the following formats apply:

            1) NONE
            2) RELATIVETIME

            For details on these formats, refer to the comment on the
            ConditionSpec type."
        ::= { atRtgRuleEntry 66 }

    atRtgRuleExternalAttributesCondition  OBJECT-TYPE
        SYNTAX  ConditionSpec
        ACCESS  read-write
        STATUS  mandatory
        DESCRIPTION
            "Condition on the 32 boolean atributes that can be set by an 
            external approval application. For the specification for this 
            condition, the following formats apply:

            1) NONE
            2) EXTERNALATTRIBUTES

            When the format is EXTERNALATTRIBUTES, the relating bit mask
            string specifies which external attributes apply and the relating
            bit value string specifies the values for the external
            attributes.          
            Each bit in the bit strings relates to a specific attribute. The
            bit strings consist of 32 bits. The least significant bit
            corresponds to attribute 0. The most significant bit corresponds
            to attribute 31. 
            A bit with value 1 in the bit mask string indicates that the
            relating attribute applies and needs to be checked. A bit with
            value 0 in the bit mask string indicates that the relating
            attribute does not apply and does not need to be checked. 
            A bit with value 1 in the bit value string indicates that the
            relating attribute should be TRUE. A bit with value 0 in the bit
            value string indicates that the relating attribute should be
            FALSE. 

            For further details on these formats, refer to the comment on the
            ConditionSpec type."
        ::= { atRtgRuleEntry 67 }

    atRtgRuleXsMessageTypeCondition OBJECT-TYPE
        SYNTAX  ConditionSpec
        ACCESS  read-write
        STATUS  mandatory
        DESCRIPTION
            "Condition pertaining to the external service (XS) message type
            applicable for this SM.
            For the specification for this condition, the following formats
            apply:

            1) NONE
            2) BITSTRING

            When the format is BITSTRING, the relating bit string specifies
            which values for the XS message type apply. Each bit in the bit
            string relates to a XS message type. If the bit is 1, the relating
            XS message type applies. Otherwise, if the bit is 0, the relating
            XS message type does not apply.
            The valid message types are:
                noXsMessage(0),
                forwardedMessage (1),
                copiedMessage (2)

            The bit string consists of 3 bits, with the least significant bit
            indicating whether XS message type 0 (noXsMessage) applies and the
            most significant bit indicating whether XS message type 2
            (copiedMessage) applies.

            For further details on these formats, refer to the comment on the
            ConditionSpec type."
        ::= { atRtgRuleEntry 68 }

    atRtgRuleBilProfileForSubmission OBJECT-TYPE
        SYNTAX  BilProfile
        ACCESS  read-write
        STATUS  mandatory
        DESCRIPTION
            "Identifier specifying which billing profile should be used for
            submission records. Default is 0 (i.e none). Currently, the
            generation of CDRs for incoming AT messages is not supported."
        ::= { atRtgRuleEntry 101 }

    atRtgRuleBilProfileForSuccessfulDelivery OBJECT-TYPE
        SYNTAX  BilProfile
        ACCESS  read-write
        STATUS  mandatory
        DESCRIPTION
            "Identifier specifying which billing profile should be used for
            delivery records in case the AT/SM is successfully delivered.
            Default is 0 (i.e. 'none'). This attribute is only applicable
            for the 'pass' action. Currently, the generation of CDRs for
            incoming AT messages is not supported."
        ::= { atRtgRuleEntry 102 }

    atRtgRuleBilProfileForFailedDelivery OBJECT-TYPE
        SYNTAX  BilProfile
        ACCESS  read-write
        STATUS  mandatory
        DESCRIPTION
            "Identifier specifying which billing profile should be used for
            delivery records in case delivering the AT/SM resulted in a
            failure. Default is 0 (i.e. 'none'). This attribute is only
            applicable for the 'pass' action. Currently, the generation of
            CDRs for incoming AT messages is not supported."
        ::= { atRtgRuleEntry 103 }

    atRtgRuleBilProfileForBlockedDelivery OBJECT-TYPE
        SYNTAX  BilProfile
        ACCESS  read-write
        STATUS  mandatory
        DESCRIPTION
            "Identifier specifying which billing profile should be used for
            delivery records in case the AT/SM is blocked by the rule.
            Default is 0 (i.e. 'none'). This attribute is only applicable
            for the actions that can block the AT/SM. Currently, the
            generation of CDRs for incoming AT messages is not supported."
        ::= { atRtgRuleEntry 104 }

    atRtgRuleBilProfileForDeliveryNotification OBJECT-TYPE
        SYNTAX  BilProfile
        ACCESS  read-write
        STATUS  mandatory
        DESCRIPTION
            "Identifier specifying which billing profile should be used for
            delivery notification. Default is 0 (i.e. 'none').Currently, the
            generation of CDRs for incoming AT notifications is not
            supported."
        ::= { atRtgRuleEntry 105 }

    aoRtgRuleApplication OBJECT-TYPE
        SYNTAX  ApplicationTableIndex
        ACCESS  read-write
        STATUS  mandatory
        DESCRIPTION
            "Reference to an application. When 0 is specified, the rule routes 
            to the application belonging to the short number that is specified 
            in an AO/SM as recipient.

            Only applicable when action of AO routing rule is
            routeToApplication, routeToApplicationFallbackToStorage,
            storeForDeliveryToApplication. By default the value is 0."
        ::= { aoRtgRuleEntry 112 }

    atRtgRuleLogProfile OBJECT-TYPE
        SYNTAX  LogProfile
        ACCESS  read-write
        STATUS  mandatory
        DESCRIPTION
            "Identifier specifying which logging profile should be used.
            Default is 0 (i.e. 'none')."
        ::= { atRtgRuleEntry 111 }

    atCntRuleTable OBJECT-TYPE
        SYNTAX  SEQUENCE OF AtCntRuleEntry
        ACCESS  not-accessible
        STATUS  mandatory
        DESCRIPTION
            "A table containing properties, conditions and counters for each
            AT counting rule.

            An AT counting rule matches when both of the following conditions
            are met:
            1) its administrative state is active;
            2) all its conditions do satisfy."
        ::= { sms 87 }

    atCntRuleEntry OBJECT-TYPE
        SYNTAX  AtCntRuleEntry
        ACCESS  not-accessible
        STATUS  mandatory
        DESCRIPTION
            "Table entry specifying a single AT counting rule."
        INDEX   { atCntRuleIndex }
        ::= { atCntRuleTable 1 }

    AtCntRuleEntry ::=
        SEQUENCE {
            atCntRuleIndex                        AtCntRuleTableIndex,
            atCntRuleAdminState                   AdminState,
            atCntRuleName                         NameString,
            atCntRuleLogProfile                   LogProfile,
            atCntRuleTotalCounter                 Counter,
            atCntRuleSuccessfulDeliverOperationCounter Counter,
            atCntRuleFailedDeliverOperationCounter Counter,
            atCntRuleSuccessfulNotificationOperationCounter Counter,
            atCntRuleFailedNotificationOperationCounter Counter,
            atCntRuleSuccessfulUnknownOperationCounter Counter,
            atCntRuleFailedUnknownOperationCounter Counter,
            atCntRuleApplicationCondition         ConditionSpec,
            atCntRuleApplicationGroupCondition    ConditionSpec,
            atCntRuleApplicationCategoryCondition ConditionSpec,
            atCntRuleServiceClassCondition        ConditionSpec,
            atCntRuleProtocolCondition            ConditionSpec,
            atCntRuleOperationCondition           ConditionSpec,
            atCntRuleOriginatorCondition          ConditionSpec,
            atCntRuleOriginatorTonCondition       ConditionSpec,
            atCntRuleOriginatorNpiCondition       ConditionSpec,
            atCntRuleOriginatorImsiCondition      ConditionSpec,
            atCntRuleRecipientCondition           ConditionSpec,
            atCntRuleRecipientTonCondition        ConditionSpec,
            atCntRuleRecipientNpiCondition        ConditionSpec,
            atCntRuleMscOrSgsnCondition           ConditionSpec,
            atCntRuleSmscCondition                ConditionSpec,
            atCntRuleUserDataCondition            ConditionSpec,
            atCntRuleUserDataHeaderIndicationCondition ConditionSpec,
            atCntRuleUserDataHeaderCondition      ConditionSpec,
            atCntRuleMoreMessagesToSendCondition  ConditionSpec,
            atCntRulePriorityCondition            ConditionSpec,
            atCntRuleProtocolIdCondition          ConditionSpec,
            atCntRuleDataCodingSchemeCondition    ConditionSpec,
            atCntRuleConcatenatedMessageSegmentsCondition ConditionSpec,
            atCntRuleScTimestampCondition         ConditionSpec,
            atCntRuleDeliveryStatusCondition      ConditionSpec,
            atCntRuleDeliveryTimestampCondition   ConditionSpec,
            atCntRuleExternalAttributesCondition  ConditionSpec,
            atCntRuleXsMessageTypeCondition       ConditionSpec
        }

    atCntRuleIndex OBJECT-TYPE
        SYNTAX  AtCntRuleTableIndex
        ACCESS  read-write
        STATUS  mandatory
        DESCRIPTION
            "Index of entry in AT counting rule table."
        ::= { atCntRuleEntry 1 }

    atCntRuleAdminState OBJECT-TYPE
        SYNTAX  AdminState
        ACCESS  read-write
        STATUS  mandatory
        DESCRIPTION
            "Administrative state of the AT counting rule.

            Transition from 'inactive' to 'active' is only possible when:
            1) name has been supplied;
            2) name is not already in use by another rule;
            3) conditions of rule specifying a network refer to an 'active'
               country and an 'active' network;
            4) conditions of rule specifying a country refer to an 'active'
               country;
            5) conditions of rule specifying an application refer to an
               'active' application;
            6) in case applicationGroupCondition specified, all referred
               groups should exists;
            7) in case applicationCategoryCondition specified, all referred
               categories should exists;
            8) in case serviceClassCondition specified, all referred service
               classes should exists;

            For details, refer to the comment on the AdminState type."
        ::= { atCntRuleEntry 2 }

    atCntRuleName OBJECT-TYPE
        SYNTAX  NameString
        ACCESS  read-write
        STATUS  mandatory
        DESCRIPTION
            "Name of the AT counting rule."
        ::= { atCntRuleEntry 3 }

    atCntRuleLogProfile OBJECT-TYPE
        SYNTAX  LogProfile
        ACCESS  read-write
        STATUS  mandatory
        DESCRIPTION
            "Identifier specifying which logging profile should be used.
            Default is 0 (i.e. 'none')."
        ::= { atCntRuleEntry 4 }

    atCntRuleTotalCounter OBJECT-TYPE
        SYNTAX  Counter
        ACCESS  read-write
        STATUS  mandatory
        DESCRIPTION
            "Counter specifying the number of times that an operation was
            terminated in an application."
        ::= { atCntRuleEntry 11 }

    atCntRuleSuccessfulDeliverOperationCounter OBJECT-TYPE
        SYNTAX  Counter
        ACCESS  read-write
        STATUS  mandatory
        DESCRIPTION
            "Counter specifying the number of times that routing a deliver
            operation terminated in an application succeeded."
        ::= { atCntRuleEntry 12 }

    atCntRuleFailedDeliverOperationCounter OBJECT-TYPE
        SYNTAX  Counter
        ACCESS  read-write
        STATUS  mandatory
        DESCRIPTION
            "Counter specifying the number of times that routing a deliver
            operation terminated in an application failed."
        ::= { atCntRuleEntry 13 }

    atCntRuleSuccessfulNotificationOperationCounter OBJECT-TYPE
        SYNTAX  Counter
        ACCESS  read-write
        STATUS  mandatory
        DESCRIPTION
            "Counter specifying the number of times that routing a
            notification operation terminated in an application succeeded."
        ::= { atCntRuleEntry 14 }

    atCntRuleFailedNotificationOperationCounter OBJECT-TYPE
        SYNTAX  Counter
        ACCESS  read-write
        STATUS  mandatory
        DESCRIPTION
            "Counter specifying the number of times that routing a
            notification operation terminated in an application failed."
        ::= { atCntRuleEntry 15 }

    atCntRuleSuccessfulUnknownOperationCounter OBJECT-TYPE
        SYNTAX  Counter
        ACCESS  read-write
        STATUS  mandatory
        DESCRIPTION
            "Counter specifying the number of times that routing an unknown
            operation terminated in an application succeeded."
        ::= { atCntRuleEntry 16 }

    atCntRuleFailedUnknownOperationCounter OBJECT-TYPE
        SYNTAX  Counter
        ACCESS  read-write
        STATUS  mandatory
        DESCRIPTION
            "Counter specifying the number of times that routing an unknown
            operation terminated in an application failed."
        ::= { atCntRuleEntry 17 }

    atCntRuleApplicationCondition OBJECT-TYPE
        SYNTAX  ConditionSpec
        ACCESS  read-write
        STATUS  mandatory
        DESCRIPTION
            "Condition pertaining to the application terminating the SM. For
            the specification for this condition, the following formats
            apply:

            1) NONE
            2) APPLICATION

            For details on these formats, refer to the comment on the
            ConditionSpec type."
        ::= { atCntRuleEntry 41 }

    atCntRuleApplicationGroupCondition OBJECT-TYPE
        SYNTAX  ConditionSpec
        ACCESS  read-write
        STATUS  mandatory
        DESCRIPTION
            "Condition pertaining to the application group associated with
            the application terminating the SM. For the specification for
            this condition, the following formats apply:

            1) NONE
            2) BITSTRING

            When the format is BITSTRING, the relating bit string specifies
            which application groups apply. Each bit in the bit string
            relates to a specific application group. If the bit is 1, the
            application group applies. Otherwise, if the bit is 0, the
            application group does not apply. Up to 1000 application
            groups can be defined. As such, the bit string consists of 1000
            bits with the least significant bit indicating whether application
            group with SNMP index 1 applies and the most significant bit
            indicating whether application group with SNMP index 1000 applies.

            For further details on these formats, refer to the comment on the
            ConditionSpec type."
        ::= { atCntRuleEntry 42 }


    atCntRuleApplicationCategoryCondition OBJECT-TYPE
        SYNTAX  ConditionSpec
        ACCESS  read-write
        STATUS  mandatory
        DESCRIPTION
            "Condition pertaining to the application categories associated
            with the application terminating the SM. For the specification
            for this condition, the following formats apply:

            1) NONE
            2) BITSTRING

            When the format is BITSTRING, the relating bit string specifies
            which application categories apply. Each bit in the bit string
            relates to a specific application category. If the bit is 1, the
            application category applies. Otherwise, if the bit is 0, the
            application category does not apply. Up to 1000 application
            categories can be defined. As such, the bit string consists of
            1000 bits with the least significant bit indicating whether
            application category with SNMP index 1 applies and the most
            significant bit indicating whether application category with SNMP
            index 1000 applies.

            For further details on these formats, refer to the comment on the
            ConditionSpec type."
        ::= { atCntRuleEntry 43 }


    atCntRuleServiceClassCondition OBJECT-TYPE
        SYNTAX  ConditionSpec
        ACCESS  read-write
        STATUS  mandatory
        DESCRIPTION
            "Condition pertaining to the service class associated with the
            application terminating the SM. For the specification for this
            condition, the following formats apply:

            1) NONE
            2) BITSTRING

            When the format is BITSTRING, the relating bit string specifies
            which service classes apply. Each bit in the bit string relates
            to a specific service class. If the bit is 1, the service class
            applies.
            Otherwise, if the bit is 0, the service class does not apply. Up
            to 1000 service classes can be defined. As such, the bit string
            consists of 1000 bits with the least significant bit indicating
            whether service class with SNMP index 1 applies and the most
            significant bit indicating whether service class with SNMP index
            1000 applies.

            For further details on these formats, refer to the comment on the
            ConditionSpec type."
        ::= { atCntRuleEntry 44 }


    atCntRuleProtocolCondition OBJECT-TYPE
        SYNTAX  ConditionSpec
        ACCESS  read-write
        STATUS  mandatory
        DESCRIPTION
            "Condition pertaining to the protocol used to deliver the SM to
            the terminating application. For the specification for this
            condition, the following formats apply:

            1) NONE
            2) BITSTRING

            When the format is BITSTRING, the relating bit string specifies
            which protocols apply. Each bit in the bit string relates to a
            specific protocol. If the bit is 1, the protocol applies.
            Otherwise, if the bit is 0, the protocol does not apply. Three
            protocols are used to deliver an SM. These protocols are UCP,
            SMPP and CIMD. As such, the bit string consists of 3 bits with
            - bit 0 indicating whether the UCP protocol applies,
            - bit 1 indicating whether the SMPP protocol applies, and
            - bit 2 indicating whether the CIMD protocol applies.
            Note that bit 0 is the least significant bit and bit 2 the most
            significant bit.

            For further details on these formats, refer to the comment on the
            ConditionSpec type."
        ::= { atCntRuleEntry 45 }


    atCntRuleOperationCondition OBJECT-TYPE
        SYNTAX  ConditionSpec
        ACCESS  read-write
        STATUS  mandatory
        DESCRIPTION
            "Condition pertaining to the operation used to deliver the SM. For
            the specification for this condition, the following formats apply:

            1) NONE
            2) BITSTRING

            When the format is BITSTRING, the relating bit string specifies
            which operations apply. Not all bits of the bit string are used.
            Each bit in the bit string that is used relates to a specific
            operation. If the bit is 1, the operation applies. Otherwise, if
            the bit is 0, the operation does not apply. The bit string
            consists of 32 bits and has the following mapping:

              ---------------------------------------------------------------
              bit  operation
              ---------------------------------------------------------------
               0   UCP Call input operation -01
               5   UCP Deliver Short Message operation -52
               6   UCP Deliver Notification operation -53
               9   UCP operation other than the ones above
               11  SMPP DeliverSm
               13  SMPP DataSm
               19  SMPP operation other than the ones above
               21  CIMD DeliverMessage
               22  CIMD DeliverStatusReport
               29  CIMD operation other than the ones above
               30  operation from another protocol than UCP, SMPP and CIMD
              --------------------------------------------------------------

            Note that bit 0 is the least significant bit and bit 2 the most
            significant bit.

            For further details on these formats, refer to the comment on the
            ConditionSpec type."
        ::= { atCntRuleEntry 46 }


    atCntRuleOriginatorCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST

            For details on these formats, refer to the comment on the
            ConditionSpec type."
        ::= { atCntRuleEntry 47 }


    atCntRuleOriginatorTonCondition OBJECT-TYPE
        SYNTAX  ConditionSpec
        ACCESS  read-write
        STATUS  mandatory
        DESCRIPTION
            "Condition pertaining to the type of number (TON) specified for
            the originator of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { atCntRuleEntry 48 }


    atCntRuleOriginatorNpiCondition OBJECT-TYPE
        SYNTAX  ConditionSpec
        ACCESS  read-write
        STATUS  mandatory
        DESCRIPTION
            "Condition pertaining to the numbering plan identification (NPI)
            specified for the originator of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { atCntRuleEntry 49 }


    atCntRuleOriginatorImsiCondition OBJECT-TYPE
        SYNTAX  ConditionSpec
        ACCESS  read-write
        STATUS  mandatory
        DESCRIPTION
            "Condition pertaining to the IMSI specified for the originator of
            the SM. For the specification for this condition, the following
            formats apply:

            1) NONE
            2) SINGLEIMSI
            3) IMSIRANGE
            4) COUNTRY
            5) NETWORK
            6) LIST

            For further details on these formats, refer to the comment on the
            ConditionSpec type."
        ::= { atCntRuleEntry 50 }


    atCntRuleRecipientCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST
            12) ALPHANUMADDRESS

            For details on these formats, refer to the comment on the
            ConditionSpec type."
        ::= { atCntRuleEntry 51 }


    atCntRuleRecipientTonCondition OBJECT-TYPE
        SYNTAX  ConditionSpec
        ACCESS  read-write
        STATUS  mandatory
        DESCRIPTION
            "Condition pertaining to the type of number (TON) specified for
            the recipient of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { atCntRuleEntry 52 }


    atCntRuleRecipientNpiCondition OBJECT-TYPE
        SYNTAX  ConditionSpec
        ACCESS  read-write
        STATUS  mandatory
        DESCRIPTION
            "Condition pertaining to the numbering plan identification (NPI)
            specified for the recipient of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { atCntRuleEntry 53 }

    atCntRuleMscOrSgsnCondition OBJECT-TYPE
        SYNTAX  ConditionSpec
        ACCESS  read-write
        STATUS  mandatory
        DESCRIPTION
            "Condition pertaining to the MSC or SGSN serving the originator
            that is specified in the SM. For the specification for this
            condition, the following formats apply:

            1) NONE
            2) SINGLEMSISDN
            3) MSISDNRANGE
            4) MSISDNPREFIX
            5) COUNTRY
            6) NETWORK
            7) LIST

            For details on these formats, refer to the comment on the
            ConditionSpec type."
        ::= { atCntRuleEntry 54 }


    atCntRuleSmscCondition OBJECT-TYPE
        SYNTAX  ConditionSpec
        ACCESS  read-write
        STATUS  mandatory
        DESCRIPTION
            "Condition pertaining to the SMSC that is specified in the SM. For
            the specification for this condition, the following formats apply:

            1) NONE
            2) SINGLEMSISDN
            3) MSISDNRANGE
            4) MSISDNPREFIX
            5) COUNTRY
            6) NETWORK
            7) LIST

            For details on these formats, refer to the comment on the
            ConditionSpec type."
        ::= { atCntRuleEntry 55 }


    atCntRuleUserDataCondition OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT
            5) TEXTLENGTH

            For details on these formats, refer to the comment on the
            ConditionSpec type."
        ::= { atCntRuleEntry 56 }


    atCntRuleUserDataHeaderIndicationCondition OBJECT-TYPE
        SYNTAX  ConditionSpec
        ACCESS  read-write
        STATUS  mandatory
        DESCRIPTION
            "Condition pertaining to the user data header indication specified
            in the SM. For the specification for this condition, the following
            formats apply:

            1) NONE
            2) BITVALUE

            For details on these formats, refer to the comment on the
            ConditionSpec type."
        ::= { atCntRuleEntry 57 }


    atCntRuleUserDataHeaderCondition OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to GSM 03.40. The
            values for most common information element identifiers are:

            00 hex - Concatenated short message
            01 hex - Special SMS Message Indication
            04 hex - application port addressing scheme, 8 bit address
            05 hex - application port addressing scheme, 16 bit address
            06 hex - SMSC Control Parameters
            07 hex - UDH Source Indicator "
        ::= { atCntRuleEntry 58 }


    atCntRuleMoreMessagesToSendCondition OBJECT-TYPE
        SYNTAX  ConditionSpec
        ACCESS  read-write
        STATUS  mandatory
        DESCRIPTION
            "Condition pertaining to the more message to send indicator
            specified in the SM. For the specification for this condition, the
            following formats apply:

            1) NONE
            2) BITVALUE

            For details on these formats, refer to the comment on the
            ConditionSpec type."
        ::= { atCntRuleEntry 59 }


    atCntRulePriorityCondition OBJECT-TYPE
        SYNTAX  ConditionSpec
        ACCESS  read-write
        STATUS  mandatory
        DESCRIPTION
            "Condition pertaining to the priority level that is specified in
            the SM. For the specification for this condition, the following
            formats apply:

            1) NONE
            2) BITSTRING

            When the format is BITSTRING, the relating bit string specifies
            which priority levels apply. Not all bits of the bit string are
            used. Each bit in the bit string that is used relates to a
            specific priority level. If the bit is 1, the priority level
            applies.
            Otherwise, if the bit is 0, the priority level does not apply. The
            bit string consists of 32 bits and has the following mapping:

              ---------------------------------------------------------------
              bit  operation
              ---------------------------------------------------------------
               10  SMPP no priority requested
               11  SMPP priority requested
              --------------------------------------------------------------

            Note that bit 0 is the least significant bit and bit 2 the most
            significant bit.

            For further details on these formats, refer to the comment on the
            ConditionSpec type."
        ::= { atCntRuleEntry 60 }


    atCntRuleProtocolIdCondition OBJECT-TYPE
        SYNTAX  ConditionSpec
        ACCESS  read-write
        STATUS  mandatory
        DESCRIPTION
            "Condition pertaining to the protocol ID specified in the SM. For
            the specification for this condition, the following formats apply:

            1) NONE
            2) BYTEVALUE

            For details on these formats, refer to the comment on the
            ConditionSpec type.

            For details on the values supported for the protocol ID, refer to
            GSM 03.40."
        ::= { atCntRuleEntry 61 }


    atCntRuleDataCodingSchemeCondition OBJECT-TYPE
        SYNTAX  ConditionSpec
        ACCESS  read-write
        STATUS  mandatory
        DESCRIPTION
            "Condition pertaining to the data coding scheme specified in the
            SM. For the specification for this condition, the following
            formats apply:

            1) NONE
            2) BYTEVALUE

            For details on these formats, refer to the comment on the
            ConditionSpec type.

            For details on the values supported for the data coding scheme,
            refer to GSM 03.38."
        ::= { atCntRuleEntry 62 }


    atCntRuleConcatenatedMessageSegmentsCondition OBJECT-TYPE
        SYNTAX  ConditionSpec
        ACCESS  read-write
        STATUS  mandatory
        DESCRIPTION
            "Condition pertaining to the segment sequence number of a
            concatenated SM. For the specification for this condition, the
            following formats apply:

            1) NONE
            2) BITSTRING

            When the format is BITSTRING, the relating bit string specifies
            which concatenated message segments apply. Each bit in the bit
            string relates to a specific segment of a concatenated message. If
            the bit is 1, the segment applies. Otherwise, if the bit is 0, the
            segment does not apply. The segments are distinguished in three
            groups. As such, the bit string consists of 3 bits with
            - bit 0 indicating whether the segment is the first of the
              concatenated message,
            - bit 1 indicating whether the segment is the last of the
              concatenated message,
            - bit 2 indicating whether the segment is not the first nor the
              last of the concatenated message,
            Note that bit 0 is the least significant bit and bit 2 the most
            significant bit.

            For further details on these formats, refer to the comment on the
            ConditionSpec type."
        ::= { atCntRuleEntry 63 }


    atCntRuleScTimestampCondition OBJECT-TYPE
        SYNTAX  ConditionSpec
        ACCESS  read-write
        STATUS  mandatory
        DESCRIPTION
            "Condition pertaining to the SC timestamp that is specified in
            the SM. For the specification for this condition, the following
            formats apply:

            1) NONE
            2) RELATIVETIME

            For details on these formats, refer to the comment on the
            ConditionSpec type."
        ::= { atCntRuleEntry 64 }


    atCntRuleDeliveryStatusCondition OBJECT-TYPE
        SYNTAX  ConditionSpec
        ACCESS  read-write
        STATUS  mandatory
        DESCRIPTION
            "Condition pertaining to the delivery status that is specified in
            the notification. For the specification for this condition, the
            following formats apply:

            1) NONE
            2) BITSTRING

            When the format is BITSTRING, the relating bit string specifies
            which delivery statuses apply. Each bit in the bit string relates
            to a specific delivery status. If the bit is 1, the delivery
            status applies. Otherwise, if the bit is 0, the delivery status
            does not apply. The bit string consists of 32 bits and has the
            following mapping:

              ---------------------------------------------------------------
              bit  address PID
              ---------------------------------------------------------------
               0   UCP: in progress
               1   UCP: delivery failed
               2   UCP: delivery successful
              10   SMPP: no status available
              11   SMPP: in progress
              12   SMPP: validity period expired
              13   SMPP: delivery failed
              14   SMPP: delivery successful
              15   SMPP: deleted
              16   SMPP: deleted by cancel
              17   SMPP: scheduled
              18   SMPP: accepted
              19   SMPP: rejected
              20   CIMD: no status available
              21   CIMD: in progress
              22   CIMD: validity period expired
              23   CIMD: delivery failed
              24   CIMD: delivery successful
              25   CIMD: no response
              26   CIMD: last no response
              27   CIMD: cancelled
              28   CIMD: deleted
              29   CIMD: deleted by cancel
              --------------------------------------------------------------

            Note that bit 0 is the least significant bit and bit 2 the most
            significant bit.

            For further details on these formats, refer to the comment on the
            ConditionSpec type."
        ::= { atCntRuleEntry 65 }

    atCntRuleDeliveryTimestampCondition OBJECT-TYPE
        SYNTAX  ConditionSpec
        ACCESS  read-write
        STATUS  mandatory
        DESCRIPTION
            "Condition pertaining to the delivery timestamp that is specified
            in the notification. For the specification for this condition,
            the following formats apply:

            1) NONE
            2) RELATIVETIME

            For details on these formats, refer to the comment on the
            ConditionSpec type."
        ::= { atCntRuleEntry 66 }

    atCntRuleExternalAttributesCondition  OBJECT-TYPE
        SYNTAX  ConditionSpec
        ACCESS  read-write
        STATUS  mandatory
        DESCRIPTION
            "Condition on the 32 boolean atributes that can be set by an 
            external approval application. For the specification for this 
            condition, the following formats apply:

            1) NONE
            2) EXTERNALATTRIBUTES

            When the format is EXTERNALATTRIBUTES, the relating bit mask
            string specifies which external attributes apply and the relating
            bit value string specifies the values for the external
            attributes.          
            Each bit in the bit strings relates to a specific attribute. The
            bit strings consist of 32 bits. The least significant bit
            corresponds to attribute 0. The most significant bit corresponds
            to attribute 31. 
            A bit with value 1 in the bit mask string indicates that the
            relating attribute applies and needs to be checked. A bit with
            value 0 in the bit mask string indicates that the relating
            attribute does not apply and does not need to be checked. 
            A bit with value 1 in the bit value string indicates that the
            relating attribute should be TRUE. A bit with value 0 in the bit
            value string indicates that the relating attribute should be
            FALSE. 

            For further details on these formats, refer to the comment on the
            ConditionSpec type."
        ::= { atCntRuleEntry 67 }

    atCntRuleXsMessageTypeCondition OBJECT-TYPE
        SYNTAX  ConditionSpec
        ACCESS  read-write
        STATUS  mandatory
        DESCRIPTION
            "Condition pertaining to the external service (XS) message type
            applicable for this SM.
            For the specification for this condition, the following formats
            apply:

            1) NONE
            2) BITSTRING

            When the format is BITSTRING, the relating bit string specifies
            which values for the XS message type apply. Each bit in the bit
            string relates to a XS message type. If the bit is 1, the relating
            XS message type applies. Otherwise, if the bit is 0, the relating
            XS message type does not apply.
            The valid message types are:
                noXsMessage(0),
                forwardedMessage (1),
                copiedMessage (2)

            The bit string consists of 3 bits, with the least significant bit
            indicating whether XS message type 0 (noXsMessage) applies and the
            most significant bit indicating whether XS message type 2
            (copiedMessage) applies.

            For further details on these formats, refer to the comment on the
            ConditionSpec type."
        ::= { atCntRuleEntry 68 }

    atExtCondRuleTable OBJECT-TYPE
        SYNTAX  SEQUENCE OF AtExtCondRuleEntry
        ACCESS  not-accessible
        STATUS  mandatory
        DESCRIPTION
            "A table containing properties, conditions, counters and action
            parameters for each AT ExternalCondition rule.

            An AT ExternalCondition rule matches when all of the following
            conditions are met:
            1) its administrative state is active;
            2) all its (internal) conditions do satisfy;

            In case multiple rules match, all matching rules are applied in
            order of priority of the rules.
            For each matching rule, the specified ExternalCondition is
            evaluated by sending a validationRequest to the ExternalCondition
            application, which will return a evaluationResponse.
            When the ExternalCondition evaluates to True, the next rule will
            be processed. When all matching ExternalCondition rules evaluate
            to True, the AT SM will be routed according to the AT routing
            rules.
            When during the processing of an ExternalCondition rule a rule
            evaluates to False, the FailureAction of that rule will be
            exectuted and further processing of the ExternalCondition rules
            is stopped for this SM."
        ::= { sms 88 }

    atExtCondRuleEntry OBJECT-TYPE
        SYNTAX  AtExtCondRuleEntry
        ACCESS  not-accessible
        STATUS  mandatory
        DESCRIPTION
            "Table entry specifying a single AT ExternalCondition."
        INDEX   { atExtCondRuleIndex }
        ::= { atExtCondRuleTable 1 }

    AtExtCondRuleEntry ::=
        SEQUENCE {
            atExtCondRuleIndex                        AtExtCondRuleTableIndex,
            atExtCondRuleAdminState                   AdminState,
            atExtCondRuleName                         NameString,
            atExtCondRulePriority                     EciPriority,
            atExtCondRuleLogProfile                   LogProfile,
            atExtCondRuleTotalAppliedCounter          Counter,
            atExtCondRulePassedDeliverOperationCounter Counter,
            atExtCondRuleBlockedDeliverOperationCounter Counter,
            atExtCondRulePassedNotificationOperationCounter Counter,
            atExtCondRuleBlockedNotificationOperationCounter Counter,
            atExtCondRuleFailureAction                ExtCondAtAction,
            atExtCondRuleExternalCondition            ConditionSpec,
            atExtCondRuleApplicationCondition         ConditionSpec,
            atExtCondRuleApplicationGroupCondition    ConditionSpec,
            atExtCondRuleApplicationCategoryCondition ConditionSpec,
            atExtCondRuleServiceClassCondition        ConditionSpec,
            atExtCondRuleProtocolCondition            ConditionSpec,
            atExtCondRuleOperationCondition           ConditionSpec,
            atExtCondRuleOriginatorCondition          ConditionSpec,
            atExtCondRuleOriginatorTonCondition       ConditionSpec,
            atExtCondRuleOriginatorNpiCondition       ConditionSpec,
            atExtCondRuleOriginatorImsiCondition      ConditionSpec,
            atExtCondRuleRecipientCondition           ConditionSpec,
            atExtCondRuleRecipientTonCondition        ConditionSpec,
            atExtCondRuleRecipientNpiCondition        ConditionSpec,
            atExtCondRuleMscOrSgsnCondition           ConditionSpec,
            atExtCondRuleSmscCondition                ConditionSpec,
            atExtCondRuleUserDataCondition            ConditionSpec,
            atExtCondRuleUserDataHeaderIndicationCondition ConditionSpec,
            atExtCondRuleUserDataHeaderCondition      ConditionSpec,
            atExtCondRuleMoreMessagesToSendCondition  ConditionSpec,
            atExtCondRulePriorityCondition            ConditionSpec,
            atExtCondRuleProtocolIdCondition          ConditionSpec,
            atExtCondRuleDataCodingSchemeCondition    ConditionSpec,
            atExtCondRuleConcatenatedMessageSegmentsCondition ConditionSpec,
            atExtCondRuleScTimestampCondition         ConditionSpec,
            atExtCondRuleDeliveryStatusCondition      ConditionSpec,
            atExtCondRuleDeliveryTimestampCondition   ConditionSpec,
            atExtCondRuleExternalAttributesCondition  ConditionSpec,
            atExtCondRuleXsMessageTypeCondition       ConditionSpec
        }

    atExtCondRuleIndex OBJECT-TYPE
        SYNTAX  AtExtCondRuleTableIndex
        ACCESS  read-write
        STATUS  mandatory
        DESCRIPTION
            "Index of entry in AT ExternalCondition table."
        ::= { atExtCondRuleEntry 1 }

    atExtCondRuleAdminState OBJECT-TYPE
        SYNTAX  AdminState
        ACCESS  read-write
        STATUS  mandatory
        DESCRIPTION
            "Administrative state of the AT ExternalCondition.

            Transition from 'inactive' to 'active' is only possible when:
            1) name has been supplied;
            2) name is not already in use by another rule;
            3) conditions of rule specifying a network refer to an 'active'
               country and an 'active' network;
            4) conditions of rule specifying a country refer to an 'active'
               country;
            5) conditions of rule specifying an application refer to an
               'active' application;
            6) in case applicationGroupCondition specified, all referred
               groups should exists;
            7) in case applicationCategoryCondition specified, all referred
               categories should exists;
            8) in case serviceClassCondition specified, all referred service
               classes should exists;

            For details, refer to the comment on the AdminState type."
        ::= { atExtCondRuleEntry 2 }

    atExtCondRuleName OBJECT-TYPE
        SYNTAX  NameString
        ACCESS  read-write
        STATUS  mandatory
        DESCRIPTION
            "Name of the AT ExternalCondition."
        ::= { atExtCondRuleEntry 3 }

    atExtCondRulePriority OBJECT-TYPE
        SYNTAX  EciPriority
        ACCESS  read-write
        STATUS  mandatory
        DESCRIPTION
            "Priority of the AT ExternalCondition rule.
            For details, refer to the comment on the EciPriority type."
        ::= { atExtCondRuleEntry 4 }

    atExtCondRuleLogProfile OBJECT-TYPE
        SYNTAX  LogProfile
        ACCESS  read-write
        STATUS  mandatory
        DESCRIPTION
            "Identifier specifying which logging profile should be used. 
            Default is 0 (i.e. 'none')."
        ::= { atExtCondRuleEntry 5 }
        
    atExtCondRuleTotalAppliedCounter OBJECT-TYPE
        SYNTAX  Counter
        ACCESS  read-write
        STATUS  mandatory
        DESCRIPTION
            "Counter specifying the number of times that the ExternalCondition
            rule has been applied."
        ::= { atExtCondRuleEntry 11 }

    atExtCondRulePassedDeliverOperationCounter OBJECT-TYPE
        SYNTAX  Counter
        ACCESS  read-write
        STATUS  mandatory
        DESCRIPTION
            "Counter specifying the number of times that the ExternalCondition
            rule has been applied to a deliver operation with result 'pass'."
        ::= { atExtCondRuleEntry 12 }

    atExtCondRuleBlockedDeliverOperationCounter OBJECT-TYPE
        SYNTAX  Counter
        ACCESS  read-write
        STATUS  mandatory
        DESCRIPTION
            "Counter specifying the number of times that the ExternalCondition
            rule has been applied to a deliver operation with result 'block'."
        ::= { atExtCondRuleEntry 13 }

    atExtCondRulePassedNotificationOperationCounter OBJECT-TYPE
        SYNTAX  Counter
        ACCESS  read-write
        STATUS  mandatory
        DESCRIPTION
            "Counter specifying the number of times that the ExternalCondition
            rule has been applied to a notification operation with result
            'pass'."
        ::= { atExtCondRuleEntry 14 }

    atExtCondRuleBlockedNotificationOperationCounter OBJECT-TYPE
        SYNTAX  Counter
        ACCESS  read-write
        STATUS  mandatory
        DESCRIPTION
            "Counter specifying the number of times that the
            ExternalCondition rule has been applied to a notification
            operation with result 'block'."
        ::= { atExtCondRuleEntry 15 }

    atExtCondRuleFailureAction OBJECT-TYPE
        SYNTAX  ExtCondAtAction
        ACCESS  read-write
        STATUS  mandatory
        DESCRIPTION
            "Action to execute when the AT ExternalCondition rule matches,
            but the ExternalCondition evaluates to False.
            For details, refer to the comments on the ExtCondAtAction type."
        ::= { atExtCondRuleEntry 21 }

    atExtCondRuleExternalCondition OBJECT-TYPE
        SYNTAX  ConditionSpec
        ACCESS  read-write
        STATUS  mandatory
        DESCRIPTION
            "Condition refering to an external condition application
            which has to validate this rule.
            The following formats apply:
            1) EXTERNALCONDITION

            For details, refer to the ConditionSpec type."
        ::= { atExtCondRuleEntry 22 }

    atExtCondRuleApplicationCondition OBJECT-TYPE
        SYNTAX  ConditionSpec
        ACCESS  read-write
        STATUS  mandatory
        DESCRIPTION
            "Condition pertaining to the application terminating the SM. For
            the specification for this condition, the following formats
            apply:

            1) NONE
            2) APPLICATION

            For details on these formats, refer to the comment on the
            ConditionSpec type."
        ::= { atExtCondRuleEntry 41 }

    atExtCondRuleApplicationGroupCondition OBJECT-TYPE
        SYNTAX  ConditionSpec
        ACCESS  read-write
        STATUS  mandatory
        DESCRIPTION
            "Condition pertaining to the application group associated with
            the application terminating the SM. For the specification for
            this condition, the following formats apply:

            1) NONE
            2) BITSTRING

            When the format is BITSTRING, the relating bit string specifies
            which application groups apply. Each bit in the bit string
            relates to a specific application group. If the bit is 1, the
            application group applies. Otherwise, if the bit is 0, the
            application group does not apply. Up to 1000 application
            groups can be defined. As such, the bit string consists of 1000
            bits with the least significant bit indicating whether application
            group with SNMP index 1 applies and the most significant bit
            indicating whether application group with SNMP index 1000 applies.

            For further details on these formats, refer to the comment on the
            ConditionSpec type."
        ::= { atExtCondRuleEntry 42 }


    atExtCondRuleApplicationCategoryCondition OBJECT-TYPE
        SYNTAX  ConditionSpec
        ACCESS  read-write
        STATUS  mandatory
        DESCRIPTION
            "Condition pertaining to the application categories associated
            with the application terminating the SM. For the specification
            for this condition, the following formats apply:

            1) NONE
            2) BITSTRING

            When the format is BITSTRING, the relating bit string specifies
            which application categories apply. Each bit in the bit string
            relates to a specific application category. If the bit is 1, the
            application category applies. Otherwise, if the bit is 0, the
            application category does not apply. Up to 1000 application
            categories can be defined. As such, the bit string consists of
            1000 bits with the least significant bit indicating whether
            application category with SNMP index 1 applies and the most
            significant bit indicating whether application category with SNMP
            index 1000 applies.

            For further details on these formats, refer to the comment on the
            ConditionSpec type."
        ::= { atExtCondRuleEntry 43 }


    atExtCondRuleServiceClassCondition OBJECT-TYPE
        SYNTAX  ConditionSpec
        ACCESS  read-write
        STATUS  mandatory
        DESCRIPTION
            "Condition pertaining to the service class associated with the
            application terminating the SM. For the specification for this
            condition, the following formats apply:

            1) NONE
            2) BITSTRING

            When the format is BITSTRING, the relating bit string specifies
            which service classes apply. Each bit in the bit string relates
            to a specific service class. If the bit is 1, the service class
            applies.
            Otherwise, if the bit is 0, the service class does not apply. Up
            to 1000 service classes can be defined. As such, the bit string
            consists of 1000 bits with the least significant bit indicating
            whether service class with SNMP index 1 applies and the most
            significant bit indicating whether service class with SNMP index
            1000 applies.

            For further details on these formats, refer to the comment on the
            ConditionSpec type."
        ::= { atExtCondRuleEntry 44 }


    atExtCondRuleProtocolCondition OBJECT-TYPE
        SYNTAX  ConditionSpec
        ACCESS  read-write
        STATUS  mandatory
        DESCRIPTION
            "Condition pertaining to the protocol used to deliver the SM to
            the terminating application. For the specification for this
            condition, the following formats apply:

            1) NONE
            2) BITSTRING

            When the format is BITSTRING, the relating bit string specifies
            which protocols apply. Each bit in the bit string relates to a
            specific protocol. If the bit is 1, the protocol applies.
            Otherwise, if the bit is 0, the protocol does not apply. Three
            protocols are used to deliver an SM. These protocols are UCP,
            SMPP and CIMD. As such, the bit string consists of 3 bits with
            - bit 0 indicating whether the UCP protocol applies,
            - bit 1 indicating whether the SMPP protocol applies, and
            - bit 2 indicating whether the CIMD protocol applies.
            Note that bit 0 is the least significant bit and bit 2 the most
            significant bit.

            For further details on these formats, refer to the comment on the
            ConditionSpec type."
        ::= { atExtCondRuleEntry 45 }


    atExtCondRuleOperationCondition OBJECT-TYPE
        SYNTAX  ConditionSpec
        ACCESS  read-write
        STATUS  mandatory
        DESCRIPTION
            "Condition pertaining to the operation used to deliver the SM. For
            the specification for this condition, the following formats apply:

            1) NONE
            2) BITSTRING

            When the format is BITSTRING, the relating bit string specifies
            which operations apply. Not all bits of the bit string are used.
            Each bit in the bit string that is used relates to a specific
            operation. If the bit is 1, the operation applies. Otherwise, if
            the bit is 0, the operation does not apply. The bit string
            consists of 32 bits and has the following mapping:

              ---------------------------------------------------------------
              bit  operation
              ---------------------------------------------------------------
               0   UCP Call input operation -01
               5   UCP Deliver Short Message operation -52
               6   UCP Deliver Notification operation -53
               9   UCP operation other than the ones above
               11  SMPP DeliverSm
               13  SMPP DataSm
               19  SMPP operation other than the ones above
               21  CIMD DeliverMessage
               22  CIMD DeliverStatusReport
               29  CIMD operation other than the ones above
               30  operation from another protocol than UCP, SMPP and CIMD
              --------------------------------------------------------------

            Note that bit 0 is the least significant bit and bit 2 the most
            significant bit.

            For further details on these formats, refer to the comment on the
            ConditionSpec type."
        ::= { atExtCondRuleEntry 46 }


    atExtCondRuleOriginatorCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST

            For details on these formats, refer to the comment on the
            ConditionSpec type."
        ::= { atExtCondRuleEntry 47 }


    atExtCondRuleOriginatorTonCondition OBJECT-TYPE
        SYNTAX  ConditionSpec
        ACCESS  read-write
        STATUS  mandatory
        DESCRIPTION
            "Condition pertaining to the type of number (TON) specified for
            the originator of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM 
            03.40."
        ::= { atExtCondRuleEntry 48 }


    atExtCondRuleOriginatorNpiCondition OBJECT-TYPE
        SYNTAX  ConditionSpec
        ACCESS  read-write
        STATUS  mandatory
        DESCRIPTION
            "Condition pertaining to the numbering plan identification (NPI)
            specified for the originator of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { atExtCondRuleEntry 49 }


    atExtCondRuleOriginatorImsiCondition OBJECT-TYPE
        SYNTAX  ConditionSpec
        ACCESS  read-write
        STATUS  mandatory
        DESCRIPTION
            "Condition pertaining to the IMSI specified for the originator of
            the SM. For the specification for this condition, the following
            formats apply:

            1) NONE
            2) SINGLEIMSI
            3) IMSIRANGE
            4) COUNTRY
            5) NETWORK
            6) LIST

            For further details on these formats, refer to the comment on the
            ConditionSpec type."
        ::= { atExtCondRuleEntry 50 }


    atExtCondRuleRecipientCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST
            12) ALPHANUMADDRESS

            For details on these formats, refer to the comment on the
            ConditionSpec type."
        ::= { atExtCondRuleEntry 51 }


    atExtCondRuleRecipientTonCondition OBJECT-TYPE
        SYNTAX  ConditionSpec
        ACCESS  read-write
        STATUS  mandatory
        DESCRIPTION
            "Condition pertaining to the type of number (TON) specified for
            the recipient of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant bit indicating
            whether TON value 0 applies and the most significant bit
            indicating whether TON value 7 applies.

            For further details on these formats, refer to the comment on the
            ConditionSpec type.

            For details on the values supported for the TON, refer to GSM
            03.40."
        ::= { atExtCondRuleEntry 52 }


    atExtCondRuleRecipientNpiCondition OBJECT-TYPE
        SYNTAX  ConditionSpec
        ACCESS  read-write
        STATUS  mandatory
        DESCRIPTION
            "Condition pertaining to the numbering plan identification (NPI)
            specified for the recipient of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant bit indicating
            whether NPI value 0 applies and the most significant bit
            indicating whether NPI value 15 applies.

            For further details on these formats, refer to the comment on the
            ConditionSpec type.

            For details on the values supported for the NPI, refer to GSM
            03.40."
        ::= { atExtCondRuleEntry 53 }

    atExtCondRuleMscOrSgsnCondition OBJECT-TYPE
        SYNTAX  ConditionSpec
        ACCESS  read-write
        STATUS  mandatory
        DESCRIPTION
            "Condition pertaining to the MSC or SGSN serving the originator
            that is specified in the SM. For the specification for this
            condition, the following formats apply:

            1) NONE
            2) SINGLEMSISDN
            3) MSISDNRANGE
            4) MSISDNPREFIX
            5) COUNTRY
            6) NETWORK
            7) LIST

            For details on these formats, refer to the comment on the
            ConditionSpec type."
        ::= { atExtCondRuleEntry 54 }


    atExtCondRuleSmscCondition OBJECT-TYPE
        SYNTAX  ConditionSpec
        ACCESS  read-write
        STATUS  mandatory
        DESCRIPTION
            "Condition pertaining to the SMSC that is specified in the SM. For
            the specification for this condition, the following formats apply:

            1) NONE
            2) SINGLEMSISDN
            3) MSISDNRANGE
            4) MSISDNPREFIX
            5) COUNTRY
            6) NETWORK
            7) LIST

            For details on these formats, refer to the comment on the
            ConditionSpec type."
        ::= { atExtCondRuleEntry 55 }


    atExtCondRuleUserDataCondition OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT
            5) TEXTLENGTH

            For details on these formats, refer to the comment on the
            ConditionSpec type."
        ::= { atExtCondRuleEntry 56 }


    atExtCondRuleUserDataHeaderIndicationCondition OBJECT-TYPE
        SYNTAX  ConditionSpec
        ACCESS  read-write
        STATUS  mandatory
        DESCRIPTION
            "Condition pertaining to the user data header indication specified
            in the SM. For the specification for this condition, the following
            formats apply:

            1) NONE
            2) BITVALUE

            For details on these formats, refer to the comment on the
            ConditionSpec type."
        ::= { atExtCondRuleEntry 57 }


    atExtCondRuleUserDataHeaderCondition OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to GSM 03.40. The
            values for most common information element identifiers are:

            00 hex - Concatenated short message
            01 hex - Special SMS Message Indication
            04 hex - application port addressing scheme, 8 bit address
            05 hex - application port addressing scheme, 16 bit address
            06 hex - SMSC Control Parameters
            07 hex - UDH Source Indicator "
        ::= { atExtCondRuleEntry 58 }


    atExtCondRuleMoreMessagesToSendCondition OBJECT-TYPE
        SYNTAX  ConditionSpec
        ACCESS  read-write
        STATUS  mandatory
        DESCRIPTION
            "Condition pertaining to the more message to send indicator
            specified in the SM. For the specification for this condition, the
            following formats apply:

            1) NONE
            2) BITVALUE

            For details on these formats, refer to the comment on the
            ConditionSpec type."
        ::= { atExtCondRuleEntry 59 }


    atExtCondRulePriorityCondition OBJECT-TYPE
        SYNTAX  ConditionSpec
        ACCESS  read-write
        STATUS  mandatory
        DESCRIPTION
            "Condition pertaining to the priority level that is specified in
            the SM. For the specification for this condition, the following
            formats apply:

            1) NONE
            2) BITSTRING

            When the format is BITSTRING, the relating bit string specifies
            which priority levels apply. Not all bits of the bit string are
            used. Each bit in the bit string that is used relates to a
            specific priority level. If the bit is 1, the priority level
            applies.  Otherwise, if the bit is 0, the priority level does not
            apply. The bit string consists of 32 bits and has the following
            mapping:

              ---------------------------------------------------------------
              bit  operation
              ---------------------------------------------------------------
               10  SMPP no priority requested
               11  SMPP priority requested
              --------------------------------------------------------------

            Note that bit 0 is the least significant bit and bit 2 the most
            significant bit.

            For further details on these formats, refer to the comment on the
            ConditionSpec type."
        ::= { atExtCondRuleEntry 60 }


    atExtCondRuleProtocolIdCondition OBJECT-TYPE
        SYNTAX  ConditionSpec
        ACCESS  read-write
        STATUS  mandatory
        DESCRIPTION
            "Condition pertaining to the protocol ID specified in the SM. For
            the specification for this condition, the following formats apply:

            1) NONE
            2) BYTEVALUE

            For details on these formats, refer to the comment on the
            ConditionSpec type.

            For details on the values supported for the protocol ID, refer to
            GSM 03.40."
        ::= { atExtCondRuleEntry 61 }


    atExtCondRuleDataCodingSchemeCondition OBJECT-TYPE
        SYNTAX  ConditionSpec
        ACCESS  read-write
        STATUS  mandatory
        DESCRIPTION
            "Condition pertaining to the data coding scheme specified in the
            SM. For the specification for this condition, the following
            formats apply:

            1) NONE
            2) BYTEVALUE

            For details on these formats, refer to the comment on the
            ConditionSpec type.

            For details on the values supported for the data coding scheme,
            refer to GSM 03.38."
        ::= { atExtCondRuleEntry 62 }


    atExtCondRuleConcatenatedMessageSegmentsCondition OBJECT-TYPE
        SYNTAX  ConditionSpec
        ACCESS  read-write
        STATUS  mandatory
        DESCRIPTION
            "Condition pertaining to the segment sequence number of a
            concatenated SM. For the specification for this condition, the
            following formats apply:

            1) NONE
            2) BITSTRING

            When the format is BITSTRING, the relating bit string specifies
            which concatenated message segments apply. Each bit in the bit
            string relates to a specific segment of a concatenated message. If
            the bit is 1, the segment applies. Otherwise, if the bit is 0, the
            segment does not apply. The segments are distinguished in three
            groups. As such, the bit string consists of 3 bits with
            - bit 0 indicating whether the segment is the first of the
              concatenated message,
            - bit 1 indicating whether the segment is the last of the
              concatenated message,
            - bit 2 indicating whether the segment is not the first nor the
              last of the concatenated message,
            Note that bit 0 is the least significant bit and bit 2 the most
            significant bit.

            For further details on these formats, refer to the comment on the
            ConditionSpec type."
        ::= { atExtCondRuleEntry 63 }


    atExtCondRuleScTimestampCondition OBJECT-TYPE
        SYNTAX  ConditionSpec
        ACCESS  read-write
        STATUS  mandatory
        DESCRIPTION
            "Condition pertaining to the SC timestamp that is specified in
            the SM. For the specification for this condition, the following
            formats apply:

            1) NONE
            2) RELATIVETIME

            For details on these formats, refer to the comment on the
            ConditionSpec type."
        ::= { atExtCondRuleEntry 64 }


    atExtCondRuleDeliveryStatusCondition OBJECT-TYPE
        SYNTAX  ConditionSpec
        ACCESS  read-write
        STATUS  mandatory
        DESCRIPTION
            "Condition pertaining to the delivery status that is specified in
            the notification. For the specification for this condition, the
            following formats apply:

            1) NONE
            2) BITSTRING

            When the format is BITSTRING, the relating bit string specifies
            which delivery statuses apply. Each bit in the bit string relates
            to a specific delivery status. If the bit is 1, the delivery
            status applies. Otherwise, if the bit is 0, the delivery status
            does not apply. The bit string consists of 32 bits and has the
            following mapping:

              ---------------------------------------------------------------
              bit  address PID
              ---------------------------------------------------------------
               0   UCP: in progress
               1   UCP: delivery failed
               2   UCP: delivery successful
              10   SMPP: no status available
              11   SMPP: in progress
              12   SMPP: validity period expired
              13   SMPP: delivery failed
              14   SMPP: delivery successful
              15   SMPP: deleted
              16   SMPP: deleted by cancel
              17   SMPP: scheduled
              18   SMPP: accepted
              19   SMPP: rejected
              20   CIMD: no status available
              21   CIMD: in progress
              22   CIMD: validity period expired
              23   CIMD: delivery failed
              24   CIMD: delivery successful
              25   CIMD: no response
              26   CIMD: last no response
              27   CIMD: cancelled
              28   CIMD: deleted
              29   CIMD: deleted by cancel
              --------------------------------------------------------------

            Note that bit 0 is the least significant bit and bit 2 the most
            significant bit.

            For further details on these formats, refer to the comment on the
            ConditionSpec type."
        ::= { atExtCondRuleEntry 65 }

    atExtCondRuleDeliveryTimestampCondition OBJECT-TYPE
        SYNTAX  ConditionSpec
        ACCESS  read-write
        STATUS  mandatory
        DESCRIPTION
            "Condition pertaining to the delivery timestamp that is specified
            in the notification. For the specification for this condition,
            the following formats apply:

            1) NONE
            2) RELATIVETIME

            For details on these formats, refer to the comment on the
            ConditionSpec type."
        ::= { atExtCondRuleEntry 66 }

    atExtCondRuleExternalAttributesCondition  OBJECT-TYPE
        SYNTAX  ConditionSpec
        ACCESS  read-write
        STATUS  mandatory
        DESCRIPTION
            "Condition on the 32 boolean atributes that can be set by an 
            external approval application. For the specification for this 
            condition, the following formats apply:

            1) NONE
            2) EXTERNALATTRIBUTES

            When the format is EXTERNALATTRIBUTES, the relating bit mask 
            string specifies which external attributes apply and the relating 
            bit value string specifies the values for the external attributes.          
            Each bit in the bit strings relates to a specific attribute. The 
            bit strings consist of 32 bits. The least significant bit 
            corresponds to attribute 0. The most significant bit corresponds 
            to attribute 31. 
            A bit with value 1 in the bit mask string indicates that the 
            relating attribute applies and needs to be checked. A bit with 
            value 0 in the bit mask string indicates that the relating 
            attribute does not apply and does not need to be checked. 
            A bit with value 1 in the bit value string indicates that the 
            relating attribute should be TRUE. A bit with value 0 in the bit 
            value string  indicates that the relating attribute should be 
            FALSE. 

            For further details on these formats, refer to the comment on the
            ConditionSpec type."
        ::= { atExtCondRuleEntry 67 }

    atExtCondRuleXsMessageTypeCondition OBJECT-TYPE
        SYNTAX  ConditionSpec
        ACCESS  read-write
        STATUS  mandatory
        DESCRIPTION
            "Condition pertaining to the external service (XS) message type
            applicable for this SM.
            For the specification for this condition, the following formats
            apply:

            1) NONE
            2) BITSTRING

            When the format is BITSTRING, the relating bit string specifies
            which values for the XS message type apply. Each bit in the bit
            string relates to a XS message type. If the bit is 1, the relating
            XS message type applies. Otherwise, if the bit is 0, the relating
            XS message type does not apply.
            The valid message types are:
                noXsMessage(0),
                forwardedMessage (1),
                copiedMessage (2)

            The bit string consists of 3 bits, with the least significant bit
            indicating whether XS message type 0 (noXsMessage) applies and the
            most significant bit indicating whether XS message type 2
            (copiedMessage) applies.

            For further details on these formats, refer to the comment on the
            ConditionSpec type."
        ::= { atExtCondRuleEntry 68 }

    -- atModifierTable

    atModifierTable OBJECT-TYPE
        SYNTAX  SEQUENCE OF AtModifierEntry
        ACCESS  not-accessible
        STATUS  mandatory
        DESCRIPTION
            "A list of AT modifier entries."
        ::= { sms 89 }

    atModifierEntry OBJECT-TYPE
        SYNTAX  AtModifierEntry
        ACCESS  not-accessible
        STATUS  mandatory
        DESCRIPTION
            "Table entry specifying a single AT modifier."
        INDEX   { atModifierIndex }
        ::= { atModifierTable 1 }

    AtModifierEntry ::=
        SEQUENCE {
            atModifierIndex                      AtModifierTableIndex,
            atModifierAdminState                 AdminState,
            atModifierName                       NameString,
            atModifierPriority                   DeliveryPriority
        }

    atModifierIndex OBJECT-TYPE
        SYNTAX  AtModifierTableIndex
        ACCESS  not-accessible
        STATUS  mandatory
        DESCRIPTION
            "Index of entry in AT modifier table."
        ::= { atModifierEntry 1 }

    atModifierAdminState OBJECT-TYPE
        SYNTAX  AdminState
        ACCESS  read-write
        STATUS  mandatory
        DESCRIPTION
            "Administrative state of the AT modifier.

            Transition from 'inactive' to 'active' is only possible when:
            1) name supplied and not already in use by another AT modifier;

            Transition from 'active' to 'inactive' is only possible when:
            1) AT modifier is not being referred.

            For details, refer to the comment on the AdminState type."
        ::= { atModifierEntry 2 }

    atModifierName OBJECT-TYPE
        SYNTAX  NameString
        ACCESS  read-write
        STATUS  mandatory
        DESCRIPTION
            "Name of the AT modifier."
        ::= { atModifierEntry 3 }

    atModifierPriority OBJECT-TYPE
        SYNTAX  DeliveryPriority
        ACCESS  read-write
        STATUS  mandatory
        DESCRIPTION
            "Modify the priority flag. If the value is unChanged(-1), this
            means to leave the field unchanged. Values bulk(1),
            low(2)/normal(3)/interactive(4), medium(5)/urgent(6),
            high(7)/emergency(8) and background(0) correspond to the SMPP
            priority levels 0 through 4 respectively. Values normal(3) and
            below correspond to GSM non-priority deliveries.Default value
            is unChanged(-1)."
        ::= { atModifierEntry 12 }

    sriSmFallbackTriggers OBJECT IDENTIFIER ::= { sms 91 }
    
    sriSmFallbackOnTimeout OBJECT-TYPE
        SYNTAX  Boolean
        ACCESS  read-write
        STATUS  mandatory
        DESCRIPTION
            "Identifier specifying that a timeout on the SendRoutingInfoForSm 
            operation for the recipient of an MT/SM triggers re-sending of the 
            SendRoutingInfoForSm operation with another Translation Type (TT) 
            value. Note that the re-sending is only done when enabled by the 
            mobile network entity to which the recipient's MSISDN relates.            
            Default is 'false'."
        ::= { sriSmFallbackTriggers 1 }

    sriSmFallbackOnSysFailError OBJECT-TYPE
        SYNTAX  Boolean
        ACCESS  read-write
        STATUS  mandatory
        DESCRIPTION
            "Identifier specifying that a 'system failure' error on the 
            SendRoutingInfoForSm operation for the recipient of an MT/SM 
            triggers re-sending of the SendRoutingInfoForSm operation with 
            another Translation Type (TT) value. Note that the re-sending is 
            only done when enabled by the mobile network entity to which the 
            recipient's MSISDN relates.            
            Default is 'false'."
       ::= { sriSmFallbackTriggers 2 }

    sriSmFallbackOnDataMisError OBJECT-TYPE
        SYNTAX  Boolean
        ACCESS  read-write
        STATUS  mandatory
        DESCRIPTION
            "Identifier specifying that a 'data missing' error on the 
            SendRoutingInfoForSm operation for the recipient of an MT/SM 
            triggers re-sending of the SendRoutingInfoForSm operation with 
            another Translation Type (TT) value. Note that the re-sending is 
            only done when enabled by the mobile network entity to which the 
            recipient's MSISDN relates.            
            Default is 'false'."
        ::= { sriSmFallbackTriggers 3 }

    sriSmFallbackOnUnexpDataValError OBJECT-TYPE
        SYNTAX  Boolean
        ACCESS  read-write
        STATUS  mandatory
        DESCRIPTION
            "Identifier specifying that a 'unexpected data value' error on
            the SendRoutingInfoForSm operation for the recipient of an MT/SM
            triggers re-sending of the SendRoutingInfoForSm operation with
            another Translation Type (TT) value. Note that the re-sending is
            only done when enabled by the mobile network entity to which the
            recipient's MSISDN relates.            
            Default is 'false'."
        ::= { sriSmFallbackTriggers 4 }

    sriSmFallbackOnFacNotSuppError OBJECT-TYPE
        SYNTAX  Boolean
        ACCESS  read-write
        STATUS  mandatory
        DESCRIPTION
            "Identifier specifying that a 'facility not supported' error on
            the SendRoutingInfoForSm operation for the recipient of an MT/SM
            triggers re-sending of the SendRoutingInfoForSm operation with
            another Translation Type (TT) value. Note that the re-sending is
            only done when enabled by the mobile network entity to which the
            recipient's MSISDN relates.            
            Default is 'false'."
        ::= { sriSmFallbackTriggers 5 }

    sriSmFallbackOnUnkSubError OBJECT-TYPE
        SYNTAX  Boolean
        ACCESS  read-write
        STATUS  mandatory
        DESCRIPTION
            "Identifier specifying that a 'unknown subscriber' error on the 
            SendRoutingInfoForSm operation for the recipient of an MT/SM 
            triggers re-sending of the SendRoutingInfoForSm operation with 
            another Translation Type (TT) value. Note that the re-sending is 
            only done when enabled by the mobile network entity to which the 
            recipient's MSISDN relates.            
            Default is 'true'."

        ::= { sriSmFallbackTriggers 6 }

    sriSmFallbackOnAbsSubError OBJECT-TYPE
        SYNTAX  Boolean
        ACCESS  read-write
        STATUS  mandatory
        DESCRIPTION
            "Identifier specifying that a 'absent subscriber' error on the 
            SendRoutingInfoForSm operation for the recipient of an MT/SM 
            triggers re-sending of the SendRoutingInfoForSm operation with 
            another Translation Type (TT) value. Note that the re-sending is 
            only done when enabled by the mobile network entity to which the 
            recipient's MSISDN relates.            
            Default is 'false'."
        ::= { sriSmFallbackTriggers 7 }

    sriSmFallbackOnCallBarredError OBJECT-TYPE
        SYNTAX  Boolean
        ACCESS  read-write
        STATUS  mandatory
        DESCRIPTION
            "Identifier specifying that a 'call barred' error on the 
            SendRoutingInfoForSm operation for the recipient of an MT/SM 
            triggers re-sending of the SendRoutingInfoForSm operation with 
            another Translation Type (TT) value. Note that the re-sending is 
            only done when enabled by the mobile network entity to which the 
            recipient's MSISDN relates.            
            Default is 'false'."
        ::= { sriSmFallbackTriggers 8 }

    sriSmFallbackOnTeleServNotProvError OBJECT-TYPE
        SYNTAX  Boolean
        ACCESS  read-write
        STATUS  mandatory
        DESCRIPTION
            "Identifier specifying that a 'teleservice not provisioned' error
            on the SendRoutingInfoForSm operation for the recipient of an
            MT/SM triggers re-sending of the SendRoutingInfoForSm operation
            with another Translation Type (TT) value. Note that the
            re-sending is only done when enabled by the mobile network entity
            to which the recipient's MSISDN relates.            
            Default is 'false'."
        ::= { sriSmFallbackTriggers 9 }

    sriSmFallbackOnTcapAborted OBJECT-TYPE
        SYNTAX  Boolean
        ACCESS  read-write
        STATUS  mandatory
        DESCRIPTION
            "Identifier specifying that a TCAP abort on the 
            SendRoutingInfoForSm operation for the recipient of an MT/SM 
            triggers re-sending of the SendRoutingInfoForSm operation with 
            another Translation Type (TT) value. Note that the re-sending is 
            only done when enabled by the mobile network entity to which the 
            recipient's MSISDN relates.            
            Default is 'false'."
        ::= { sriSmFallbackTriggers 10 }

    sriSmFallbackOnSccpAborted OBJECT-TYPE
        SYNTAX  Boolean
        ACCESS  read-write
        STATUS  mandatory
        DESCRIPTION
            "Identifier specifying that a ACCP abort on the 
            SendRoutingInfoForSm operation for the recipient of an MT/SM 
            triggers re-sending of the SendRoutingInfoForSm operation with 
            another Translation Type (TT) value. Note that the re-sending is 
            only done when enabled by the mobile network entity to which the 
            recipient's MSISDN relates.            
            Default is 'true'."
        ::= { sriSmFallbackTriggers 11 }

    -- Routing Numbers

    routingNumberProperties OBJECT IDENTIFIER ::= { sms 96 }
    
    rnPropRecipientMsisdnParsingEnabled OBJECT-TYPE
        SYNTAX  Boolean
        ACCESS  read-write
        STATUS  mandatory
        DESCRIPTION
            "Specifies whether the router should try and match the recipient
            MSISDN digits against the provisioned and available set of routing
            numbers (see routingNumberTable), and strip the digits upon
            matching. By default, this property is set to 'false'."
        ::= { routingNumberProperties 1 }

    rnPropRecipientImsiParsingEnabled OBJECT-TYPE
        SYNTAX  Boolean
        ACCESS  read-write
        STATUS  mandatory
        DESCRIPTION
            "Specifies whether the router should try and match the recipient
            IMSI digits against the provisioned and available set of routing
            numbers (see routingNumberTable), and strip the digits upon
            matching. By default, this property is set to 'false'."
        ::= { routingNumberProperties 2 }

    rnPropDefaultGroupForRecipientMsisdn OBJECT-TYPE
        SYNTAX  RoutingNumberGroupRef
        ACCESS  read-write
        STATUS  mandatory
        DESCRIPTION
            "Specifies the index of the routing number group that
            should be used if a parsed recipient MSISDN cannot be
            associated with any of the provisioned and available routing
            numbers. By default, this object is set to 0, which refers to
            'no' routing group."
        ::= { routingNumberProperties 11 }

    rnPropDefaultGroupForRecipientImsi OBJECT-TYPE
        SYNTAX  RoutingNumberGroupRef
        ACCESS  read-write
        STATUS  mandatory
        DESCRIPTION
            "Specifies the index of the routing number group that
            should be used if a parsed recipient IMSI cannot be
            associated with any of the provisioned and available routing
            numbers. By default, this object is set to 0, which refers to
            'no' routing group."
        ::= { routingNumberProperties 12 }

    routingNumberCounters OBJECT IDENTIFIER ::= { sms 97 }

    rnCntMsisdnDefaultGroupCounter OBJECT-TYPE
        SYNTAX  Counter
        ACCESS  read-write
        STATUS  mandatory
        DESCRIPTION
            "Counts how many times the default routing number group
            was assigned to an MSISDN number."
        ::= { routingNumberCounters 1 }

    rnCntImsiDefaultGroupCounter OBJECT-TYPE
        SYNTAX  Counter
        ACCESS  read-write
        STATUS  mandatory
        DESCRIPTION
            "Counts how many times the default routing number group
            was assigned to an IMSI number."
        ::= { routingNumberCounters 2 }


    routingNumberTable OBJECT-TYPE
        SYNTAX  SEQUENCE OF RoutingNumberEntry
        ACCESS  not-accessible
        STATUS  mandatory
        DESCRIPTION
            "A table to hold all routing numbers known to TextPass."
        ::= { sms 98 }

    routingNumberEntry OBJECT-TYPE
        SYNTAX  RoutingNumberEntry
        ACCESS  not-accessible
        STATUS  mandatory
        DESCRIPTION
            "Table entry specifying a single routing number."
        INDEX   { routingNumberGroup, routingNumberIndex }
        ::= { routingNumberTable 1 }

    RoutingNumberEntry ::=
        SEQUENCE {
            routingNumberGroup          RoutingNumberGroupIndex,
            routingNumberIndex          RoutingNumberIndex,
            routingNumberAdminState     AdminState,
            routingNumberDigits         RoutingNumber,
            routingNumberTotalCounter   Counter,
            routingNumberMsisdnCounter  Counter,
            routingNumberImsiCounter    Counter
        }

    routingNumberGroup OBJECT-TYPE
        SYNTAX  RoutingNumberGroupIndex
        ACCESS  read-write
        STATUS  mandatory
        DESCRIPTION
            "Index of the routing number group, to which this entry of the
            routing number table belongs."
        ::= { routingNumberEntry 1 }

    routingNumberIndex OBJECT-TYPE
        SYNTAX  RoutingNumberIndex
        ACCESS  read-write
        STATUS  mandatory
        DESCRIPTION
            "Index of the routing number within the routing number group as
            identified by routingNumberGroupIndex."
        ::= { routingNumberEntry 2 }

    routingNumberAdminState OBJECT-TYPE
        SYNTAX  AdminState
        ACCESS  read-write
        STATUS  mandatory
        DESCRIPTION
            "Administrative state of a routing number. This parameter is
            only used for destroying a routing number table entry."
        ::= { routingNumberEntry 3 }

    routingNumberDigits OBJECT-TYPE
        SYNTAX  RoutingNumber
        ACCESS  read-write
        STATUS  mandatory
        DESCRIPTION
            "Hexadecimal 'digits' of the routing number. The value of this
            parameter must be unique for the entire table.
            By default, this object is set to the empty string ''."
        ::= { routingNumberEntry 4 }

    routingNumberTotalCounter OBJECT-TYPE
        SYNTAX  Counter
        ACCESS  read-write
        STATUS  mandatory
        DESCRIPTION
            "Counts the total number of times that the corresponding routing
            number has been matched against a message's address."
        ::= { routingNumberEntry 11 }

    routingNumberMsisdnCounter OBJECT-TYPE
        SYNTAX  Counter
        ACCESS  read-write
        STATUS  mandatory
        DESCRIPTION
            "Counts the number of times that the corresponding routing
            number has been matched against a message's MSISDN."
        ::= { routingNumberEntry 12 }

    routingNumberImsiCounter OBJECT-TYPE
        SYNTAX  Counter
        ACCESS  read-write
        STATUS  mandatory
        DESCRIPTION
            "Counts the number of times that the corresponding routing
            number has been matched against a message's IMSI."
        ::= { routingNumberEntry 13 }


    routingNumberGroupTable OBJECT-TYPE
        SYNTAX  SEQUENCE OF RoutingNumberGroupEntry
        ACCESS  not-accessible
        STATUS  mandatory
        DESCRIPTION
            "A table to hold all routing number groups known to TextPass."
        ::= { sms 99 }

    routingNumberGroupEntry OBJECT-TYPE
        SYNTAX  RoutingNumberGroupEntry
        ACCESS  not-accessible
        STATUS  mandatory
        DESCRIPTION
            "Table entry specifying a single routing number group."
        INDEX   { routingNumberGroupIndex }
        ::= { routingNumberGroupTable 1 }

    RoutingNumberGroupEntry ::=
        SEQUENCE {
            routingNumberGroupIndex         RoutingNumberGroupIndex,
            routingNumberGroupAdminState    AdminState,
            routingNumberGroupName          NameString,
            routingNumberGroupTotalCounter  Counter,
            routingNumberGroupMsisdnCounter Counter,
            routingNumberGroupImsiCounter   Counter
        }

    routingNumberGroupIndex OBJECT-TYPE
        SYNTAX  RoutingNumberGroupIndex
        ACCESS  read-write
        STATUS  mandatory
        DESCRIPTION
            "Index of the routing number group."
        ::= { routingNumberGroupEntry 1 }

    routingNumberGroupAdminState OBJECT-TYPE
        SYNTAX  AdminState
        ACCESS  read-write
        STATUS  mandatory
        DESCRIPTION
            "Administrative state of a routing number group. A routing
            number group can only be activated if it has a unique name
            in this table.
            Routing numbers can only be matched if the administrative
            state of their group is set to active."
        ::= { routingNumberGroupEntry 2 }

    routingNumberGroupName OBJECT-TYPE
        SYNTAX  NameString
        ACCESS  read-write
        STATUS  mandatory
        DESCRIPTION
            "Descriptive yet unique name of the routing number group.
            The value of this object cannot be changed while its
            administrative state is set to active. By default, this
            object is set to the empty string ''."
        ::= { routingNumberGroupEntry 3 }

    routingNumberGroupTotalCounter OBJECT-TYPE
        SYNTAX  Counter
        ACCESS  read-write
        STATUS  mandatory
        DESCRIPTION
            "Counts the total number of times that a message's address
            has been matched against a number of this group."
        ::= { routingNumberGroupEntry 11 }

    routingNumberGroupMsisdnCounter OBJECT-TYPE
        SYNTAX  Counter
        ACCESS  read-write
        STATUS  mandatory
        DESCRIPTION
            "Counts the number of times that a MSISDN
            has been matched against a number of this group."
        ::= { routingNumberGroupEntry 12 }

    routingNumberGroupImsiCounter OBJECT-TYPE
        SYNTAX  Counter
        ACCESS  read-write
        STATUS  mandatory
        DESCRIPTION
            "Counts the number of times that a IMSI
            has been matched against a number of this group."
        ::= { routingNumberGroupEntry 13 }


    -- Billing

    bilProperties OBJECT IDENTIFIER ::= { sms 101 }

    bilPropDefaultProfileForMo OBJECT-TYPE
        SYNTAX  BilProfile
        ACCESS  read-write
        STATUS  mandatory
        DESCRIPTION
            "Identifier specifying which billing profile should be used for
            MO/SM's as a default. Default is 0 (i.e. 'none'). The value 1000
            (i.e. 'default') does not apply for this object."
        ::= { bilProperties 1 }

    bilPropDefaultProfileForMt OBJECT-TYPE
        SYNTAX  BilProfile
        ACCESS  read-write
        STATUS  mandatory
        DESCRIPTION
            "Identifier specifying which billing profile should be used for
            MT/SM's as a default. Default is 0 (i.e. 'none'). The value 1000
            (i.e. 'default') does not apply for this object."
        ::= { bilProperties 2 }

    bilPropDefaultProfileForAo OBJECT-TYPE
        SYNTAX  BilProfile
        ACCESS  read-write
        STATUS  mandatory
        DESCRIPTION
            "Identifier specifying which billing profile should be used for
            AO/SM's as a default. Default is 0 (i.e. 'none'). The value 1000
            (i.e. 'default') does not apply for this object."
        ::= { bilProperties 3 }

    bilPropDefaultProfileForAt OBJECT-TYPE
        SYNTAX  BilProfile
        ACCESS  read-write
        STATUS  mandatory
        DESCRIPTION
            "Identifier specifying which billing profile should be used for
            AT/SM's as a default. Default is 0 (i.e. 'none'). The value 1000
            (i.e. 'default') does not apply for this object."
        ::= { bilProperties 4 }

    bilPropFcdrAlphanumericAddressInOrigAddressGsmField OBJECT-TYPE
        SYNTAX  Boolean
        ACCESS  read-write
        STATUS  mandatory
        DESCRIPTION
            "Indicator specifying whether or not an alphanumeric address
            should be stored in the origAddressGsm field in case of an AO
            message with an alphanumeric address. When set to 'true', the
            alphanumeric address is put in the the origAddressGsm field. When
            set to 'false', the short number of the relating application will
            be used for the origAddressGsm field.
            Default is 'true'."
        ::= { bilProperties 11 }

    bilPropFcdrSupportForMtMt OBJECT-TYPE
        SYNTAX  Boolean
        ACCESS  read-write
        STATUS  mandatory
        DESCRIPTION
            "Indicator specifying whether CDR-s needs to be generated for
            MT-MT path when billing format is equal to 'fcdr'. Note that the
            CDR-s generated are not conform the FCDR standard as defined by
            CMG. The CDR-s follow a mBalance proprietary standard.
            Default is 'false'."
        ::= { bilProperties 12 }

    bilPropFcdrMaxValidityPeriod OBJECT-TYPE
        SYNTAX  FcdrMaxPeriod
        ACCESS  read-write
        STATUS  mandatory
        DESCRIPTION
            "Threshold for maximum value for fcdrValidityPeriod field. If
            this threshold is exceeded, the maximum value will be put in the
            billing record. Default is 8760 (1 year)."
        ::= { bilProperties 13 }

    bilPropFcdrMaxDeferPeriod OBJECT-TYPE
        SYNTAX  FcdrMaxPeriod
        ACCESS  read-write
        STATUS  mandatory
        DESCRIPTION
            "Threshold for maximum value for fcdrDeferPeriod field. If this
            threshold is exceeded, the maximum value will be put in the
            billing record. Default is 8760 (1 year)."
        ::= { bilProperties 14 }

    bilPropFcdrEnforceTon4AndNpi5ForShortNumbers OBJECT-TYPE
        SYNTAX  Boolean
        ACCESS  read-write
        STATUS  mandatory
        DESCRIPTION
            "Indicator specifying whether TON value 4 (subscriber) and NPI
            value 5 (private) are to be used for short numbers. Only
            applicable in case the format for the concerning billing field is
            'national' or 'international'. Default is true."
        ::= { bilProperties 15 }

    bilPropFcdrAlphanumericFormatInConstruct OBJECT-TYPE
        SYNTAX  AlphanumInConstruct
        ACCESS  read-write
        STATUS  mandatory
        DESCRIPTION
            "Indicator specifying how alphanumeric addresses should be
            formatted in the MSISDN field of the address construct:

                - 'empty': MSISDN field is empty (length 0).
                - 'numeric' (default): decoded as if the address were numeric.
                - 'alphanumeric': decoded as readable string (UTF-8).

            Note that if the message's relation with an application can be
            established (like in the case of an AO message),
            bilPropFcdrAlphanumericAddressInOrigAddressGsmField allows you to
            encode the application's short number rather than the alphanumeric
            address."
        ::= { bilProperties 16 }

    bilPropFcdrVsmscId OBJECT-TYPE
        SYNTAX  INTEGER (-1..999)
        ACCESS  read-write
        STATUS  mandatory
        DESCRIPTION
            "Value of the VsmscId field. When set to -1 (default), the ID is
            determined based on the last 3 digits of the SMSC's GT. Otherwise,
            the specified value is placed into the CDR."
        ::= { bilProperties 17 }

    bilPropIcacheTimeoutStatus OBJECT-TYPE
        SYNTAX  FcdrStatus
        ACCESS  read-write
        STATUS  mandatory
        DESCRIPTION
            "Value to be used for Icache records that timeout, where a billing
            record is written in spite of the absence of a real SMSC expiry.
            Default value is 'expired(1)'"
        ::= { bilProperties 18 }

    bilPropNcdrExchangeId OBJECT-TYPE
        SYNTAX  E164Address
        ACCESS  read-write
        STATUS  mandatory
        DESCRIPTION
            "Address to be used for the Exchange Id field in the header and
            tailer and for smsCentre file in the body of the Nokia CDR block.
            By default, this address is equal to the specific GT address."
        ::= { bilProperties 21 }

    bilPropBillingId OBJECT-TYPE
        SYNTAX  NameString
        ACCESS  read-write
        STATUS  mandatory
        DESCRIPTION
            "String specifying the billing ID. This string will replace the
            %i format specifier in bilProfileFileNameTemplate."
        ::= { bilProperties 31 }
        
    bilPropResetSequenceNumberOfBillingProfileUponDestroy OBJECT-TYPE     
        SYNTAX  Boolean
        ACCESS  read-write
        STATUS  mandatory
        DESCRIPTION
            "Boolean specifying whether destroying a billing profile should 
            imply a reset of the associated sequence number in the permanent 
            storage that TextPass maintains for billing profile sequence 
            numbers. Default is 'true'.      
            The sequence number that is maintained for a billing profile is 
            (optionally) used in the names of the CDR files that are generated
            for the billing profile.
            Resetting the billing profile sequence number is required to
            ensure that a newly added billing profile that is mapped to a
            table index that has been used before has a properly initialised
            sequence number (rather than the sequence number of the billing
            profile that was mapped to the same table index before).
            The value 'false' is typically used when a billing profile is
            temporary removed. Not resetting the sequence number will then
            ensure that the sequence number after removal will commence from
            the value before the removal."
        ::= { bilProperties 32 }

    bilPropCcdrRouterId OBJECT-TYPE
        SYNTAX  CcdrRouterId
        ACCESS  read-write
        STATUS  mandatory
        DESCRIPTION
            "Unique ID for router that is used in the generation of the ISN 
            field. By default, the ID is 0."
        ::= { bilProperties 41 }

    bilPropScdrRouterId OBJECT-TYPE
        SYNTAX  ScdrRouterId
        ACCESS  read-write
        STATUS  mandatory
        DESCRIPTION
            "Unique ID for router that is used in the generation of the 
            Message ID field in SS8 CDRs. ID conflicts are likely if
            this number is not unique (modulo bilPropScdrRouterNum). 
            By default, the ID is 0."
        ::= { bilProperties 42 }

    bilPropScdrRouterNum OBJECT-TYPE
        SYNTAX  ScdrRouterNum
        ACCESS  read-write
        STATUS  mandatory
        DESCRIPTION
            "Number of routers with unique IDs. This is used for the 
            generation of the Message ID field in SS8 CDRs. ID conflicts are 
            likely if more routers are used. The valid range is 1-255.
            By default, the number is 2."
        ::= { bilProperties 43 }

    bilPropScdrSmPerSecond OBJECT-TYPE
        SYNTAX  ScdrSmPerSecond
        ACCESS  read-write
        STATUS  mandatory
        DESCRIPTION
            "Number of expected messages per routers and second. This is used 
            for the generation of a uniquee Message ID field in SS8 CDRs.
            ID conflicts are possible if more messages are processed for a 
            longer a mount of time. Otherwise, IDs are guaranteed to be unique
            for about 50000 days divided by this number and divided by
            bilPropScdrRouterNum. The valid range is 1-10000.
            By default, the expected value is 1024."
        ::= { bilProperties 44 }

    bilPropAdjustPrepaidIndicatorOnDeductFailure OBJECT-TYPE
        SYNTAX  Boolean
        ACCESS  read-write
        STATUS  mandatory
        DESCRIPTION
            "Indicator specifying whether the Prepaid-Indicator of the
            Comverse deliver CDR and prepaidBillingState of the CMG delvier
            CDR should be adjusted from 'online-billed' to 'hot-billed' if
            the Diameter deduct operation fails (result code is outside the
            range 2001-2999). 
            By default, the value of this attribute is 'false'."
        ::= { bilProperties 45 }

    bilPropDeliverCdrForSuccessfulMoAoForwarding OBJECT-TYPE
        SYNTAX  Boolean
        ACCESS  read-write
        STATUS  mandatory
        DESCRIPTION
            "Indicator specifying whether delivery CDRs should be generated
            after successful MO-AO or MO-MT-AO submission. By default, the
            value of this attribute is 'false'."
        ::= { bilProperties 46 }

    bilPropDeliverCdrForSuccessfulAoAoForwarding OBJECT-TYPE
        SYNTAX  Boolean
        ACCESS  read-write
        STATUS  mandatory
        DESCRIPTION
            "Indicator specifying whether delivery CDRs should be generated
            after successful AO-AO or AO-MT-AO submission. By default, the
            value of this attribute is 'true'."
        ::= { bilProperties 47 }

    bilPropExtAttrUsedForPostpaidOriginator OBJECT-TYPE
        SYNTAX  ExtAttrId
        ACCESS  read-write
        STATUS  mandatory
        DESCRIPTION
            "Index of external attribute that is used by PBC to indicate that
            the originator is postpaid. 
            For Comverse CDR-s, this info is used to compose the field
            prepaid_status in the CDR. It is also used for the (optional)
            alternative indication of the prepaid status in the field 
            Sa_options_int_n of the CDR.
            For CMG CDR-s, this field is used as a base to compose the ppPser 
            field as well as the proprietary subscriberStatus and 
            prepaidBillingState fields.
            Default value is 0, implying that no external attribute is defined 
            for postpaid originators."
        ::= { bilProperties 51 }

    bilPropExtAttrUsedForPrepaidHotBillingOriginator OBJECT-TYPE
        SYNTAX  ExtAttrId
        ACCESS  read-write
        STATUS  mandatory
        DESCRIPTION
            "Index of external attribute that is used by PBC to indicate that
            the originator is prepaid and charged using the hot-billing 
            mechanism. 
            For Comverse CDR-s, this info is used to compose the field 
            prepaid_status in the CDR. It is also used for the (optional) 
            alternative indication of the prepaid status in the field 
            Sa_options_int_n of the CDR. 
            For CMG CDR-s, this field is used as a base to compose the ppPser 
            field as well as the proprietary subscriberStatus and 
            prepaidBillingState fields.
            Default value is 0, implying that no external attribute is defined 
            for prepaid originators that are charged using the hot-billing
            mechanism."
        ::= { bilProperties 52 }

    bilPropExtAttrUsedForPrepaidOnlineOriginator OBJECT-TYPE
        SYNTAX  ExtAttrId
        ACCESS  read-write
        STATUS  mandatory
        DESCRIPTION
            "Index of external attribute that is used by PBC to indicate that
            the originator is prepaid and charged using an on-line mechanism 
            (e.g. Diameter). 
            For Comverse CDR-s, this info is used to compose the field 
            prepaid_status in the CDR. It is also used for the (optional)
            alternative indication of the prepaid status in the field 
            Sa_options_int_n of the CDR.
            For CMG CDR-s, this field is used as a base to compose the ppPser 
            field as well as the proprietary subscriberStatus and 
            prepaidBillingState fields.
            Default value is 0, implying that no external attribute is defined 
            for prepaid originators that are charged using an on-line
            mechanism."
        ::= { bilProperties 53 }

    bilPropExtAttrUsedForPostpaidRecipient OBJECT-TYPE
        SYNTAX  ExtAttrId
        ACCESS  read-write
        STATUS  mandatory
        DESCRIPTION
            "Index of external attribute that is used by PBC to indicate that
            the recipient is postpaid. 
            For Comverse CDR-s, this info is not used at all.
            For CMG CDR-s, this field is used as a base to compose the ppPser 
            field.
            Default value is 0, implying that no external attribute is defined 
            for postpaid recipients."
        ::= { bilProperties 56 }

    bilPropExtAttrUsedForPrepaidHotBillingRecipient OBJECT-TYPE
        SYNTAX  ExtAttrId
        ACCESS  read-write
        STATUS  mandatory
        DESCRIPTION
            "Index of external attribute that is used by PBC to indicate that
            the recipient is prepaid and charged using the hot-billing 
            mechanism. 
            For Comverse CDR-s, this info is not used at all.
            For CMG CDR-s, this field is used as a base to compose the ppPser 
            field.
            Default value is 0, implying that no external attribute is defined 
            for prepaid recipients that are charged using the hot-billing
            mechanism."
        ::= { bilProperties 57 }

    bilPropExtAttrUsedForPrepaidOnlineRecipient OBJECT-TYPE
        SYNTAX  ExtAttrId
        ACCESS  read-write
        STATUS  mandatory
        DESCRIPTION
            "Index of external attribute that is used by PBC to indicate that
            the recipient is prepaid and charged using an on-line mechanism 
            (e.g. Diameter). 
            For Comverse CDR-s, this info is not used at all.
            For CMG CDR-s, this field is used as a base to compose the ppPser 
            field.
            Default value is 0, implying that no external attribute is defined 
            for prepaid recipients that are charged using an on-line
            mechanism."
        ::= { bilProperties 58 }
        
    bilPropExtAttrUsedForSmartLimitOriginator OBJECT-TYPE
        SYNTAX  ExtAttrId
        ACCESS  read-write
        STATUS  mandatory
        DESCRIPTION
            "Index of external attribute that is used by PBC to indicate that
            the originator is using SmartLimit."
        ::= { bilProperties 59 }
        
    bilPropExtAttrUsedForSmartLimitRecipient OBJECT-TYPE
        SYNTAX  ExtAttrId
        ACCESS  read-write
        STATUS  mandatory
        DESCRIPTION
            "Index of external attribute that is used by PBC to indicate that
            the recipient is using SmartLimit."
        ::= { bilProperties 60 }

    bilPropLcdrRouterId OBJECT-TYPE
        SYNTAX  LcdrRouterId
        ACCESS  read-write
        STATUS  mandatory
        DESCRIPTION
            "Unique ID for router that is used in the generation of the Call
            Reference field. By default, the ID is 0."
        ::= { bilProperties 71 }

    bilProfileTable OBJECT-TYPE
        SYNTAX  SEQUENCE OF BilProfileEntry
        ACCESS  not-accessible
        STATUS  mandatory
        DESCRIPTION
            "A table containing profiles for billing."
        ::= { sms 102 }

    bilProfileEntry OBJECT-TYPE
        SYNTAX  BilProfileEntry
        ACCESS  not-accessible
        STATUS  mandatory
        DESCRIPTION
            "Table entry specifying a single billing profile."
        INDEX   { bilProfileIndex }
        ::= { bilProfileTable 1 }

    BilProfileEntry ::=
        SEQUENCE {
            bilProfileIndex                       BilProfileTableIndex,
            bilProfileAdminState                  AdminState,
            bilProfileName                        NameString,
            bilProfileLastIoError                 ErrorString,
            bilProfileProcessingDirectory         FileSpec,
            bilProfileFinishedDirectory           FileSpec,
            bilProfileFileNameTemplate            FileSpec,
            bilProfileMaxFileSize                 BilFileSize,
            bilProfileMaxFileDuration             BilFileDuration,
            bilProfileMaxFileRecords              BilFileRecords,
            bilProfileFileFormat                  BilFileFormat,
            bilProfileStartingSequenceNumber      Gauge,
            bilProfileAffectedMessageTypes        BilAffectedMessageTypes,
            bilProfileApplicableForSuccessfulCasesOnly Boolean,
            bilProfileScdrSequenceNumber          Gauge,
            bilProfileFcdrNotDeliveredStatus      FcdrStatus,
            bilProfileFcdrMtSriOnlyStatus         FcdrStatus,
            bilProfileFcdrMtFailedStatus          FcdrStatus,
            bilProfileFcdrMtSuccessStatus         FcdrStatus,
            bilProfileFcdrUseAoConsolidationForAoAt     Boolean,
            bilProfileFcdrFormatOrigAddressField  AddressFormat,
            bilProfileFcdrFormatOrigAddressGsmField AddressFormat,
            bilProfileFcdrFormatRecipAddressField AddressFormat,
            bilProfileFcdrFormatRecipAddressGsmField AddressFormat,
            bilProfileFcdrFormatNotifAddressField AddressFormat,
            bilProfileFcdrFormatNotifAddressGsmField AddressFormat,
            bilProfileFcdrFormatOgtiAddressField  AddressFormat,
            bilProfileFcdrFormatOgtiAddressGsmField AddressFormat,
            bilProfileFcdrFormatDgtiAddressField  AddressFormat,
            bilProfileFcdrFormatDgtiAddressGsmField AddressFormat,
            bilProfileFcdrFormatCallingLineIdField AddressFormat,
            bilProfileFcdrFormatCallingLineIdGsmField AddressFormat,
            bilProfileFcdrIncludeSubscriberStatusOfRecipientField Boolean,
            bilProfileFcdrIncludePrepaidBillingStateOfRecipientField Boolean,
            bilProfileFcdrIncludeOriginatorApplicationChargingUnitsField Boolean,
            bilProfileFcdrIncludeRecipientApplicationChargingUnitsField Boolean,
            bilProfileFcdrIncludeLangField        Boolean,
            bilProfileFcdrIncludeSmeReferenceField Boolean,
            bilProfileFcdrIncludeSmsContentDcsField Boolean,
            bilProfileFcdrIncludeSmsContentsField Boolean,
            bilProfileFcdrIncludeMessageReferenceField Boolean,
            bilProfileFcdrIncludeOrigLasnField    Boolean,
            bilProfileFcdrIncludeRecipLasnField   Boolean,
            bilProfileFcdrIncludeOrigMsgIdField   Boolean,
            bilProfileFcdrIncludeServiceTypeField Boolean,
            bilProfileFcdrIncludeUntranslOrigAddressField Boolean,
            bilProfileFcdrIncludeUntranslOrigAddressGsmField Boolean,
            bilProfileFcdrIncludeUntranslRecipAddressField Boolean,
            bilProfileFcdrIncludeUntranslRecipAddressGsmField Boolean,
            bilProfileFcdrIncludeTpDcsField       Boolean,
            bilProfileFcdrIncludeGenericUrgencyLevelField Boolean,
            bilProfileFcdrIncludeFurnishChargingInfoField Boolean,
            bilProfileFcdrIncludeXsMessageTypeField Boolean,
            bilProfileFcdrIncludeRecipientRoutingNumber Boolean,
            bilProfileFcdrIncludeXsTieBillingIdField  Boolean,
            bilProfileFcdrIncludeSs8LastFailureReasonField Boolean,
            bilProfileFcdrIncludeChargeInfoField  Boolean,
            bilProfileFcdrIncludeSubscriberStatusField Boolean,
            bilProfileFcdrIncludePrepaidResultCodeField Boolean,
            bilProfileFcdrIncludePrepaidBillingStateField Boolean,            
            bilProfileFcdrIncludeSmscPresentationAddressField Boolean,
            bilProfileFcdrIncludeSmscPresentationAddressGsmField Boolean,
            bilProfileFcdrIncludeOrglOrigAddressField Boolean,
            bilProfileFcdrIncludeOrglOrigAddressGsmField Boolean,
            bilProfileFcdrIncludeOrglRecipAddressField Boolean,
            bilProfileFcdrIncludeOrglRecipAddressGsmField Boolean,
            bilProfileFcdrIncludeOrglNotifAddressField Boolean,
            bilProfileFcdrIncludeOrglNotifAddressGsmField Boolean,
            bilProfileFcdrIncludeExternalAttributesField Boolean,
            bilProfileFcdrIncludeCimdPriorityField Boolean,
            bilProfileFcdrIncludeCimdServiceDescriptionField Boolean,
            bilProfileFcdrIncludeCimdTariffClassField Boolean,
            bilProfileFcdrIncludeOrigAddressField Boolean,
            bilProfileFcdrIncludeOrigAddressGsmField Boolean,
            bilProfileFcdrIncludeRecipAddressField Boolean,
            bilProfileFcdrIncludeRecipAddressGsmField Boolean,
            bilProfileFcdrIncludeSubmitDateField  Boolean,
            bilProfileFcdrIncludeSubmitTimeField  Boolean,
            bilProfileFcdrIncludeStatusField Boolean,
            bilProfileFcdrIncludeTerminDateField  Boolean,
            bilProfileFcdrIncludeTerminTimeField  Boolean,
            bilProfileFcdrIncludeLengthOfMessageField Boolean,
            bilProfileFcdrIncludePrioIndicatorField Boolean,
            bilProfileFcdrIncludeValidityPeriodField Boolean,
            bilProfileFcdrIncludeDeferIndicatorField Boolean,
            bilProfileFcdrIncludeDeferPeriodField Boolean,
            bilProfileFcdrIncludeNotifIndicatorField Boolean,
            bilProfileFcdrIncludeNotifAddressField Boolean,
            bilProfileFcdrIncludeNotifAddressGsmField Boolean,
            bilProfileFcdrIncludeVsmscIdField     Boolean,
            bilProfileFcdrIncludeVsmscTypeField   Boolean,
            bilProfileFcdrIncludeDgtiAddressField Boolean,
            bilProfileFcdrIncludeDgtiAddressGsmField Boolean,
            bilProfileFcdrIncludeDestPointCodeField Boolean,
            bilProfileFcdrIncludeOgtiAddressField Boolean,
            bilProfileFcdrIncludeOgtiAddressGsmField Boolean,
            bilProfileFcdrIncludeOrigPointCodeField Boolean,
            bilProfileFcdrIncludeOrglSubmitDateField Boolean,
            bilProfileFcdrIncludeOrglSubmitTimeField Boolean,
            bilProfileFcdrIncludeTransparentPidField Boolean,
            bilProfileFcdrIncludeMesgReplyPathField Boolean,
            bilProfileFcdrIncludeIntlMobileSubIdField Boolean,
            bilProfileFcdrIncludeCallingLineIdField Boolean,
            bilProfileFcdrIncludeCallingLineIdGsmField Boolean,
            bilProfileFcdrIncludeConsolidationField Boolean,
            bilProfileFcdrIncludePortNumberField  Boolean,
            bilProfileFcdrIncludeAserField        Boolean,
            bilProfileFcdrIncludeMserField        Boolean,
            bilProfileFcdrIncludeNserField        Boolean,
            bilProfileFcdrIncludeXserField        Boolean,
            bilProfileFcdrIncludeOrigIntlMobileSubIdField Boolean,
            bilProfileFcdrIncludeBillIdField      Boolean,
            bilProfileFcdrIncludePpPserField      Boolean,
            bilProfileFcdrIncludeCmReferenceNrField Boolean,
            bilProfileFcdrIncludeCurrentSegmentField Boolean,
            bilProfileFcdrIncludeSegmentsTotalField Boolean,
            bilProfileFcdrIncludeDeliveryAttemptsField Boolean,
            bilProfileFcdrAddressInformationIncludesMsisdnUtf8 Boolean,
            bilProfileNcdrFormatVersion           NcdrFormat,
            bilProfileNcdrIncludeFormatVersion    Boolean,
            bilProfileNcdrCloseEmptyFile          Boolean,
            bilProfileNcdrUseGmtTimestamp         Boolean,
            bilProfileNcdrMinTariffClass          CimdTariffClass,
            bilProfileNcdrDefaultTariffClass      CimdTariffClass,
            bilProfileNcdrDefaultServiceDescription CimdServiceDescription,
            bilProfileNcdrRecordTypeSubmit        NcdrRecordType,
            bilProfileNcdrRecordTypeDeliver       NcdrRecordType,
            bilProfileNcdrRecordTypeReceive       NcdrRecordType,
            bilProfileNcdrRecordTypeDeleted       NcdrRecordType,
            bilProfileNcdrRecordTypeStatus1       NcdrRecordType,
            bilProfileNcdrRecordTypeStatus2       NcdrRecordType,
            bilProfileNcdrRecordTypeExpired       NcdrRecordType,
            bilProfileNcdrFallbackTariffClass     CimdTariffClass,
            bilProfileEcdrRecordType              EcdrRecordType,
            bilProfileEcdrTacTsc                  EcdrTsc,
            bilProfileEcdrTacTos                  EcdrTos,
            bilProfileEcdrTacToi                  EcdrToi,
            bilProfileEcdrTypeOfCallingSubscriber EcdrTypeOfCallingSubscriber,
            bilProfileEcdrChargedParty            EcdrChargedParty,
            bilProfileEcdrOriginForCharging       EcdrOriginForCharging,
            bilProfileEcdrExchangeIdentity        EcdrExchangeIdentity,
            bilProfileEcdrIncomingRoute           EcdrRoute,
            bilProfileEcdrOutgoingRoute           EcdrRoute,
            bilProfileEcdrGsmTeleServiceCode      EcdrGsmTeleServiceCode,
            bilProfileEcdrIncludeTacField         Boolean,
            bilProfileEcdrIncludeCallIdentificationNumberField  Boolean,
            bilProfileEcdrIncludeRecordSequenceNumberField  Boolean,
            bilProfileEcdrIncludeTypeOfCallingSubscriberField  Boolean,
            bilProfileEcdrIncludeCallingPartyNumberField  Boolean,
            bilProfileEcdrIncludeCallingSubscriberImsiField  Boolean,
            bilProfileEcdrIncludeDateForStartOfChargeField  Boolean,
            bilProfileEcdrIncludeTimeForStartOfChargeField  Boolean,
            bilProfileEcdrIncludeChargedPartyField  Boolean,
            bilProfileEcdrIncludeOriginForChargingField  Boolean,
            bilProfileEcdrIncludeExchangeIdentityField  Boolean,
            bilProfileEcdrIncludeMscIdentificationField  Boolean,
            bilProfileEcdrIncludeIncomingRouteField  Boolean,
            bilProfileEcdrIncludeGsmTeleServiceCodeField  Boolean,
            bilProfileEcdrIncludeServiceCentreAddressField  Boolean,
            bilProfileEcdrIncludeCalledPartyNumberField  Boolean,
            bilProfileEcdrIncludeCalledSubscriberImsiField  Boolean,
            bilProfileEcdrIncludeOutgoingRouteField  Boolean,
            bilProfileEcdrIncludeMscNumberField   Boolean,
            bilProfileCcdrIncludeProprietaryPrepaidIndicator Boolean,
            bilProfileCcdrIncludeDiameterDetails  Boolean,
            bilProfileCopy1OfFinishedDirectory    FileSpec,                      
            bilProfileCopy2OfFinishedDirectory    FileSpec,                      
            bilProfileCopy3OfFinishedDirectory    FileSpec,                      
            bilProfileCopy4OfFinishedDirectory    FileSpec,                      
            bilProfileCopy5OfFinishedDirectory    FileSpec,                      
            bilProfileCopy6OfFinishedDirectory    FileSpec,                      
            bilProfileCopy7OfFinishedDirectory    FileSpec,                      
            bilProfileCopy8OfFinishedDirectory    FileSpec,                      
            bilProfileCopy9OfFinishedDirectory    FileSpec,
            bilProfileScdrIncludeSmField          Boolean,
            bilProfileLcdrCustomFormat            LcdrCustomFormat           
    }

    bilProfileIndex OBJECT-TYPE
        SYNTAX  BilProfileTableIndex
        ACCESS  read-write
        STATUS  mandatory
        DESCRIPTION
            "Index of entry in billing profile table."
        ::= { bilProfileEntry 1 }

    bilProfileAdminState OBJECT-TYPE
        SYNTAX  AdminState
        ACCESS  read-write
        STATUS  mandatory
        DESCRIPTION
            "Administrative state of billing profile."
        ::= { bilProfileEntry 2 }

    bilProfileName OBJECT-TYPE
        SYNTAX  NameString
        ACCESS  read-write
        STATUS  mandatory
        DESCRIPTION
            "Name of billing profile."
        ::= { bilProfileEntry 3 }

    bilProfileLastIoError OBJECT-TYPE
        SYNTAX  ErrorString
        ACCESS  read-write
        STATUS  mandatory
        DESCRIPTION
            "Information about last I/O error that occurred for the 
            billing profile. The information comprises timestamp, file name,
            and error description."
        ::= { bilProfileEntry 4 }

    bilProfileProcessingDirectory OBJECT-TYPE
        SYNTAX  FileSpec
        ACCESS  read-write
        STATUS  mandatory
        DESCRIPTION
            "Specification of the directory which is used for the billing
            files during the creation of these files. Default is
            /var/TextPass/processing.
            Note: this setting can only be changed when the device adminState
            is disabled."
        ::= { bilProfileEntry 11 }

    bilProfileFinishedDirectory OBJECT-TYPE
        SYNTAX  FileSpec
        ACCESS  read-write
        STATUS  mandatory
        DESCRIPTION
            "Specification of the directory where the billing files are stored
            when they are completed. This directory should be on the same disc
            partition as the bilProfileProcessingDirectory.
            Default is /var/TextPass/billing.
            Note: this setting can only be changed when the device adminState
            is disabled."
        ::= { bilProfileEntry 12 }

    bilProfileFileNameTemplate OBJECT-TYPE
        SYNTAX  FileSpec
        ACCESS  read-write
        STATUS  mandatory
        DESCRIPTION
            "String specifying the format for the name of the billing file.
            The following format specifiers are supported:
            %Y - year specified in four digits (e.g. 2004)
            %y - year specified in two digits (e.g. 04)
            %m - month specified in two digits (e.g. 01 for Jan, 10 for Oct)
            %d - day specified in two digits (e.g 01 for 1st day of month, 31
                                              for last day of month)
            %H - hour specified in two digits (e.g 00 for midnight, 12 for
                                               noon)
            %M - minute specified in two digits
            %S - second specified in two digits
            %h - hostname
            %i - billing ID (specified using object bilPropBillingId)
            %1 - a one-digit sequence number
            %2 - a two-digit sequence number
            %3 - a three-digit sequence number
            %4 - a four-digit sequence number
            %5 - a five-digit sequence number
            %6 - a six-digit sequence number
            %7 - a seven-digit sequence number
            %8 - a eight-digit sequence number
            %n5 - a five-digit count of records (Huawei format only)
            %n6 - a six-digit count of records (Huawei format only)
            %n7 - a seven-digit count of records (Huawei format only)
            %n8 - a eight-digit count of records (Huawei format only)
            %n9 - a nine-digit count of records (Huawei format only)

            Default is: cdr_%h_%Y%m%d_%H%M%S_%3.dat"
        ::= { bilProfileEntry 13 }

    bilProfileMaxFileSize OBJECT-TYPE
        SYNTAX  BilFileSize
        ACCESS  read-write
        STATUS  mandatory
        DESCRIPTION
            "Specification of maximum length, expressed in bytes, for a
            billing file. Default is 1M."
        ::= { bilProfileEntry 14 }

    bilProfileMaxFileDuration OBJECT-TYPE
        SYNTAX  BilFileDuration
        ACCESS  read-write
        STATUS  mandatory
        DESCRIPTION
            "Specification of maximum duration, expressed in seconds, for a
            billing file. Default is 1 hour."
        ::= { bilProfileEntry 15 }

    bilProfileMaxFileRecords OBJECT-TYPE
        SYNTAX  BilFileRecords
        ACCESS  read-write
        STATUS  mandatory
        DESCRIPTION
            "Specification of maximum number of records in a billing file.
            Default is 10000."
        ::= { bilProfileEntry 16 }

    bilProfileFileFormat OBJECT-TYPE
        SYNTAX  BilFileFormat
        ACCESS  read-write
        STATUS  mandatory
        DESCRIPTION
            "Format of billing file. Default is 'fcdr'."
        ::= { bilProfileEntry 17 }

    bilProfileStartingSequenceNumber OBJECT-TYPE
        SYNTAX  Gauge
        ACCESS  read-write
        STATUS  mandatory
        DESCRIPTION
            "Start of range of sequence numbers to be used in the billing
            file name. Default is 0."
        ::= { bilProfileEntry 18 }

    bilProfileAffectedMessageTypes OBJECT-TYPE
        SYNTAX  BilAffectedMessageTypes
        ACCESS  read-write
        STATUS  mandatory
        DESCRIPTION
            "Bitstring specifying the message types for which this profile
            applies."
        ::= { bilProfileEntry 21 }

    bilProfileApplicableForSuccessfulCasesOnly OBJECT-TYPE
        SYNTAX  Boolean
        ACCESS  read-write
        STATUS  mandatory
        DESCRIPTION
            "Boolean specifying whether using this profile is restricted to
            successful messsages. Default is 'false'."
        ::= { bilProfileEntry 22 }

    bilProfileScdrSequenceNumber OBJECT-TYPE
        SYNTAX  Gauge
        ACCESS  read-write
        STATUS  mandatory
        DESCRIPTION
            "Current record sequence number used for SS8 CDRs. 
            It is incremented by one for each CDR written. 
            The setting is persistent. It is read when the device goes
            active, and written while it is active and when it goes
            inactive. So you should only change this value while the device
            is active."
        ::= { bilProfileEntry 23 }

    bilProfileFcdrNotDeliveredStatus OBJECT-TYPE
        SYNTAX  FcdrStatus
        ACCESS  read-write
        STATUS  mandatory
        DESCRIPTION
            "Value for FCDR 'Status' field that should be put in a CDR when an
            SM is not sent to an application (due to decimation or because a
            rule with an action to discard with ack has been applied). Default
            is 'submitted'."
        ::= { bilProfileEntry 31 }

    bilProfileFcdrMtSriOnlyStatus OBJECT-TYPE
        SYNTAX  FcdrStatus
        ACCESS  read-write
        STATUS  mandatory
        DESCRIPTION
            "Value for FCDR 'Status' field that should be put in a CDR when
            only a SRI_SM (SendRoutingInfoForSM) has been executed for a
            MT delivery attempt (AO-MT or MO-MT).
            Default is 'deleted'."
        ::= { bilProfileEntry 32 }

    bilProfileFcdrMtFailedStatus OBJECT-TYPE
        SYNTAX  FcdrStatus
        ACCESS  read-write
        STATUS  mandatory
        DESCRIPTION
            "Value for FCDR 'Status' field that should be put in a CDR when
            a MT delivery attempt has failed.
            Default is 'submitted'."
        ::= { bilProfileEntry 33 }

    bilProfileFcdrMtSuccessStatus OBJECT-TYPE
        SYNTAX  FcdrStatus
        ACCESS  read-write
        STATUS  mandatory
        DESCRIPTION
            "Value for FCDR 'Status' field that should be put in a CDR when
            a MT delivery attempt was successful.
            Default is 'delivered'."
        ::= { bilProfileEntry 34 }

    bilProfileFcdrUseAoConsolidationForAoAt  OBJECT-TYPE
        SYNTAX  Boolean
        ACCESS  read-write
        STATUS  mandatory
        DESCRIPTION
            "Indicator specifying whether the consolidation 
            field of the Originating Application (when true) 
            or of the Terminating Application (when false) 
            should be included in the CDR for AO-AT traffic. 
            The default value is false i.e. the Terminating 
            Application consolidation data is included."
        ::= { bilProfileEntry 35 }

    bilProfileFcdrFormatOrigAddressField OBJECT-TYPE
        SYNTAX  AddressFormat
        ACCESS  read-write
        STATUS  mandatory
        DESCRIPTION
            "Indicator specifying how the fields 'origAddress' should be
            specified in the CDR. Default is transparent, meaning that the
            address is taken from the SM without any modification."
        ::= { bilProfileEntry 41 }

    bilProfileFcdrFormatOrigAddressGsmField OBJECT-TYPE
        SYNTAX  AddressFormat
        ACCESS  read-write
        STATUS  mandatory
        DESCRIPTION
            "Indicator specifying how the fields 'origAddressGsm' should be
            specified in the CDR. Default is transparent, meaning that the
            address is taken from the SM without any modification."
        ::= { bilProfileEntry 42 }

    bilProfileFcdrFormatRecipAddressField OBJECT-TYPE
        SYNTAX  AddressFormat
        ACCESS  read-write
        STATUS  mandatory
        DESCRIPTION
            "Indicator specifying how the fields 'recipAddress' should be
            specified in the CDR. Default is transparent, meaning that the
            address is taken from the SM without any modification."
        ::= { bilProfileEntry 43 }

    bilProfileFcdrFormatRecipAddressGsmField OBJECT-TYPE
        SYNTAX  AddressFormat
        ACCESS  read-write
        STATUS  mandatory
        DESCRIPTION
            "Indicator specifying how the fields 'recipAddressGsm' should be
            specified in the CDR. Default is transparent, meaning that the
            address is taken from the SM without any modification."
        ::= { bilProfileEntry 44 }

    bilProfileFcdrFormatNotifAddressField OBJECT-TYPE
        SYNTAX  AddressFormat
        ACCESS  read-write
        STATUS  mandatory
        DESCRIPTION
            "Indicator specifying how the fields 'notifAddress' should be
            specified in the CDR. Default is transparent, meaning that the
            address is taken from the SM without any modification."
        ::= { bilProfileEntry 45 }

    bilProfileFcdrFormatNotifAddressGsmField OBJECT-TYPE
        SYNTAX  AddressFormat
        ACCESS  read-write
        STATUS  mandatory
        DESCRIPTION
            "Indicator specifying how the fields 'notifAddressGsm' should be
            specified in the CDR. Default is transparent, meaning that the
            address is taken from the SM without any modification."
        ::= { bilProfileEntry 46 }

    bilProfileFcdrFormatOgtiAddressField OBJECT-TYPE
        SYNTAX  AddressFormat
        ACCESS  read-write
        STATUS  mandatory
        DESCRIPTION
            "Indicator specifying how the fields 'ogtiAddress' should be
            specified in the CDR. Default is transparent, meaning that the
            address is taken from the SM without any modification."
        ::= { bilProfileEntry 47 }

    bilProfileFcdrFormatOgtiAddressGsmField OBJECT-TYPE
        SYNTAX  AddressFormat
        ACCESS  read-write
        STATUS  mandatory
        DESCRIPTION
            "Indicator specifying how the fields 'ogtiAddressGsm' should be
            specified in the CDR. Default is transparent, meaning that the
            address is taken from the SM without any modification."
        ::= { bilProfileEntry 48 }

    bilProfileFcdrFormatDgtiAddressField OBJECT-TYPE
        SYNTAX  AddressFormat
        ACCESS  read-write
        STATUS  mandatory
        DESCRIPTION
            "Indicator specifying how the fields 'dgtiAddress' should be
            specified in the CDR. Default is transparent, meaning that the
            address is taken from the SM without any modification."
        ::= { bilProfileEntry 49 }

    bilProfileFcdrFormatDgtiAddressGsmField OBJECT-TYPE
        SYNTAX  AddressFormat
        ACCESS  read-write
        STATUS  mandatory
        DESCRIPTION
            "Indicator specifying how the fields 'dgtiAddressGsm' should be
            specified in the CDR. Default is transparent, meaning that the
            address is taken from the SM without any modification."
        ::= { bilProfileEntry 50 }

    bilProfileFcdrFormatCallingLineIdField OBJECT-TYPE
        SYNTAX  AddressFormat
        ACCESS  read-write
        STATUS  mandatory
        DESCRIPTION
            "Indicator specifying how the fields 'callingLineIdGsm' should be
            specified in the CDR. Default is transparent, meaning that the
            address is taken from the SM without any modification."
        ::= { bilProfileEntry 51 }

    bilProfileFcdrFormatCallingLineIdGsmField OBJECT-TYPE
        SYNTAX  AddressFormat
        ACCESS  read-write
        STATUS  mandatory
        DESCRIPTION
            "Indicator specifying how the fields 'callingLineIdGsm' should be
            specified in the CDR. Default is transparent, meaning that the
            address is taken from the SM without any modification."
        ::= { bilProfileEntry 52 }

    bilProfileFcdrIncludeSubscriberStatusOfRecipientField OBJECT-TYPE
        SYNTAX  Boolean
        ACCESS  read-write
        STATUS  mandatory
        DESCRIPTION
            "Indicator specifying whether FCDR field
            'subscriberStatusOfRecipient' should be included in the
            CDR or not. By default, the field is excluded."
        ::= { bilProfileEntry 61 }

    bilProfileFcdrIncludePrepaidBillingStateOfRecipientField OBJECT-TYPE
        SYNTAX  Boolean
        ACCESS  read-write
        STATUS  mandatory
        DESCRIPTION
            "Indicator specifying whether FCDR field
            'prepaidBillingStateOfRecipient' should be included in the
            CDR or not. By default, the field is excluded."
        ::= { bilProfileEntry 62 }

    bilProfileFcdrIncludeOriginatorApplicationChargingUnitsField OBJECT-TYPE
        SYNTAX  Boolean
        ACCESS  read-write
        STATUS  mandatory
        DESCRIPTION
            "Indicator specifying whether FCDR field
            'originatorApplicationChargingUnits' should be included in the
            CDR or not. By default, the field is excluded."
        ::= { bilProfileEntry 63 }

    bilProfileFcdrIncludeRecipientApplicationChargingUnitsField OBJECT-TYPE
        SYNTAX  Boolean
        ACCESS  read-write
        STATUS  mandatory
        DESCRIPTION
            "Indicator specifying whether FCDR field
            'recipientApplicationChargingUnits' should be included in the
            CDR or not. By default, the field is excluded."
        ::= { bilProfileEntry 64 }

    bilProfileFcdrIncludeLangField  OBJECT-TYPE
        SYNTAX  Boolean
        ACCESS  read-write
        STATUS  mandatory
        DESCRIPTION
            "Indicator specifying whether FCDR field 'lang'
            should be included in the CDR or not.  
            By default, the field is excluded."
        ::= { bilProfileEntry 65 }

    bilProfileFcdrIncludeSmeReferenceField  OBJECT-TYPE
        SYNTAX  Boolean
        ACCESS  read-write
        STATUS  mandatory
        DESCRIPTION
            "Indicator specifying whether FCDR field 'smeReference'
            should be included in the CDR or not.  
            By default, the field is excluded."
        ::= { bilProfileEntry 66 }

    bilProfileFcdrIncludeSmsContentDcsField  OBJECT-TYPE
        SYNTAX  Boolean
        ACCESS  read-write
        STATUS  mandatory
        DESCRIPTION
            "Indicator specifying whether FCDR field 'smsContentDcs'
            should be included in the CDR or not.  
            By default, the field is excluded."
        ::= { bilProfileEntry 67 }

    bilProfileFcdrIncludeSmsContentsField  OBJECT-TYPE
        SYNTAX  Boolean
        ACCESS  read-write
        STATUS  mandatory
        DESCRIPTION
            "Indicator specifying whether FCDR field 'smsContents'
            should be included in the CDR or not.  
            By default, the field is excluded."
        ::= { bilProfileEntry 68 }

    bilProfileFcdrIncludeMessageReferenceField  OBJECT-TYPE
        SYNTAX  Boolean
        ACCESS  read-write
        STATUS  mandatory
        DESCRIPTION
            "Indicator specifying whether FCDR field 'messageReference'
            should be included in the CDR or not.  
            By default, the field is excluded."
        ::= { bilProfileEntry 69 }

    bilProfileFcdrIncludeOrigLasnField  OBJECT-TYPE
        SYNTAX  Boolean
        ACCESS  read-write
        STATUS  mandatory
        DESCRIPTION
            "Indicator specifying whether FCDR field 'origLasn'
            should be included in the CDR or not.  
            By default, the field is excluded."
        ::= { bilProfileEntry 70 }

    bilProfileFcdrIncludeRecipLasnField  OBJECT-TYPE
        SYNTAX  Boolean
        ACCESS  read-write
        STATUS  mandatory
        DESCRIPTION
            "Indicator specifying whether FCDR field 'recipLasn'
            should be included in the CDR or not.  
            By default, the field is excluded."
        ::= { bilProfileEntry 71 }

    bilProfileFcdrIncludeOrigMsgIdField  OBJECT-TYPE
        SYNTAX  Boolean
        ACCESS  read-write
        STATUS  mandatory
        DESCRIPTION
            "Indicator specifying whether FCDR field 'origMsgId'
            should be included in the CDR or not.  
            By default, the field is excluded."
        ::= { bilProfileEntry 72 }

    bilProfileFcdrIncludeServiceTypeField  OBJECT-TYPE
        SYNTAX  Boolean
        ACCESS  read-write
        STATUS  mandatory
        DESCRIPTION
            "Indicator specifying whether FCDR field 'serviceType'
            should be included in the CDR or not.  
            By default, the field is excluded."
        ::= { bilProfileEntry 73 }

    bilProfileFcdrIncludeUntranslOrigAddressField  OBJECT-TYPE
        SYNTAX  Boolean
        ACCESS  read-write
        STATUS  mandatory
        DESCRIPTION
            "Indicator specifying whether FCDR field 'untranslOrigAddress'
            should be included in the CDR or not.  
            By default, the field is excluded."
        ::= { bilProfileEntry 74 }

    bilProfileFcdrIncludeUntranslOrigAddressGsmField  OBJECT-TYPE
        SYNTAX  Boolean
        ACCESS  read-write
        STATUS  mandatory
        DESCRIPTION
            "Indicator specifying whether FCDR field 'untranslOrigAddressGsm'
            should be included in the CDR or not.  
            By default, the field is excluded."
        ::= { bilProfileEntry 75 }

    bilProfileFcdrIncludeUntranslRecipAddressField  OBJECT-TYPE
        SYNTAX  Boolean
        ACCESS  read-write
        STATUS  mandatory
        DESCRIPTION
            "Indicator specifying whether FCDR field 'untranslRecipAddress'
            should be included in the CDR or not.  
            By default, the field is excluded."
        ::= { bilProfileEntry 76 }

    bilProfileFcdrIncludeUntranslRecipAddressGsmField  OBJECT-TYPE
        SYNTAX  Boolean
        ACCESS  read-write
        STATUS  mandatory
        DESCRIPTION
            "Indicator specifying whether FCDR field 'untranslRecipAddressGsm'
            should be included in the CDR or not.  
            By default, the field is excluded."
        ::= { bilProfileEntry 77 }

    bilProfileFcdrIncludeTpDcsField  OBJECT-TYPE
        SYNTAX  Boolean
        ACCESS  read-write
        STATUS  mandatory
        DESCRIPTION
            "Indicator specifying whether FCDR field 'tpDcs' should be 
            included in the CDR or not.  
            By default, the field is excluded."
        ::= { bilProfileEntry 78 }

    bilProfileFcdrIncludeGenericUrgencyLevelField  OBJECT-TYPE
        SYNTAX  Boolean
        ACCESS  read-write
        STATUS  mandatory
        DESCRIPTION
            "Indicator specifying whether FCDR field 'genericUrgencyLevel'
            should be included in the CDR or not.  
            By default, the field is excluded."
        ::= { bilProfileEntry 79 }

    bilProfileFcdrIncludeFurnishChargingInfoField OBJECT-TYPE
        SYNTAX  Boolean
        ACCESS  read-write
        STATUS  mandatory
        DESCRIPTION
            "Indicator specifying whether FCDR field 'FurnishChargingInfo'
            should be included in the CDR or not.  Note that this field
            is not a field adopted by LogicaCMG, but a proprietary
            field defined by mBalance. By default, the field is excluded."
        ::= { bilProfileEntry 80 }

    bilProfileFcdrIncludeXsMessageTypeField  OBJECT-TYPE
        SYNTAX  Boolean
        ACCESS  read-write
        STATUS  mandatory
        DESCRIPTION
            "Indicator specifying whether FCDR field 'xsMessageType'
            should be included in the CDR or not.  Note that this field
            is not a field adopted by LogicaCMG, but a proprietary
            field defined by mBalance. By default, the field is excluded."
        ::= { bilProfileEntry 81 }

    bilProfileFcdrIncludeRecipientRoutingNumber OBJECT-TYPE
        SYNTAX  Boolean
        ACCESS  read-write
        STATUS  mandatory
        DESCRIPTION
            "Indicator specifying whether FCDR field 'RecipientRoutingNumber'
            should be included in the CDR or not.  Note that this field
            is not a field adopted by LogicaCMG, but a proprietary
            field defined by mBalance. By default, the field is excluded."
        ::= { bilProfileEntry 82 }

    bilProfileFcdrIncludeXsTieBillingIdField  OBJECT-TYPE
        SYNTAX  Boolean
        ACCESS  read-write
        STATUS  mandatory
        DESCRIPTION
            "Indicator specifying whether FCDR field 'xsTieBillingId'
            should be included in the CDR or not.  Note that this field
            is not a field adopted by LogicaCMG, but a proprietary
            field defined by mBalance. By default, the field is excluded."
        ::= { bilProfileEntry 83 }
    
    bilProfileFcdrIncludeSs8LastFailureReasonField  OBJECT-TYPE
        SYNTAX  Boolean
        ACCESS  read-write
        STATUS  mandatory
        DESCRIPTION
            "Indicator specifying whether FCDR field 'ss8LastFailureReason'
            should be included in the CDR or not.  Note that this field
            is not a field adopted by LogicaCMG, but a proprietary
            field defined by mBalance. By default, the field is excluded."
        ::= { bilProfileEntry 84 }
    
    bilProfileFcdrIncludeChargeInfoField OBJECT-TYPE
        SYNTAX  Boolean
        ACCESS  read-write
        STATUS  mandatory
        DESCRIPTION
            "Indicator specifying whether FCDR field 'chargeInfo'
            should be included in the CDR or not.  Note that this field
            is not a field adopted by LogicaCMG, but a proprietary
            field defined by mBalance. This field is only applicable
            when PBC is involved. By default, the field is excluded."
        ::= { bilProfileEntry 85 }

    bilProfileFcdrIncludeSubscriberStatusField OBJECT-TYPE
        SYNTAX  Boolean
        ACCESS  read-write
        STATUS  mandatory
        DESCRIPTION
            "Indicator specifying whether FCDR field 'subscriberStatus'
            should be included in the CDR or not.  Note that this field
            is not a field adopted by LogicaCMG, but a proprietary
            field defined by mBalance. This field is only applicable
            when PBC is involved. By default, the field is excluded."
        ::= { bilProfileEntry 86 }

    bilProfileFcdrIncludePrepaidResultCodeField OBJECT-TYPE
        SYNTAX  Boolean
        ACCESS  read-write
        STATUS  mandatory
        DESCRIPTION
            "Indicator specifying whether FCDR field 'prepaidResultCode'
            should be included in the CDR or not.  Note that this field
            is not a field adopted by LogicaCMG, but a proprietary
            field defined by mBalance. This field is only applicable
            when PBC is involved. By default, the field is excluded."
        ::= { bilProfileEntry 87 }

    bilProfileFcdrIncludePrepaidBillingStateField OBJECT-TYPE
        SYNTAX  Boolean
        ACCESS  read-write
        STATUS  mandatory
        DESCRIPTION
            "Indicator specifying whether FCDR field 'prepaidBillingState'
            should be included in the CDR or not.  Note that this field
            is not a field adopted by LogicaCMG, but a proprietary
            field defined by mBalance. This field is only applicable
            when PBC is involved. By default, the field is excluded."
        ::= { bilProfileEntry 88 }

    bilProfileFcdrIncludeSmscPresentationAddressField OBJECT-TYPE
        SYNTAX  Boolean
        ACCESS  read-write
        STATUS  mandatory
        DESCRIPTION
            "Indicator specifying whether FCDR field 'smscPresentationAddress'
            should be included in the CDR or not.  Note that this field
            is not a field adopted by LogicaCMG, but a proprietary
            field defined by mBalance. This field is only applicable
            for MT-MT path. By default, the field is excluded."
        ::= { bilProfileEntry 89 }

    bilProfileFcdrIncludeSmscPresentationAddressGsmField OBJECT-TYPE
        SYNTAX  Boolean
        ACCESS  read-write
        STATUS  mandatory
        DESCRIPTION
            "Indicator specifying whether FCDR field 
            'smscPresentationAddressGsm' should be included in the CDR or not.  
            Note that this field is not a field adopted by LogicaCMG, but a
            proprietary field defined by mBalance. This field is only
            applicable for MT-MT path. By default, the field is excluded."
        ::= { bilProfileEntry 90 }
    
    bilProfileFcdrIncludeOrglOrigAddressField OBJECT-TYPE
        SYNTAX  Boolean
        ACCESS  read-write
        STATUS  mandatory
        DESCRIPTION
            "Indicator specifying whether FCDR field 'orglOrigAddress'
            should be included in the CDR or not. By default, the
            field is included."
        ::= { bilProfileEntry 91 }

    bilProfileFcdrIncludeOrglOrigAddressGsmField OBJECT-TYPE
        SYNTAX  Boolean
        ACCESS  read-write
        STATUS  mandatory
        DESCRIPTION
            "Indicator specifying whether FCDR field 'orglOrigAddressGsm'
            should be included in the CDR or not. By default, the
            field is included."
        ::= { bilProfileEntry 92 }

    bilProfileFcdrIncludeOrglRecipAddressField OBJECT-TYPE
        SYNTAX  Boolean
        ACCESS  read-write
        STATUS  mandatory
        DESCRIPTION
            "Indicator specifying whether FCDR field 'orglRecipAddress'
            should be included in the CDR or not. By default, the
            field is included."
        ::= { bilProfileEntry 93 }

    bilProfileFcdrIncludeOrglRecipAddressGsmField OBJECT-TYPE
        SYNTAX  Boolean
        ACCESS  read-write
        STATUS  mandatory
        DESCRIPTION
            "Indicator specifying whether FCDR field 'orglRecipAddressGsm'
            should be included in the CDR or not. By default, the
            field is included."
        ::= { bilProfileEntry 94 }

    bilProfileFcdrIncludeOrglNotifAddressField OBJECT-TYPE
        SYNTAX  Boolean
        ACCESS  read-write
        STATUS  mandatory
        DESCRIPTION
            "Indicator specifying whether FCDR field 'orglNotifAddress'
            should be included in the CDR or not. By default, the
            field is included."
        ::= { bilProfileEntry 95 }

    bilProfileFcdrIncludeOrglNotifAddressGsmField OBJECT-TYPE
        SYNTAX  Boolean
        ACCESS  read-write
        STATUS  mandatory
        DESCRIPTION
            "Indicator specifying whether FCDR field 'orglNotifAddressGsm'
            should be included in the CDR or not. By default, the
            field is included."
        ::= { bilProfileEntry 96 }

    bilProfileFcdrIncludeExternalAttributesField OBJECT-TYPE
        SYNTAX  Boolean
        ACCESS  read-write
        STATUS  mandatory
        DESCRIPTION
            "Indicator specifying whether FCDR field 'externalAttributes'
            should be included in the CDR or not. Note that this field
            is not a field adopted by LogicaCMG, but a proprietary
            field defined by mBalance. This field is only applicable
            when an ECI application has specified has set or reset  
            attributes in the response. By default, the field is 
            excluded."
        ::= { bilProfileEntry 97 }

    bilProfileFcdrIncludeCimdPriorityField OBJECT-TYPE
        SYNTAX  Boolean
        ACCESS  read-write
        STATUS  mandatory
        DESCRIPTION
            "Indicator specifying whether FCDR field 'cimdPriority'
            should be included in the CDR or not. Note that this field
            is not a field adopted by LogicaCMG, but a proprietary
            field defined by mBalance. This field is only applicable
            for AO messages submitted by a CIMD application.
            By default, the field is excluded."
        ::= { bilProfileEntry 98 }

    bilProfileFcdrIncludeCimdServiceDescriptionField OBJECT-TYPE
        SYNTAX  Boolean
        ACCESS  read-write
        STATUS  mandatory
        DESCRIPTION
            "Indicator specifying whether FCDR field 'cimdServiceDescription'
            should be included in the CDR or not. Note that this field
            is not a field adopted by LogicaCMG, but a proprietary
            field defined by mBalance. This field is only applicable
            for AO messages submitted by a CIMD application.
            By default, the field is excluded."
        ::= { bilProfileEntry 99 }

    bilProfileFcdrIncludeCimdTariffClassField OBJECT-TYPE
        SYNTAX  Boolean
        ACCESS  read-write
        STATUS  mandatory
        DESCRIPTION
            "Indicator specifying whether FCDR field 'cimdTariffClass'
            should be included in the CDR or not. Note that this field
            is not a field adopted by LogicaCMG, but a proprietary
            field defined by mBalance. This field is only applicable
            for AO messages submitted by a CIMD application.
            By default, the field is excluded."
        ::= { bilProfileEntry 100 }

    bilProfileFcdrIncludeOrigAddressField OBJECT-TYPE
        SYNTAX  Boolean
        ACCESS  read-write
        STATUS  mandatory
        DESCRIPTION
            "Indicator specifying whether FCDR field 'origAddress'
            should be included in the CDR or not. By default, the
            field is included."
        ::= { bilProfileEntry 101 }

    bilProfileFcdrIncludeOrigAddressGsmField OBJECT-TYPE
        SYNTAX  Boolean
        ACCESS  read-write
        STATUS  mandatory
        DESCRIPTION
            "Indicator specifying whether FCDR field 'origAddressGsm'
            should be included in the CDR or not. By default, the
            field is included."
        ::= { bilProfileEntry 102 }

    bilProfileFcdrIncludeRecipAddressField OBJECT-TYPE
        SYNTAX  Boolean
        ACCESS  read-write
        STATUS  mandatory
        DESCRIPTION
            "Indicator specifying whether FCDR field 'recipAddress'
            should be included in the CDR or not. By default, the
            field is included."
        ::= { bilProfileEntry 103 }

    bilProfileFcdrIncludeRecipAddressGsmField OBJECT-TYPE
        SYNTAX  Boolean
        ACCESS  read-write
        STATUS  mandatory
        DESCRIPTION
            "Indicator specifying whether FCDR field 'recipAddressGsm'
            should be included in the CDR or not. By default, the
            field is included."
        ::= { bilProfileEntry 104 }

    bilProfileFcdrIncludeSubmitDateField OBJECT-TYPE
        SYNTAX  Boolean
        ACCESS  read-write
        STATUS  mandatory
        DESCRIPTION
            "Indicator specifying whether FCDR field 'submitDate'
            should be included in the CDR or not. By default, the
            field is excluded."
        ::= { bilProfileEntry 105 }

    bilProfileFcdrIncludeSubmitTimeField OBJECT-TYPE
        SYNTAX  Boolean
        ACCESS  read-write
        STATUS  mandatory
        DESCRIPTION
            "Indicator specifying whether FCDR field 'submitTime'
            should be included in the CDR or not. By default, the
            field is excluded."
        ::= { bilProfileEntry 106 }

    bilProfileFcdrIncludeStatusField OBJECT-TYPE
        SYNTAX  Boolean
        ACCESS  read-write
        STATUS  mandatory
        DESCRIPTION
            "Indicator specifying whether FCDR field 'Status'
            should be included in the CDR or not. By default, the
            field is included."
        ::= { bilProfileEntry 107 }

    bilProfileFcdrIncludeTerminDateField OBJECT-TYPE
        SYNTAX  Boolean
        ACCESS  read-write
        STATUS  mandatory
        DESCRIPTION
            "Indicator specifying whether FCDR field 'terminDate'
            should be included in the CDR or not. By default, the
            field is included."
        ::= { bilProfileEntry 108 }

    bilProfileFcdrIncludeTerminTimeField OBJECT-TYPE
        SYNTAX  Boolean
        ACCESS  read-write
        STATUS  mandatory
        DESCRIPTION
            "Indicator specifying whether FCDR field 'terminTime'
            should be included in the CDR or not. By default, the
            field is included."
        ::= { bilProfileEntry 109 }

    bilProfileFcdrIncludeLengthOfMessageField OBJECT-TYPE
        SYNTAX  Boolean
        ACCESS  read-write
        STATUS  mandatory
        DESCRIPTION
            "Indicator specifying whether FCDR field 'lengthOfMessage'
            should be included in the CDR or not. By default, the
            field is included."
        ::= { bilProfileEntry 110 }

    bilProfileFcdrIncludePrioIndicatorField OBJECT-TYPE
        SYNTAX  Boolean
        ACCESS  read-write
        STATUS  mandatory
        DESCRIPTION
            "Indicator specifying whether FCDR field 'prioIndicator'
            should be included in the CDR or not. By default, the
            field is included."
        ::= { bilProfileEntry 111 }

    bilProfileFcdrIncludeValidityPeriodField OBJECT-TYPE
        SYNTAX  Boolean
        ACCESS  read-write
        STATUS  mandatory
        DESCRIPTION
            "Indicator specifying whether FCDR field 'validityPeriod'
            should be included in the CDR or not. By default, the
            field is excluded."
        ::= { bilProfileEntry 112 }

    bilProfileFcdrIncludeDeferIndicatorField OBJECT-TYPE
        SYNTAX  Boolean
        ACCESS  read-write
        STATUS  mandatory
        DESCRIPTION
            "Indicator specifying whether FCDR field 'deferIndicator'
            should be included in the CDR or not. By default, the
            field is excluded."
        ::= { bilProfileEntry 113 }

    bilProfileFcdrIncludeDeferPeriodField OBJECT-TYPE
        SYNTAX  Boolean
        ACCESS  read-write
        STATUS  mandatory
        DESCRIPTION
            "Indicator specifying whether FCDR field 'deferPeriod'
            should be included in the CDR or not. By default, the
            field is excluded."
        ::= { bilProfileEntry 114 }

    bilProfileFcdrIncludeNotifIndicatorField OBJECT-TYPE
        SYNTAX  Boolean
        ACCESS  read-write
        STATUS  mandatory
        DESCRIPTION
            "Indicator specifying whether FCDR field 'notifIndicator'
            should be included in the CDR or not. By default, the
            field is included."
        ::= { bilProfileEntry 115 }

    bilProfileFcdrIncludeNotifAddressField OBJECT-TYPE
        SYNTAX  Boolean
        ACCESS  read-write
        STATUS  mandatory
        DESCRIPTION
            "Indicator specifying whether FCDR field 'notifAddress'
            should be included in the CDR or not. By default, the
            field is included."
        ::= { bilProfileEntry 116 }

    bilProfileFcdrIncludeNotifAddressGsmField OBJECT-TYPE
        SYNTAX  Boolean
        ACCESS  read-write
        STATUS  mandatory
        DESCRIPTION
            "Indicator specifying whether FCDR field 'notifAddressGsm'
            should be included in the CDR or not. By default, the
            field is included."
        ::= { bilProfileEntry 117 }

    bilProfileFcdrIncludeVsmscIdField OBJECT-TYPE
        SYNTAX  Boolean
        ACCESS  read-write
        STATUS  mandatory
        DESCRIPTION
            "Indicator specifying whether FCDR field 'vsmscId'
            should be included in the CDR or not. By default, the
            field is included."
        ::= { bilProfileEntry 118 }

    bilProfileFcdrIncludeVsmscTypeField OBJECT-TYPE
        SYNTAX  Boolean
        ACCESS  read-write
        STATUS  mandatory
        DESCRIPTION
            "Indicator specifying whether FCDR field 'vsmscType'
            should be included in the CDR or not. By default, the
            field is included."
        ::= { bilProfileEntry 119 }

    bilProfileFcdrIncludeDgtiAddressField OBJECT-TYPE
        SYNTAX  Boolean
        ACCESS  read-write
        STATUS  mandatory
        DESCRIPTION
            "Indicator specifying whether FCDR field 'dgtiAddress'
            should be included in the CDR or not. By default, the
            field is excluded."
        ::= { bilProfileEntry 120 }

    bilProfileFcdrIncludeDgtiAddressGsmField OBJECT-TYPE
        SYNTAX  Boolean
        ACCESS  read-write
        STATUS  mandatory
        DESCRIPTION
            "Indicator specifying whether FCDR field 'dgtiAddressGsm'
            should be included in the CDR or not. By default, the
            field is excluded."
        ::= { bilProfileEntry 121 }

    bilProfileFcdrIncludeDestPointCodeField OBJECT-TYPE
        SYNTAX  Boolean
        ACCESS  read-write
        STATUS  mandatory
        DESCRIPTION
            "Indicator specifying whether FCDR field 'destPointCode'
            should be included in the CDR or not. By default, the
            field is excluded."
        ::= { bilProfileEntry 122 }

    bilProfileFcdrIncludeOgtiAddressField OBJECT-TYPE
        SYNTAX  Boolean
        ACCESS  read-write
        STATUS  mandatory
        DESCRIPTION
            "Indicator specifying whether FCDR field 'ogtiAddress'
            should be included in the CDR or not. By default, the
            field is included."
        ::= { bilProfileEntry 123 }

    bilProfileFcdrIncludeOgtiAddressGsmField OBJECT-TYPE
        SYNTAX  Boolean
        ACCESS  read-write
        STATUS  mandatory
        DESCRIPTION
            "Indicator specifying whether FCDR field 'ogtiAddressGsm'
            should be included in the CDR or not. By default, the
            field is included."
        ::= { bilProfileEntry 124 }

    bilProfileFcdrIncludeOrigPointCodeField OBJECT-TYPE
        SYNTAX  Boolean
        ACCESS  read-write
        STATUS  mandatory
        DESCRIPTION
            "Indicator specifying whether FCDR field 'origPointCode'
            should be included in the CDR or not. By default, the
            field is included."
        ::= { bilProfileEntry 125 }

    bilProfileFcdrIncludeOrglSubmitDateField OBJECT-TYPE
        SYNTAX  Boolean
        ACCESS  read-write
        STATUS  mandatory
        DESCRIPTION
            "Indicator specifying whether FCDR field 'orglSubmitDate'
            should be included in the CDR or not. By default, the
            field is included."
        ::= { bilProfileEntry 126 }

    bilProfileFcdrIncludeOrglSubmitTimeField OBJECT-TYPE
        SYNTAX  Boolean
        ACCESS  read-write
        STATUS  mandatory
        DESCRIPTION
            "Indicator specifying whether FCDR field 'orglSubmitTime'
            should be included in the CDR or not. By default, the
            field is included."
        ::= { bilProfileEntry 127 }

    bilProfileFcdrIncludeTransparentPidField OBJECT-TYPE
        SYNTAX  Boolean
        ACCESS  read-write
        STATUS  mandatory
        DESCRIPTION
            "Indicator specifying whether FCDR field 'transparentPid'
            should be included in the CDR or not. By default, the
            field is included."
        ::= { bilProfileEntry 128 }

    bilProfileFcdrIncludeMesgReplyPathField OBJECT-TYPE
        SYNTAX  Boolean
        ACCESS  read-write
        STATUS  mandatory
        DESCRIPTION
            "Indicator specifying whether FCDR field 'mesgReplyPath'
            should be included in the CDR or not. By default, the
            field is included."
        ::= { bilProfileEntry 129 }

    bilProfileFcdrIncludeIntlMobileSubIdField OBJECT-TYPE
        SYNTAX  Boolean
        ACCESS  read-write
        STATUS  mandatory
        DESCRIPTION
            "Indicator specifying whether FCDR field 'intlMobileSubId'
            should be included in the CDR or not. By default, the
            field is excluded."
        ::= { bilProfileEntry 130 }

    bilProfileFcdrIncludeCallingLineIdField OBJECT-TYPE
        SYNTAX  Boolean
        ACCESS  read-write
        STATUS  mandatory
        DESCRIPTION
            "Indicator specifying whether FCDR field 'callingLineId'
            should be included in the CDR or not. By default, the
            field is excluded."
        ::= { bilProfileEntry 131 }

    bilProfileFcdrIncludeCallingLineIdGsmField OBJECT-TYPE
        SYNTAX  Boolean
        ACCESS  read-write
        STATUS  mandatory
        DESCRIPTION
            "Indicator specifying whether FCDR field 'callingLineIdGsm'
            should be included in the CDR or not. By default, the
            field is excluded."
        ::= { bilProfileEntry 132 }

    bilProfileFcdrIncludeConsolidationField OBJECT-TYPE
        SYNTAX  Boolean
        ACCESS  read-write
        STATUS  mandatory
        DESCRIPTION
            "Indicator specifying whether FCDR field 'consolidation'
            should be included in the CDR or not. By default, the
            field is included."
        ::= { bilProfileEntry 133 }

    bilProfileFcdrIncludePortNumberField OBJECT-TYPE
        SYNTAX  Boolean
        ACCESS  read-write
        STATUS  mandatory
        DESCRIPTION
            "Indicator specifying whether FCDR field 'portNumber'
            should be included in the CDR or not. By default, the
            field is included."
        ::= { bilProfileEntry 134 }

    bilProfileFcdrIncludeAserField OBJECT-TYPE
        SYNTAX  Boolean
        ACCESS  read-write
        STATUS  mandatory
        DESCRIPTION
            "Indicator specifying whether FCDR field 'aser'
            should be included in the CDR or not. By default, the
            field is excluded."
        ::= { bilProfileEntry 135 }

    bilProfileFcdrIncludeMserField OBJECT-TYPE
        SYNTAX  Boolean
        ACCESS  read-write
        STATUS  mandatory
        DESCRIPTION
            "Indicator specifying whether FCDR field 'mser'
            should be included in the CDR or not. By default, the
            field is excluded."
        ::= { bilProfileEntry 136 }

    bilProfileFcdrIncludeNserField OBJECT-TYPE
        SYNTAX  Boolean
        ACCESS  read-write
        STATUS  mandatory
        DESCRIPTION
            "Indicator specifying whether FCDR field 'nser'
            should be included in the CDR or not. By default, the
            field is excluded."
        ::= { bilProfileEntry 137 }

    bilProfileFcdrIncludeXserField OBJECT-TYPE
        SYNTAX  Boolean
        ACCESS  read-write
        STATUS  mandatory
        DESCRIPTION
            "Indicator specifying whether FCDR field 'xser'
            should be included in the CDR or not. By default, the
            field is excluded."
        ::= { bilProfileEntry 138 }

    bilProfileFcdrIncludeOrigIntlMobileSubIdField OBJECT-TYPE
        SYNTAX  Boolean
        ACCESS  read-write
        STATUS  mandatory
        DESCRIPTION
            "Indicator specifying whether FCDR field 'origIntlMobileSubId'
            should be included in the CDR or not. By default, the
            field is included."
        ::= { bilProfileEntry 139 }

    bilProfileFcdrIncludeBillIdField OBJECT-TYPE
        SYNTAX  Boolean
        ACCESS  read-write
        STATUS  mandatory
        DESCRIPTION
            "Indicator specifying whether FCDR field 'billId'
            should be included in the CDR or not. By default, the
            field is excluded."
        ::= { bilProfileEntry 140 }

    bilProfileFcdrIncludePpPserField OBJECT-TYPE
        SYNTAX  Boolean
        ACCESS  read-write
        STATUS  mandatory
        DESCRIPTION
            "Indicator specifying whether FCDR field 'ppPser' should be 
            included in the CDR or not. By default, the field is excluded."
        ::= { bilProfileEntry 143 }

    bilProfileFcdrIncludeCmReferenceNrField OBJECT-TYPE
        SYNTAX  Boolean
        ACCESS  read-write
        STATUS  mandatory
        DESCRIPTION
            "Indicator specifying whether FCDR field 'cmReferenceNr'
            should be included in the CDR or not.
            By default, the field is excluded."
        ::= { bilProfileEntry 151 }

    bilProfileFcdrIncludeCurrentSegmentField OBJECT-TYPE
        SYNTAX  Boolean
        ACCESS  read-write
        STATUS  mandatory
        DESCRIPTION
            "Indicator specifying whether FCDR field 'currentSegment'
            should be included in the CDR or not.
            By default, the field is excluded."
        ::= { bilProfileEntry 152 }

    bilProfileFcdrIncludeSegmentsTotalField OBJECT-TYPE
        SYNTAX  Boolean
        ACCESS  read-write
        STATUS  mandatory
        DESCRIPTION
            "Indicator specifying whether FCDR field 'segmentsTotal'
            should be included in the CDR or not.
            By default, the field is excluded."
        ::= { bilProfileEntry 153 }

    bilProfileFcdrIncludeDeliveryAttemptsField OBJECT-TYPE
        SYNTAX  Boolean
        ACCESS  read-write
        STATUS  mandatory
        DESCRIPTION
            "Indicator specifying whether FCDR field 'deliveryAttempts'
            should be included in the CDR or not.
            By default, the field is excluded."
        ::= { bilProfileEntry 183 }

    bilProfileFcdrAddressInformationIncludesMsisdnUtf8 OBJECT-TYPE
        SYNTAX  Boolean
        ACCESS  read-write
        STATUS  mandatory
        DESCRIPTION
            "Indicator specifying whether the FCDR fields of type 
            'address information' do contain a subordinate 'msisdnUTF8'
            field or not. By default, the fields are excluded."
        ::= { bilProfileEntry 199 }

    bilProfileNcdrFormatVersion OBJECT-TYPE
        SYNTAX  NcdrFormat
        ACCESS  read-write
        STATUS  mandatory
        DESCRIPTION
            "Specification of the format version to be used for creating the
            Nokia CDR files. Default is SC5B-CD3."
        ::= { bilProfileEntry 201 }

    bilProfileNcdrIncludeFormatVersion OBJECT-TYPE
        SYNTAX  Boolean
        ACCESS  read-write
        STATUS  mandatory
        DESCRIPTION
            "Flag indicating whether or not the format version is filled in
            in the header of the CDR blocks. Default is true."
        ::= { bilProfileEntry 202 }

    bilProfileNcdrCloseEmptyFile OBJECT-TYPE
        SYNTAX  Boolean
        ACCESS  read-write
        STATUS  mandatory
        DESCRIPTION
            "Flag indicating if empty CDR files, i.e. only containing header
            and trailer, should be closed. This happens when the
            MaxFileDuration expires without any traffic. Default is true."
        ::= { bilProfileEntry 203 }

    bilProfileNcdrUseGmtTimestamp OBJECT-TYPE
        SYNTAX  Boolean
        ACCESS  read-write
        STATUS  mandatory
        DESCRIPTION
            "Indicates whether or not the timestamps in the CDR records will
            be in GMT time. If set to false local time will be used.
            Default is false."
        ::= { bilProfileEntry 205 }

    bilProfileNcdrMinTariffClass OBJECT-TYPE
        SYNTAX  CimdTariffClass
        ACCESS  read-write
        STATUS  mandatory
        DESCRIPTION
            "Defines the threshold value for the tariff class. Only tariff
            class values that are equal to or greater than this value are
            included in the CDR recorded. Default is 0."
        ::= { bilProfileEntry 206 }

    bilProfileNcdrDefaultTariffClass OBJECT-TYPE
        SYNTAX  CimdTariffClass
        ACCESS  read-write
        STATUS  mandatory
        DESCRIPTION
            "Defines the default value for the tariff class used for
            creating CDR records.
            Default is 1."
        ::= { bilProfileEntry 207 }

    bilProfileNcdrDefaultServiceDescription OBJECT-TYPE
        SYNTAX  CimdServiceDescription
        ACCESS  read-write
        STATUS  mandatory
        DESCRIPTION
            "Defines the default value for the service description used for
            creating CDR records.
            Default is 1."
        ::= { bilProfileEntry 208 }

    bilProfileNcdrFallbackTariffClass OBJECT-TYPE
        SYNTAX  CimdTariffClass
        ACCESS  read-write
        STATUS  mandatory
        DESCRIPTION
            "Defines the value for the tariff class used for creating
            CDR records for messages that have been delivered through
            the fallback leg of a routing path. Default is 0."
        ::= { bilProfileEntry 209 }

    bilProfileNcdrRecordTypeSubmit OBJECT-TYPE
        SYNTAX  NcdrRecordType
        ACCESS  read-write
        STATUS  mandatory
        DESCRIPTION
            "Defines the value written in the record_type field of the CDR
            record for Submit events. When zero the event is not included.
            The value should not overlap with any of the other RecordType
            fields. Default is 1."
        ::= { bilProfileEntry 221 }

    bilProfileNcdrRecordTypeDeliver OBJECT-TYPE
        SYNTAX  NcdrRecordType
        ACCESS  read-write
        STATUS  mandatory
        DESCRIPTION
            "Defines the value written in the record_type field of the CDR
            record for Deliver events. When zero the event is not included.
            The value should not overlap with any of the other RecordType
            fields. Default is 2."
        ::= { bilProfileEntry 222 }

    bilProfileNcdrRecordTypeReceive OBJECT-TYPE
        SYNTAX  NcdrRecordType
        ACCESS  read-write
        STATUS  mandatory
        DESCRIPTION
            "Defines the value written in the record_type field of the CDR
            record for Receive events. When zero the event is not included.
            The value should not overlap with any of the other RecordType
            fields. Default is 3."
        ::= { bilProfileEntry 223 }

    bilProfileNcdrRecordTypeDeleted OBJECT-TYPE
        SYNTAX  NcdrRecordType
        ACCESS  read-write
        STATUS  mandatory
        DESCRIPTION
            "Defines the value written in the record_type field of the CDR
            record for Deleted events. When zero the event is not included.
            The value should not overlap with any of the other RecordType
            fields. Default is 4."
        ::= { bilProfileEntry 224 }

    bilProfileNcdrRecordTypeStatus1 OBJECT-TYPE
        SYNTAX  NcdrRecordType
        ACCESS  read-write
        STATUS  mandatory
        DESCRIPTION
            "Defines the value written in the record_type field of the CDR
            record for Status1 events. When zero the event is not included.
            The value should not overlap with any of the other RecordType
            fields. Default is 7."
        ::= { bilProfileEntry 227 }

    bilProfileNcdrRecordTypeStatus2 OBJECT-TYPE
        SYNTAX  NcdrRecordType
        ACCESS  read-write
        STATUS  mandatory
        DESCRIPTION
            "Defines the value written in the record_type field of the CDR
            record for Status2 events. When zero the event is not included.
            The value should not overlap with any of the other RecordType
            fields. Default is 8."
        ::= { bilProfileEntry 228 }

    bilProfileNcdrRecordTypeExpired OBJECT-TYPE
        SYNTAX  NcdrRecordType
        ACCESS  read-write
        STATUS  mandatory
        DESCRIPTION
            "Defines the value written in the record_type field of the CDR
            record for Status2 events. When zero the event is not included.
            The value should not overlap with any of the other RecordType
            fields. Default is 9."
        ::= { bilProfileEntry 229 }

    bilProfileEcdrRecordType OBJECT-TYPE
        SYNTAX  EcdrRecordType
        ACCESS  read-write
        STATUS  mandatory
        DESCRIPTION
            "Specifies which Ericsson CDR type should be used. Defaults to 
            'msOriginatingSmsInSmsIwMsc'."
        ::= { bilProfileEntry 301 }

    bilProfileEcdrTacTsc OBJECT-TYPE
        SYNTAX  EcdrTsc
        ACCESS  read-write
        STATUS  mandatory
        DESCRIPTION
            "Specifies the value to be used for the TSC subfield within the
            TAC field of an Ericsson CDR. Defaults to 3."
        ::= { bilProfileEntry 302 }

    bilProfileEcdrTacTos OBJECT-TYPE
        SYNTAX  EcdrTos
        ACCESS  read-write
        STATUS  mandatory
        DESCRIPTION
            "Specifies the value to be used for the TOS subfield within the
            TAC field of an Ericsson CDR. Defaults to 2."
        ::= { bilProfileEntry 303 }

    bilProfileEcdrTacToi OBJECT-TYPE
        SYNTAX  EcdrToi
        ACCESS  read-write
        STATUS  mandatory
        DESCRIPTION
            "Specifies the value to be used for the TOI subfield within the
            TAC field of an Ericsson CDR.  Defaults to 9."
        ::= { bilProfileEntry 304 }

    bilProfileEcdrTypeOfCallingSubscriber OBJECT-TYPE
        SYNTAX  EcdrTypeOfCallingSubscriber
        ACCESS  read-write
        STATUS  mandatory
        DESCRIPTION
            "Specifies the value to be used for the TypeOfCallingSubscriber 
            field of an Ericsson CDR. Defaults to 1."
        ::= { bilProfileEntry 305 }

    bilProfileEcdrChargedParty OBJECT-TYPE
        SYNTAX  EcdrChargedParty
        ACCESS  read-write
        STATUS  mandatory
        DESCRIPTION
            "Specifies the value to be used for the ChargedParty field of an 
            Ericsson CDR. Defaults to 'chargingOfCallingSubscriber'."
        ::= { bilProfileEntry 306 }

    bilProfileEcdrOriginForCharging OBJECT-TYPE
        SYNTAX  EcdrOriginForCharging
        ACCESS  read-write
        STATUS  mandatory
        DESCRIPTION
            "Specifies the value to be used for the originForCharging field
            of an Ericsson CDR. Defaults to 0."
        ::= { bilProfileEntry 307 }

    bilProfileEcdrExchangeIdentity OBJECT-TYPE
        SYNTAX  EcdrExchangeIdentity
        ACCESS  read-write
        STATUS  mandatory
        DESCRIPTION
            "Specifies the value to be used for the exchangeIdentity field of
            an Ericsson CDR. Defaults to 'MSC'."
        ::= { bilProfileEntry 308 }

    bilProfileEcdrIncomingRoute OBJECT-TYPE
        SYNTAX  EcdrRoute
        ACCESS  read-write
        STATUS  mandatory
        DESCRIPTION
            "Specifies the value to be used for the incomingRoute field of an 
            Ericsson CDR. Defaults to 'ROUTE'."
        ::= { bilProfileEntry 309 }

    bilProfileEcdrOutgoingRoute OBJECT-TYPE
        SYNTAX  EcdrRoute
        ACCESS  read-write
        STATUS  mandatory
        DESCRIPTION
            "Specifies the value to be used for the outgoingRoute field of an 
            Ericsson CDR. Defaults to 'ROUTE'."
        ::= { bilProfileEntry 310 }

    bilProfileEcdrGsmTeleServiceCode OBJECT-TYPE
        SYNTAX  EcdrGsmTeleServiceCode
        ACCESS  read-write
        STATUS  mandatory
        DESCRIPTION
            "Specifies the value to be used for the gsmTeleServiceCode field
            of an Ericsson CDR. Defaults to 'moSms'."
        ::= { bilProfileEntry 311 }

    bilProfileEcdrIncludeTacField OBJECT-TYPE
        SYNTAX  Boolean
        ACCESS  read-write
        STATUS  mandatory
        DESCRIPTION
            "Indicator specifying whether Ericsson CDR field 'Tac' should be 
            included in the CDR or not. By default, the field is included."
        ::= { bilProfileEntry 331 }

    bilProfileEcdrIncludeCallIdentificationNumberField OBJECT-TYPE
        SYNTAX  Boolean
        ACCESS  read-write
        STATUS  mandatory
        DESCRIPTION
            "Indicator specifying whether Ericsson CDR field 
            'CallIdentificationNumber' should be included in the CDR or not. 
            By default, the field is included."
        ::= { bilProfileEntry 332 }

    bilProfileEcdrIncludeRecordSequenceNumberField OBJECT-TYPE
        SYNTAX  Boolean
        ACCESS  read-write
        STATUS  mandatory
        DESCRIPTION
            "Indicator specifying whether Ericsson CDR field 
            'RecordSequenceNumber' should be included in the CDR or not. 
            By default, the field is included."
        ::= { bilProfileEntry 333 }

    bilProfileEcdrIncludeTypeOfCallingSubscriberField OBJECT-TYPE
        SYNTAX  Boolean
        ACCESS  read-write
        STATUS  mandatory
        DESCRIPTION
            "Indicator specifying whether Ericsson CDR field 
            'TypeOfCallingSubscriber' should be included in the CDR or not. 
            By default, the field is included. This field is only applicable 
            for record type 'msOriginatingSmsInMsc'."
        ::= { bilProfileEntry 334 }

    bilProfileEcdrIncludeCallingPartyNumberField OBJECT-TYPE
        SYNTAX  Boolean
        ACCESS  read-write
        STATUS  mandatory
        DESCRIPTION
            "Indicator specifying whether Ericsson CDR field 
            'CallingPartyNumber' should be included in the CDR or not. 
            By default, the field is included. This field is only applicable 
            for record types 'msOriginatingSmsInMsc' and 
            'msOriginatingSmsInSmsIwMsc'."
        ::= { bilProfileEntry 335 }

    bilProfileEcdrIncludeCallingSubscriberImsiField OBJECT-TYPE
        SYNTAX  Boolean
        ACCESS  read-write
        STATUS  mandatory
        DESCRIPTION
            "Indicator specifying whether Ericsson CDR field 
            'CallingSubscriberImsi' should be included in the CDR or not. 
            By default, the field is included. This field is only applicable 
            for record type 'msOriginatingSmsInMsc'."
        ::= { bilProfileEntry 336 }


    bilProfileEcdrIncludeCalledPartyNumberField OBJECT-TYPE
        SYNTAX  Boolean
        ACCESS  read-write
        STATUS  mandatory
        DESCRIPTION
            "Indicator specifying whether Ericsson CDR field
            'CalledPartyNumber' should be included in the CDR or not. By
            default, the field is included. This field is only applicable for
            record types 'msTerminatingSmsInMsc' and
            'msTerminatingSmsInSmsGmsc'."
        ::= { bilProfileEntry 337 }

    bilProfileEcdrIncludeCalledSubscriberImsiField OBJECT-TYPE
        SYNTAX  Boolean
        ACCESS  read-write
        STATUS  mandatory
        DESCRIPTION
            "Indicator specifying whether Ericsson CDR field 'CalledPartyImsi'
            should be included in the CDR or not. By default, the field is 
            included. This field is only applicable for record types 
            'msTerminatingSmsInMsc' and 'msTerminatingSmsInSmsGmsc'."
        ::= { bilProfileEntry 338 }
        
    bilProfileEcdrIncludeDateForStartOfChargeField OBJECT-TYPE
        SYNTAX  Boolean
        ACCESS  read-write
        STATUS  mandatory
        DESCRIPTION
            "Indicator specifying whether Ericsson CDR field 
            'DateForStartOfCharge' should be included in the CDR or not. 
            By default, the field is included."
        ::= { bilProfileEntry 339 }

    bilProfileEcdrIncludeTimeForStartOfChargeField OBJECT-TYPE
        SYNTAX  Boolean
        ACCESS  read-write
        STATUS  mandatory
        DESCRIPTION
            "Indicator specifying whether Ericsson CDR field 
            'TimeForStartOfCharge' should be included in the CDR or not. 
            By default, the field is included."
        ::= { bilProfileEntry 340 }

    bilProfileEcdrIncludeChargedPartyField OBJECT-TYPE
        SYNTAX  Boolean
        ACCESS  read-write
        STATUS  mandatory
        DESCRIPTION
            "Indicator specifying whether Ericsson CDR field 'ChargedParty' 
            should be included in the CDR or not. By default, the field is 
            included."
        ::= { bilProfileEntry 341 }

    bilProfileEcdrIncludeOriginForChargingField OBJECT-TYPE
        SYNTAX  Boolean
        ACCESS  read-write
        STATUS  mandatory
        DESCRIPTION
            "Indicator specifying whether Ericsson CDR field
            'OriginForCharging' should be included in the CDR or not. By
            default, the field is included. This field is only applicable for
            record types 'msOriginatingSmsInMsc' and 'msTerminatingSmsInMsc'
            ."
        ::= { bilProfileEntry 342 }

    bilProfileEcdrIncludeExchangeIdentityField OBJECT-TYPE
        SYNTAX  Boolean
        ACCESS  read-write
        STATUS  mandatory
        DESCRIPTION
            "Indicator specifying whether Ericsson CDR field
            'ExchangeIdentity' should be included in the CDR or not. By
            default, the field is included."
        ::= { bilProfileEntry 343 }

    bilProfileEcdrIncludeMscIdentificationField OBJECT-TYPE
        SYNTAX  Boolean
        ACCESS  read-write
        STATUS  mandatory
        DESCRIPTION
            "Indicator specifying whether Ericsson CDR field
            'MscIdentification' should be included in the CDR or not. By
            default, the field is included."
        ::= { bilProfileEntry 344 }

    bilProfileEcdrIncludeIncomingRouteField OBJECT-TYPE
        SYNTAX  Boolean
        ACCESS  read-write
        STATUS  mandatory
        DESCRIPTION
            "Indicator specifying whether Ericsson CDR field 'IncomingRoute' 
            should be included in the CDR or not. By default, the field is 
            included. This field is only applicable for record type 
            'msOriginatingSmsInMsc' "
        ::= { bilProfileEntry 345 }

    bilProfileEcdrIncludeOutgoingRouteField OBJECT-TYPE
        SYNTAX  Boolean
        ACCESS  read-write
        STATUS  mandatory
        DESCRIPTION
            "Indicator specifying whether Ericsson CDR field 'OutgoingRoute' 
            should be included in the CDR or not. By default, the field is 
            included. This field is only applicable for record type
            'msTerminatingSmsInMsc'."
        ::= { bilProfileEntry 346 }

    bilProfileEcdrIncludeGsmTeleServiceCodeField OBJECT-TYPE
        SYNTAX  Boolean
        ACCESS  read-write
        STATUS  mandatory
        DESCRIPTION
            "Indicator specifying whether Ericsson CDR field 
            'GsmTeleServiceCode' should be included in the CDR or not. By 
            default, the field is included."
        ::= { bilProfileEntry 347 }

    bilProfileEcdrIncludeServiceCentreAddressField OBJECT-TYPE
        SYNTAX  Boolean
        ACCESS  read-write
        STATUS  mandatory
        DESCRIPTION
            "Indicator specifying whether Ericsson CDR field 
            'ServiceCentreAddress' should be included in the CDR or not. By 
            default, the field is included."
        ::= { bilProfileEntry 348 }

    bilProfileEcdrIncludeMscNumberField OBJECT-TYPE
        SYNTAX  Boolean
        ACCESS  read-write
        STATUS  mandatory
        DESCRIPTION
            "Indicator specifying whether Ericsson CDR field 'MscNumber'
            should be included in the CDR or not. By default, the field is
            included.  This field is only applicable for record types
            'msTerminatingSmsInSmsGmsc'."
        ::= { bilProfileEntry 349 }

    bilProfileCcdrIncludeProprietaryPrepaidIndicator OBJECT-TYPE
        SYNTAX  Boolean
        ACCESS  read-write
        STATUS  mandatory
        DESCRIPTION
            "Indicator specifying whether Comverse CDR field 'saOptionsCharN' 
            should contain the proprietary prepaid indicator. By default,  
            'saOptionsCharN' dos no contain the proprietary prepaid 
            indicator."
        ::= { bilProfileEntry 401 }

    bilProfileCcdrIncludeDiameterDetails OBJECT-TYPE
        SYNTAX  Boolean
        ACCESS  read-write
        STATUS  mandatory
        DESCRIPTION
            "Indicator specifying whether Comverse CDR should be extended
            with a proprietary field for Diameter Details. By default, the
            field is not included."
        ::= { bilProfileEntry 402 }

    bilProfileCopy1OfFinishedDirectory OBJECT-TYPE
        SYNTAX  FileSpec
        ACCESS  read-write
        STATUS  mandatory
        DESCRIPTION
            "Specification of a directory in which to create hard links to
            the finished billing files. A hard link is created at the time
            that the billing file is moved from the processing directory to
            the finished directory. 
            The default for this specification is a zero-length string, which 
            implies that no hard links are to be created.
            When a directory is specified, it should reside on the same disc
            partition as the bilProfileProcessingDirectory and 
            bilProfileFinishedDirectory.
            Note: this setting can only be changed when the device adminState 
            is disabled."
        ::= { bilProfileEntry 501 }

    bilProfileCopy2OfFinishedDirectory OBJECT-TYPE
        SYNTAX  FileSpec
        ACCESS  read-write
        STATUS  mandatory
        DESCRIPTION
            "Specification of a directory in which to create hard links to the 
            finished billing files. A hard link is created at the time that
            the billing file is moved from the processing directory to the 
            finished directory. 
            The default for this specification is a zero-length string, which 
            implies that no hard links are to be created.
            When a directory is specified, it should reside on the same disc
            partition as the bilProfileProcessingDirectory and 
            bilProfileFinishedDirectory.
            Note: this setting can only be changed when the device adminState 
            is disabled."
        ::= { bilProfileEntry 502 }

    bilProfileCopy3OfFinishedDirectory OBJECT-TYPE
        SYNTAX  FileSpec
        ACCESS  read-write
        STATUS  mandatory
        DESCRIPTION
            "Specification of a directory in which to create hard links to the 
            finished billing files. A hard link is created at the time that
            the billing file is moved from the processing directory to the 
            finished directory. 
            The default for this specification is a zero-length string, which 
            implies that no hard links are to be created.
            When a directory is specified, it should reside on the same disc
            partition as the bilProfileProcessingDirectory and 
            bilProfileFinishedDirectory.
            Note: this setting can only be changed when the device adminState 
            is disabled."
        ::= { bilProfileEntry 503 }

    bilProfileCopy4OfFinishedDirectory OBJECT-TYPE
        SYNTAX  FileSpec
        ACCESS  read-write
        STATUS  mandatory
        DESCRIPTION
            "Specification of a directory in which to create hard links to the 
            finished billing files. A hard link is created at the time that
            the billing file is moved from the processing directory to the 
            finished directory. 
            The default for this specification is a zero-length string, which 
            implies that no hard links are to be created.
            When a directory is specified, it should reside on the same disc
            partition as the bilProfileProcessingDirectory and 
            bilProfileFinishedDirectory.
            Note: this setting can only be changed when the device adminState 
            is disabled."
        ::= { bilProfileEntry 504 }

    bilProfileCopy5OfFinishedDirectory OBJECT-TYPE
        SYNTAX  FileSpec
        ACCESS  read-write
        STATUS  mandatory
        DESCRIPTION
            "Specification of a directory in which to create hard links to
            the finished billing files. A hard link is created at the time
            that the billing file is moved from the processing directory to
            the finished directory. 
            The default for this specification is a zero-length string, which 
            implies that no hard links are to be created.
            When a directory is specified, it should reside on the same disc
            partition as the bilProfileProcessingDirectory and 
            bilProfileFinishedDirectory.
            Note: this setting can only be changed when the device adminState
            is disabled."
        ::= { bilProfileEntry 505 }

    bilProfileCopy6OfFinishedDirectory OBJECT-TYPE
        SYNTAX  FileSpec
        ACCESS  read-write
        STATUS  mandatory
        DESCRIPTION
            "Specification of a directory in which to create hard links to the 
            finished billing files. A hard link is created at the time that
            the billing file is moved from the processing directory to the 
            finished directory. 
            The default for this specification is a zero-length string, which 
            implies that no hard links are to be created.
            When a directory is specified, it should reside on the same disc
            partition as the bilProfileProcessingDirectory and 
            bilProfileFinishedDirectory.
            Note: this setting can only be changed when the device adminState
            is disabled."
        ::= { bilProfileEntry 506 }

    bilProfileCopy7OfFinishedDirectory OBJECT-TYPE
        SYNTAX  FileSpec
        ACCESS  read-write
        STATUS  mandatory
        DESCRIPTION
            "Specification of a directory in which to create hard links to
            the finished billing files. A hard link is created at the time
            that the billing file is moved from the processing directory to
            the finished directory. 
            The default for this specification is a zero-length string, which 
            implies that no hard links are to be created.
            When a directory is specified, it should reside on the same disc
            partition as the bilProfileProcessingDirectory and 
            bilProfileFinishedDirectory.
            Note: this setting can only be changed when the device adminState
            is disabled."
        ::= { bilProfileEntry 507 }

    bilProfileCopy8OfFinishedDirectory OBJECT-TYPE
        SYNTAX  FileSpec
        ACCESS  read-write
        STATUS  mandatory
        DESCRIPTION
            "Specification of a directory in which to create hard links to
            the finished billing files. A hard link is created at the time
            that the billing file is moved from the processing directory to
            the finished directory. 
            The default for this specification is a zero-length string, which 
            implies that no hard links are to be created.
            When a directory is specified, it should reside on the same disc
            partition as the bilProfileProcessingDirectory and 
            bilProfileFinishedDirectory.
            Note: this setting can only be changed when the device adminState
            is disabled."
        ::= { bilProfileEntry 508 }

    bilProfileCopy9OfFinishedDirectory OBJECT-TYPE
        SYNTAX  FileSpec
        ACCESS  read-write
        STATUS  mandatory
        DESCRIPTION
            "Specification of a directory in which to create hard links to
            the finished billing files. A hard link is created at the time
            that the billing file is moved from the processing directory to
            the finished directory. 
            The default for this specification is a zero-length string, which 
            implies that no hard links are to be created.
            When a directory is specified, it should reside on the same disc
            partition as the bilProfileProcessingDirectory and 
            bilProfileFinishedDirectory.
            Note: this setting can only be changed when the device adminState
            is disabled."
        ::= { bilProfileEntry 509 }

    bilProfileScdrIncludeSmField OBJECT-TYPE
        SYNTAX  Boolean
        ACCESS  read-write
        STATUS  mandatory
        DESCRIPTION
            "Indicator specifying whether the SS8 CDR contain the
            the SM field or not. By default, this field is empty
            for privacy reasons, but it can be enabled by setting
            this variable to true."
        ::= { bilProfileEntry 601 }

    bilProfileLcdrCustomFormat OBJECT-TYPE
        SYNTAX  LcdrCustomFormat
        ACCESS  read-write
        STATUS  mandatory
        DESCRIPTION
            "Defines sequence and presence of CDR fields in the LCDR generated
            Default string is
            
            @201@3@5@10@11@12@13@14@15@16@17@20@91@202@203@83
            "
        ::= { bilProfileEntry 611 }

    cdpaBasedMoForwardingCounters OBJECT IDENTIFIER ::= { sms 106 }

    cdpaBasedMoForwardingTotalCounter OBJECT-TYPE
        SYNTAX  Counter
        ACCESS  read-write
        STATUS  mandatory
        DESCRIPTION
            "Counter specifying the number of times a cdpa-based
            MO forwarding attempt was made."
        ::= { cdpaBasedMoForwardingCounters 1 }

    cdpaBasedMoForwardingSuccessCounter OBJECT-TYPE
        SYNTAX  Counter
        ACCESS  read-write
        STATUS  mandatory
        DESCRIPTION
            "Counter specifying the number of times a cdpa-based
            MO forwarding attempt was successful."
        ::= { cdpaBasedMoForwardingCounters 2 }

    cdpaBasedMoForwardingTimeoutCounter OBJECT-TYPE
        SYNTAX  Counter
        ACCESS  read-write
        STATUS  mandatory
        DESCRIPTION
            "Counter specifying the number of times a cdpa-based
            MO forwarding attempt timed out."
        ::= { cdpaBasedMoForwardingCounters 3 }

    cdpaBasedMoForwardingSccpAbortCounter OBJECT-TYPE
        SYNTAX  Counter
        ACCESS  read-write
        STATUS  mandatory
        DESCRIPTION
            "Counter specifying the number of times a cdpa-based
            MO forwarding attempt resulted in an SCCP abort."
        ::= { cdpaBasedMoForwardingCounters 4 }

    cdpaBasedMoForwardingTcapAbortCounter OBJECT-TYPE
        SYNTAX  Counter
        ACCESS  read-write
        STATUS  mandatory
        DESCRIPTION
            "Counter specifying the number of times a cdpa-based
            MO forwarding attempt resulted in a TCAP abort."
        ::= { cdpaBasedMoForwardingCounters 5 }

    cdpaBasedMoForwardingUnknownResultCounter OBJECT-TYPE
        SYNTAX  Counter
        ACCESS  read-write
        STATUS  mandatory
        DESCRIPTION
            "Counter specifying the number of times a cdpa-based
            MO forwarding attempt was made using transparent routing,
            in which case the forwarding result is unknown."
        ::= { cdpaBasedMoForwardingCounters 6 }

    cdpaBasedMoForwardingSysFailErrorCounter OBJECT-TYPE
        SYNTAX  Counter
        ACCESS  read-write
        STATUS  mandatory
        DESCRIPTION
            "Counter specifying the number of times a cdpa-based
            MO forwarding attempt resulted in the SMSC returning a
            systemFailure error."
        ::= { cdpaBasedMoForwardingCounters 7 }

    cdpaBasedMoForwardingDataMisErrorCounter OBJECT-TYPE
        SYNTAX  Counter
        ACCESS  read-write
        STATUS  mandatory
        DESCRIPTION
            "Counter specifying the number of times a cdpa-based
            MO forwarding attempt resulted in the SMSC returning a
            dataMissing error."
        ::= { cdpaBasedMoForwardingCounters 8 }

    cdpaBasedMoForwardingUnexpDataValErrorCounter OBJECT-TYPE
        SYNTAX  Counter
        ACCESS  read-write
        STATUS  mandatory
        DESCRIPTION
            "Counter specifying the number of times a cdpa-based
            MO forwarding attempt resulted in the SMSC returning a
            unexpectedDataValue error."
        ::= { cdpaBasedMoForwardingCounters 9 }

    cdpaBasedMoForwardingFacNotSuppErrorCounter OBJECT-TYPE
        SYNTAX  Counter
        ACCESS  read-write
        STATUS  mandatory
        DESCRIPTION
            "Counter specifying the number of times a cdpa-based
            MO forwarding attempt resulted in the SMSC returning a
            facilityNotSupported error."
        ::= { cdpaBasedMoForwardingCounters 10 }

    cdpaBasedMoForwardingUnkScErrorCounter OBJECT-TYPE
        SYNTAX  Counter
        ACCESS  read-write
        STATUS  mandatory
        DESCRIPTION
            "Counter specifying the number of times a cdpa-based
            MO forwarding attempt resulted in the SMSC returning a
            unknownServiceCentre error."
        ::= { cdpaBasedMoForwardingCounters 11 }

    cdpaBasedMoForwardingScCongErrorCounter OBJECT-TYPE
        SYNTAX  Counter
        ACCESS  read-write
        STATUS  mandatory
        DESCRIPTION
            "Counter specifying the number of times a cdpa-based
            MO forwarding attempt resulted in the SMSC returning a
            serviceCentreCongested error."
        ::= { cdpaBasedMoForwardingCounters 12 }

    cdpaBasedMoForwardingInvSmeAddrErrorCounter OBJECT-TYPE
        SYNTAX  Counter
        ACCESS  read-write
        STATUS  mandatory
        DESCRIPTION
            "Counter specifying the number of times a cdpa-based
            MO forwarding attempt resulted in the SMSC returning a
            invalidSmeAddress error."
        ::= { cdpaBasedMoForwardingCounters 13 }

    cdpaBasedMoForwardingSubNotScSubErrorCounter OBJECT-TYPE
        SYNTAX  Counter
        ACCESS  read-write
        STATUS  mandatory
        DESCRIPTION
            "Counter specifying the number of times a cdpa-based
            MO forwarding attempt resulted in the SMSC returning a
            subscriberNotScSubscriber error."
        ::= { cdpaBasedMoForwardingCounters 14 }

    cdpaBasedMoForwardingOtherErrorsCounter OBJECT-TYPE
        SYNTAX  Counter
        ACCESS  read-write
        STATUS  mandatory
        DESCRIPTION
            "Counter specifying the number of times a cdpa-based
            MO forwarding attempt resulted in an error other than the
            errors specified above."
        ::= { cdpaBasedMoForwardingCounters 15 }

    cpyProperties OBJECT IDENTIFIER ::= { sms 111 }
    
    cpyPropRestrictCopyingToOwnSubscriberBase OBJECT-TYPE 
        SYNTAX  Boolean
        ACCESS  read-write
        STATUS  mandatory
        DESCRIPTION
            "Indicator specifying whether the copying should only be done when
             the destination belongs to HPLMN. Default of this setting is 
             'true'.
             
             Enabling copying outside the HPLMN opens up the possibility of 
             copy loops. As a result of copy loops, the TextPass RTR (and even 
             the whole HPLMN) may become inoperable. As such, it strongly 
             discouraged to enable copying outside the HPLMN."
        ::= { cpyProperties 1 }

    cpyPropBillingEnabled OBJECT-TYPE
        SYNTAX  Boolean
        ACCESS  read-write
        STATUS  mandatory
        DESCRIPTION
            "Indicator specifying whether the copied message is allowed
            to create CDRs. The billingprofile for copied messages is
            assigned by the MtRoutingRules.
            Default of this setting is 'false'."
        ::= { cpyProperties 2 }
          
    cpyPropActionForSmCopiesToMobile OBJECT-TYPE
        SYNTAX  CopyAction   
        ACCESS  read-write
        STATUS  mandatory
        DESCRIPTION
            "Action pertaining to the routing of copies that are sent to 
            mobile as MT/SM. Default is routeFallbackToStorage."
        ::= { cpyProperties 11 }
     
    cpyPropAmsQueueForCopiesToMobile OBJECT-TYPE
        SYNTAX  AmsQueueIndex   
        ACCESS  read-write
        STATUS  mandatory
        DESCRIPTION
            "Specification of AMS queue to be used to store copies that are 
            sent to mobile as MT/SM. Default is 1."
        ::= { cpyProperties 12 }

    cpyPropActionForSmCopiesToApplication OBJECT-TYPE
        SYNTAX  CopyAction   
        ACCESS  read-write
        STATUS  mandatory
        DESCRIPTION
            "Action pertaining to the routing of copies that are sent to 
            application as AT/SM. Default is routeFallbackToStorage."
        ::= { cpyProperties 13 }
     
    cpyPropAmsQueueForCopiesToApplication OBJECT-TYPE
        SYNTAX  AmsQueueIndex   
        ACCESS  read-write
        STATUS  mandatory
        DESCRIPTION
            "Specification of AMS queue to be used to store copies that are 
            sent to application as AT/SM. Default is 2."
        ::= { cpyProperties 14 }

    cpyPropMaxNumCopiesPerSecond OBJECT-TYPE
        SYNTAX  Gauge   
        ACCESS  read-write
        STATUS  mandatory
        DESCRIPTION
            "Maximum number of copies that can be made per second. If the 
            number of copies per second exceeds the maximum threshold, 
            copying of the messages is delayed. Default is 10."
        ::= { cpyProperties 21 }
     
    cpyPropMaxNumConcurrentCopyTransactions OBJECT-TYPE
        SYNTAX  Gauge
        ACCESS  read-write
        STATUS  mandatory
        DESCRIPTION
            "Maximum number of concurrent copy transactions. Copying of 
            messages is refused when the number of pending copy 
            transactions is equal to the maximum threshold. Default is 1000."
        ::= { cpyProperties 22 }
     
    cpyPropExtAttrForSmRequestingCopy OBJECT-TYPE
        SYNTAX  ExtAttrId
        ACCESS  read-write
        STATUS  mandatory
        DESCRIPTION
            "Index of external attribute that will be set for a SM when a 
            request to copy SM has been received.
            Default value is 0, implying that no external attribute will be
            set."
        ::= { cpyProperties 41 }

    cpyPropExtAttrForCopiedSm OBJECT-TYPE
        SYNTAX  ExtAttrId
        ACCESS  read-write
        STATUS  mandatory
        DESCRIPTION
            "Index of external attribute that will be set for a copied SM.
            Default value is 0, implying that no external attribute will be
            set."
        ::= { cpyProperties 42 }

    cpyPropBillingECApplicationForOriginatorCopy OBJECT-TYPE
        SYNTAX  ExternalConditionRef
        ACCESS  read-write
        STATUS  mandatory
        DESCRIPTION
            "Specifies the application to use to handle pre-paid
            billing for originator copies.  If set to 0,
            originator copies are not charged.  The default value
            is 0."
      ::= { cpyProperties 43 }

    cpyPropBillingECApplicationForRecipientCopy OBJECT-TYPE
        SYNTAX  ExternalConditionRef
        ACCESS  read-write
        STATUS  mandatory
        DESCRIPTION
            "Specifies the application to use to handle pre-paid
            billing for recipient copies.  If set to 0, recipient
            copies are not charged.  The default value is 0."
      ::= { cpyProperties 44 }

    cpyPropDeliverOnOrigCopyBillingECAppFalseEval OBJECT-TYPE
        SYNTAX  Boolean
        ACCESS  read-write
        STATUS  mandatory
        DESCRIPTION
            "Specifies delivery behaviour in the event of the EC
            application evaluating to false.  If TRUE, messages will
            be delivered anyway, regardless of the false evaluation.
            If FALSE, messages will not be delivered.  Default is
            FALSE."
      ::= { cpyProperties 45 }

    cpyPropDeliverOnRecipCopyBillingECAppFalseEval OBJECT-TYPE
        SYNTAX  Boolean
        ACCESS  read-write
        STATUS  mandatory
        DESCRIPTION
            "Specifies delivery behaviour in the event of the EC
            application evaluating to false.  If TRUE, messages will
            be delivered anyway, regardless of the false evaluation.
            If FALSE, messages will not be delivered. Default is
            FALSE."
      ::= { cpyProperties 46 }

    cpyCounters OBJECT IDENTIFIER ::= { sms 112 }

    cpyCntReqReceived OBJECT-TYPE
        SYNTAX  Counter
        ACCESS  read-write
        STATUS  mandatory
        DESCRIPTION
            "Counter specifying the number of requests that the RTR received
            to copy a SM."
        ::= { cpyCounters 1 }

    cpyCntReqReceivedWithSingleCopyDestination OBJECT-TYPE
        SYNTAX  Counter
        ACCESS  read-write
        STATUS  mandatory
        DESCRIPTION
            "Counter specifying the number of requests that the RTR received 
            to copy a SM to a single destination."
        ::= { cpyCounters 2 }

    cpyCntReqReceivedWithMultipleCopyDestinations OBJECT-TYPE
        SYNTAX  Counter
        ACCESS  read-write
        STATUS  mandatory
        DESCRIPTION
            "Counter specifying the number of requests that the RTR received 
            to copy a SM to multiple destinations."
        ::= { cpyCounters 3 }

    cpyCntReqApproved  OBJECT-TYPE
        SYNTAX  Counter
        ACCESS  read-write
        STATUS  mandatory
        DESCRIPTION
            "Counter specifying the number of copy requests that the RTR has 
            approved and executed."
        ::= { cpyCounters 11 }

    cpyCntReqDiscardedAsOriginalSmNotInCopyableState OBJECT-TYPE
        SYNTAX  Counter
        ACCESS  read-write
        STATUS  mandatory
        DESCRIPTION
            "Counter specifying the number of copy requests that the RTR has 
            discarded because the original SM did not reach a state in which 
            it can be copied. An MO/SM or AO/SM becomes copy-able when the RTR
            has accepted the SM. An MT/SM or AT/SM becomes copy-able when the
            RTR has successfully delivered the SM."
        ::= { cpyCounters 12 }

    cpyCntReqDiscardedAsSmsCommandNotCopyable OBJECT-TYPE
        SYNTAX  Counter
        ACCESS  read-write
        STATUS  mandatory
        DESCRIPTION
            "Counter specifying the number of copy requests that the RTR has 
            discarded because the request pertained to a SMS-COMMAND PDU, 
            which is not copyable."
        ::= { cpyCounters 13 }

    cpyCntReqDiscardedAsSmsStatusReportNotCopyable OBJECT-TYPE
        SYNTAX  Counter
        ACCESS  read-write
        STATUS  mandatory
        DESCRIPTION
            "Counter specifying the number of copy requests that the RTR has 
            discarded because the request pertained to a SMS-STATUS-REPORT 
            PDU, which is not copyable." 
        ::= { cpyCounters 14 }

    cpyCntReqDiscardedAsSimDataDownloadNotCopyable OBJECT-TYPE
        SYNTAX  Counter
        ACCESS  read-write
        STATUS  mandatory
        DESCRIPTION
            "Counter specifying the number of copy requests that the RTR has 
            discarded because the request pertained to a SM with data to be 
            loaded on the SIM. The RTR does not support copying of such an 
            SM." 
        ::= { cpyCounters 15 }

    cpyCntReqDiscardedAsOriginalRecipientNotFromHplmn OBJECT-TYPE
        SYNTAX  Counter
        ACCESS  read-write
        STATUS  mandatory
        DESCRIPTION
            "Counter specifying the number of copy requests that the RTR has 
            discarded because the recipient from the original SM does not 
            belong to the HPLMN." 
        ::= { cpyCounters 16 }

    cpyCntReqDiscardedAsCopyOfLongSmNotSupported OBJECT-TYPE
        SYNTAX  Counter
        ACCESS  read-write
        STATUS  mandatory
        DESCRIPTION
            "Counter specifying the number of copy requests that the RTR has 
            discarded because the payload of the original SM exceeds the 
            maximum that can be carried by a single SMS-SUBMIT or 
            SMS-DELIVER PDU." 
        ::= { cpyCounters 17 }

    cpyCntReqDiscardedAsCopyOfCopiedSmNotSupported OBJECT-TYPE
        SYNTAX  Counter
        ACCESS  read-write
        STATUS  mandatory
        DESCRIPTION
            "Counter specifying the number of copy requests that the RTR has 
            discarded because the original SM is already a copy of an SM. The 
            RTR does not support copying of an SM that is already a copy of 
            an SM." 
        ::= { cpyCounters 18 }

    cpyCntNewSmIssued OBJECT-TYPE
        SYNTAX  Counter
        ACCESS  read-write
        STATUS  mandatory
        DESCRIPTION
            "Counter specifying the number of times that the RTR has issued a 
            new SM as result of a copy request."
        ::= { cpyCounters 31 }

    cpyCntNewSmNotIssuedAsInvalidAddress OBJECT-TYPE
        SYNTAX  Counter
        ACCESS  read-write
        STATUS  mandatory
        DESCRIPTION
            "Counter specifying the number of times that the RTR did not issue
            a new SM as result of a copy request because of an invalid address 
            for the copy destination."
        ::= { cpyCounters 32 }

    cpyCntNewSmNotIssuedAsShortNumberNotAssigned OBJECT-TYPE
        SYNTAX  Counter
        ACCESS  read-write
        STATUS  mandatory
        DESCRIPTION
            "Counter specifying the number of times that the RTR did not issue
            a new SM as result of a copy request because the address for the 
            copy destination concerned a short number that has not been 
            assigned to any of the applications."
        ::= { cpyCounters 33 }

    cpyCntNewSmNotIssuedAsTooManyCopiesInProgress OBJECT-TYPE
        SYNTAX  Counter
        ACCESS  read-write
        STATUS  mandatory
        DESCRIPTION
            "Counter specifying the number of times that the RTR did not issue
            a new SM as result of a copy request because too many copies were 
            already in progress."
        ::= { cpyCounters 34 }

    cpyCntNewSmNotIssuedAsNotFromHplmn OBJECT-TYPE
        SYNTAX  Counter
        ACCESS  read-write
        STATUS  mandatory
        DESCRIPTION
            "Counter specifying the number of times that the RTR did not issue
            a new SM as result of a copy request because the copy destination 
            concerned a subscriber that does not belong to the HPLMN."
        ::= { cpyCounters 35 }

    cpyCntNewSmNotIssuedAsPotentialCopyLoopDetected OBJECT-TYPE
        SYNTAX  Counter
        ACCESS  read-write
        STATUS  mandatory
        DESCRIPTION
            "Counter specifying the number of times that the RTR did not issue
            a new SM as result of a copy request because the RTR detected a 
            potential copy loop."
        ::= { cpyCounters 36 }

    cpyCntRoutingToMobileSucceeded OBJECT-TYPE
        SYNTAX  Counter
        ACCESS  read-write
        STATUS  mandatory
        DESCRIPTION
            "Counter specifying the number of times that the RTR issued a new 
            MT/SM as result of a copy request and successfully delivered the 
            new MT/SM. Note that this counter does not increment upon delivery 
            attempts that are triggered by the AMS."
        ::= { cpyCounters 41 }

    cpyCntRoutingToMobileFailed OBJECT-TYPE
        SYNTAX  Counter
        ACCESS  read-write
        STATUS  mandatory
        DESCRIPTION
            "Counter specifying the number of times that the RTR issued a new 
            MT/SM as result of a copy request and failed to deliver the new 
            MT/SM. Note that this counter does not increment upon delivery 
            attempts that are triggered by the AMS."
        ::= { cpyCounters 42 }

    cpyCntStoringForDeliveryToMobileSucceeded OBJECT-TYPE
        SYNTAX  Counter
        ACCESS  read-write
        STATUS  mandatory
        DESCRIPTION
            "Counter specifying the number of times that the RTR issued a new 
            MT/SM as result of a copy request and successfully stored the 
            new MT/SM in the AMS."
        ::= { cpyCounters 43 }

    cpyCntStoringForDeliveryToMobileFailed OBJECT-TYPE
        SYNTAX  Counter
        ACCESS  read-write
        STATUS  mandatory
        DESCRIPTION
            "Counter specifying the number of times that the RTR issued a new 
            MT/SM as result of a copy request and failed to store the new 
            MT/SM in the AMS."
        ::= { cpyCounters 44 }

    cpyCntRoutingToApplicationSucceeded OBJECT-TYPE
        SYNTAX  Counter
        ACCESS  read-write
        STATUS  mandatory
        DESCRIPTION
            "Counter specifying the number of times that the RTR issued a new 
            AT/SM as result of a copy request and successfully delivered the 
            new AT/SM. Note that this counter does not increment upon delivery 
            attempts that are triggered by the AMS."
        ::= { cpyCounters 51 }

    cpyCntRoutingToApplicationFailed OBJECT-TYPE
        SYNTAX  Counter
        ACCESS  read-write
        STATUS  mandatory
        DESCRIPTION
            "Counter specifying the number of times that the RTR issued a new 
            AT/SM as result of a copy request and failed to deliver the new 
            AT/SM. Note that this counter does not increment upon delivery 
            attempts that are triggered by the AMS."
        ::= { cpyCounters 52 }

    cpyCntStoringForDeliveryToApplicationSucceeded OBJECT-TYPE
        SYNTAX  Counter
        ACCESS  read-write
        STATUS  mandatory
        DESCRIPTION
            "Counter specifying the number of times that the RTR issued a new 
            AT/SM as result of a copy request and successfully stored the 
            new AT/SM in the AMS."
        ::= { cpyCounters 53 }

    cpyCntStoringForDeliveryToApplicationFailed OBJECT-TYPE
        SYNTAX  Counter
        ACCESS  read-write
        STATUS  mandatory
        DESCRIPTION
            "Counter specifying the number of times that the RTR issued a new 
            AT/SM as result of a copy request and failed to store the new 
            AT/SM in the AMS."
        ::= { cpyCounters 54 }

    fwdProperties OBJECT IDENTIFIER ::= { sms 116 }
    
    fwdPropRestrictForwardingToOwnSubscriberBase OBJECT-TYPE 
        SYNTAX  Boolean
        ACCESS  read-write
        STATUS  mandatory
        DESCRIPTION
            "Indicator specifying whether the forwarding should only be done 
            when the destination of the forwarding belongs to HPLMN. Default 
            of this setting is 'true'.
            
            Enabling forwarding outside the HPLMN opens up the possibility of 
            forward loops. As a result of forward loops, the TextPass RTR 
            (and even the whole HPLMN) may become inoperable. As such, it 
            strongly discouraged to enable forwardingoutside the HPLMN."
        ::= { fwdProperties 1 }

    fwdPropBillingEnabled OBJECT-TYPE
        SYNTAX  Boolean
        ACCESS  read-write
        STATUS  mandatory
        DESCRIPTION
            "Indicator specifying whether the forwarded message is allowed
            to create CDRs. The billingprofile for the forwarded messages is
            assigned by the MtRoutingRules.
            Default of this setting is 'false'."
        ::= { fwdProperties 2 }
          
    fwdPropStatusReportProcessingForUnconditionalForwarding OBJECT-TYPE
        SYNTAX  ForwardExceptionAction
        ACCESS  read-write
        STATUS  mandatory
        DESCRIPTION
            "Indicator specifying how Status Reports should be processed in
            case of unconditional forwarding. 
            Default is 'blockWithAck'."
        ::= { fwdProperties 31 }
              
    fwdPropSimDownLoadProcessingForUnconditionalForwarding OBJECT-TYPE    
        SYNTAX  ForwardExceptionAction
        ACCESS  read-write
        STATUS  mandatory
        DESCRIPTION
            "Indicator specifying how SM-s with Protocol ID equal to value for
            SIM Data Download (127) should be processed in case of 
            unconditional forwarding.
            Default is 'blockWithAck'."
        ::= { fwdProperties 32 }
    
    fwdPropStatusReportProcessingForConditionalForwarding OBJECT-TYPE
        SYNTAX  ForwardExceptionAction
        ACCESS  read-write
        STATUS  mandatory
        DESCRIPTION
            "Indicator specifying how Status Reports should be processed 
            in case of conditional forwarding. Note that this indicator 
            specifies the behaviour when the delivery attempt to the 
            original recipient has failed and the Status Report needs to be 
            forwarded to the forwarded address.
            Default is 'blockWithAck'."
        ::= { fwdProperties 36 }
    
    fwdPropSimDownLoadProcessingForConditionalForwarding OBJECT-TYPE        
        SYNTAX  ForwardExceptionAction
        ACCESS  read-write
        STATUS  mandatory
        DESCRIPTION
            "Indicator specifying how SM-s with Protocol ID equal to value 
            for SIM Data Download (127) should be processed in case of 
            conditional forwarding. Note that this indicator specifies the 
            behaviour when the delivery attempt to the original recipient has 
            failed and the message needs to be forwarded to the forwarded 
            address.
            Default is 'blockWithAck'."
        ::= { fwdProperties 37 }
    
    fwdPropExtAttrForSmRequestingConditionalForwarding OBJECT-TYPE
        SYNTAX  ExtAttrId
        ACCESS  read-write
        STATUS  mandatory
        DESCRIPTION
            "Index of external attribute that will be set for an SM when a 
            request to conditionally forward the SM has been received.
            Default value is 0, implying that no external attribute will be
            set."
        ::= { fwdProperties 41 }

    fwdPropExtAttrForSmRequestingUnconditionalForwarding OBJECT-TYPE
        SYNTAX  ExtAttrId
        ACCESS  read-write
        STATUS  mandatory
        DESCRIPTION
            "Index of external attribute that will be set for an SM when a 
            request to unconditionally forward the SM has been received.
            Default value is 0, implying that no external attribute will be
            set."
        ::= { fwdProperties 42 }    

    fwdPropExtAttrForSmBeingForwarded OBJECT-TYPE
        SYNTAX  ExtAttrId
        ACCESS  read-write
        STATUS  mandatory
        DESCRIPTION
            "Index of external attribute that will be set for an SM at the 
            point that a delivery attempt to the forwarded address is 
            initiated. 
            Default value is 0, implying that no external attribute will be
            set."
        ::= { fwdProperties 43 }

    fwdPropBillingECApplicationForUnconditionalForward OBJECT-TYPE
        SYNTAX  ExternalConditionRef
        ACCESS  read-write
        STATUS  mandatory
        DESCRIPTION
            "Specifies the application to use to handle pre-paid
            billing for unconditional forwarding.  If set to 0,
            unconditional forwarding is not charged.  Default value
            is 0."
      ::= { fwdProperties 44 }

    fwdPropBillingECApplicationForConditionalForward OBJECT-TYPE
        SYNTAX  ExternalConditionRef
        ACCESS  read-write
        STATUS  mandatory
        DESCRIPTION
            "Specifies the application to use to handle pre-paid
            billing for conditional forwarding.  If set to 0,
            conditional forwarding is not charged.  Default value
            is 0."
      ::= { fwdProperties 45 }

    fwdPropDeliverOnUnconditionalForwardBillingECAppFalseEval OBJECT-TYPE
        SYNTAX  Boolean
        ACCESS  read-write
        STATUS  mandatory
        DESCRIPTION
            "Specifies delivery behaviour in the event of the EC
            application evaluating to false.  If TRUE, messages will
            be delivered anyway, regardless of the false evaluation.
            If FALSE, messages will not be delivered.  Default is
            FALSE."
      ::= { fwdProperties 46 }

    fwdPropDeliverOnConditionalForwardBillingECAppFalseEval OBJECT-TYPE
        SYNTAX  Boolean
        ACCESS  read-write
        STATUS  mandatory
        DESCRIPTION
            "Specifies delivery behaviour in the event of the EC
            application evaluating to false.  If TRUE, messages will
            be delivered anyway, regardless of the false evaluation.
            If FALSE, messages will not be delivered. Default is FALSE."
      ::= { fwdProperties 47 }

    fwdCounters OBJECT IDENTIFIER ::= { sms 117 }
    
    fwdCntCndReqApprovedAndFwdSucceeded OBJECT-TYPE
        SYNTAX  Counter
        ACCESS  read-write
        STATUS  mandatory
        DESCRIPTION
            "Counter specifying the number of conditional forward requests 
            that the RTR has approved and for which forwarding has 
            succeeded."
        ::= { fwdCounters 1 }

    fwdCntCndReqApprovedAndFwdFailedWithTemporaryError OBJECT-TYPE
        SYNTAX  Counter
        ACCESS  read-write
        STATUS  mandatory
        DESCRIPTION
            "Counter specifying the number of conditional forward requests 
            that the RTR has approved and for which forwarding has 
            failed with a temporary error."
        ::= { fwdCounters 2 }

    fwdCntCndReqApprovedAndFwdFailedWithPermanentError OBJECT-TYPE
        SYNTAX  Counter
        ACCESS  read-write
        STATUS  mandatory
        DESCRIPTION
            "Counter specifying the number of conditional forward requests 
            that the RTR has approved and for which forwarding has 
            failed with a permanent error."
        ::= { fwdCounters 3 }

    fwdCntCndReqRefusedAsNotInForwardableState OBJECT-TYPE
        SYNTAX  Counter
        ACCESS  read-write
        STATUS  mandatory
        DESCRIPTION
            "Counter specifying the number of conditional forward requests 
            that the RTR has refused because the original SM did not reach 
            a state in which it can be forwarded. Typically, this state is 
            not reached because:
            - delivery to the original recipient succeeded 
            - delivery to the original recipient failed with another error 
              than absentSubscriber. 
            - the SM was blocked by an MT rule."
        ::= { fwdCounters 11 }

    fwdCntCndReqRefusedAsForwardAddressIsShortNumber OBJECT-TYPE 
        SYNTAX  Counter
        ACCESS  read-write
        STATUS  mandatory
        DESCRIPTION
            "Counter specifying the number of conditional forward requests 
            that the RTR has refused because the forward address is a 
            short number. Forwarding to a short numbers is not (yet) 
            supported."
        ::= { fwdCounters 12 }

    fwdCntCndReqRefusedAsForwardAddressIsNotAssigned OBJECT-TYPE 
        SYNTAX  Counter
        ACCESS  read-write
        STATUS  mandatory
        DESCRIPTION
            "Counter specifying the number of conditional forward requests 
            that the RTR has refused because the forward address has not 
            been assigned to a mobile."
        ::= { fwdCounters 13 }

    fwdCntCndReqRefusedAsForwardAddressNotFromHplmn OBJECT-TYPE 
        SYNTAX  Counter
        ACCESS  read-write
        STATUS  mandatory
        DESCRIPTION
            "Counter specifying the number of conditional forward requests 
            that the RTR has refused because the forward address is not 
            a subscriber of the HPLMN."
        ::= { fwdCounters 14 }

    fwdCntCndReqDiscardedAsSimDataDownload OBJECT-TYPE
        SYNTAX  Counter
        ACCESS  read-write
        STATUS  mandatory
        DESCRIPTION
            "Counter specifying the number of conditional forward requests 
            that the RTR has discarded because the request pertained to a 
            SM with data to be loaded on the SIM, whilst the RTR has been 
            configured not to forward such an SM."
        ::= { fwdCounters 21 }

    fwdCntCndReqDiscardedAsStatusReport OBJECT-TYPE
        SYNTAX  Counter
        ACCESS  read-write
        STATUS  mandatory
        DESCRIPTION
            "Counter specifying the number of conditional forward requests 
            that the RTR has discarded because the request pertained to a 
            a SMS-STATUS-REPORT PDU, whilst the RTR has been configured not 
            to forward such an SM."
        ::= { fwdCounters 22 }

    fwdCntCndReqDiscardedAsIsCopiedSm OBJECT-TYPE
        SYNTAX  Counter
        ACCESS  read-write
        STATUS  mandatory
        DESCRIPTION
            "Counter specifying the number of conditional forward requests 
            that the RTR has discarded because the original SM is a copy of 
            an SM. The RTR does not support forwarding of an SM that is a 
            copy of an SM." 
        ::= { fwdCounters 23 }

    fwdCntCndReqDiscardedAsOriginalRecipientNotFromHplmn OBJECT-TYPE 
        SYNTAX  Counter
        ACCESS  read-write
        STATUS  mandatory
        DESCRIPTION
            "Counter specifying the number of conditional forward requests 
            that the RTR has discarded because the recipient from the 
            original SM does not belong to the HPLMN." 
        ::= { fwdCounters 24 }

    fwdCntCndReqDiscardedAsInvalidForwardAddress OBJECT-TYPE 
        SYNTAX  Counter
        ACCESS  read-write
        STATUS  mandatory
        DESCRIPTION
            "Counter specifying the number of conditional forward requests 
            that the RTR has discarded because of an invalid forward 
            address."
        ::= { fwdCounters 25 }

    fwdCntCndReqDiscardedAsPotentialForwardLoopDetected OBJECT-TYPE 
        SYNTAX  Counter
        ACCESS  read-write
        STATUS  mandatory
        DESCRIPTION
            "Counter specifying the number of conditional forward requests 
            that the RTR has discarded because it detected a potential 
            forward loop."
        ::= { fwdCounters 26 }

    fwdCntCndReqDiscardedUsingBlockWithAck OBJECT-TYPE 
        SYNTAX  Counter
        ACCESS  read-write
        STATUS  mandatory
        DESCRIPTION
            "Counter specifying the number of conditional forward requests 
            that the RTR has discarded by blocking the SM in such a way that
            it seems (from the perspective from the point of origin) as if 
            the delivery attempt to the forward address has succeeded."
        ::= { fwdCounters 31 }

    fwdCntCndReqDiscardedUsingBlockWithTemporaryError OBJECT-TYPE 
        SYNTAX  Counter
        ACCESS  read-write
        STATUS  mandatory
        DESCRIPTION
            "Counter specifying the number of conditional forward requests 
            that the RTR has discarded by blocking the SM in such a way that
            it seems (from the perspective from the point of origin) as if 
            the delivery attempt to the forward address has failed with a
            temporary error."
        ::= { fwdCounters 32 }

    fwdCntCndReqDiscardedUsingBlockWithPermanentError OBJECT-TYPE 
        SYNTAX  Counter
        ACCESS  read-write
        STATUS  mandatory
        DESCRIPTION
            "Counter specifying the number of conditional forward requests 
            that the RTR has discarded by blocking the SM in such a way that
            it seems (from the perspective from the point of origin) as if 
            the delivery attempt to the forward address has failed with a
            permanent error."
        ::= { fwdCounters 33 }

    fwdCntUnCndReqApprovedAndFwdSucceeded OBJECT-TYPE
        SYNTAX  Counter
        ACCESS  read-write
        STATUS  mandatory
        DESCRIPTION
            "Counter specifying the number of unconditional forward requests 
            that the RTR has approved and for which forwarding has 
            succeeded."
        ::= { fwdCounters 51 }

    fwdCntUnCndReqApprovedAndFwdFailedWithTemporaryError OBJECT-TYPE
        SYNTAX  Counter
        ACCESS  read-write
        STATUS  mandatory
        DESCRIPTION
            "Counter specifying the number of unconditional forward requests 
            that the RTR has approved and for which forwarding has 
            failed with a temporary error."
        ::= { fwdCounters 52 }

    fwdCntUnCndReqApprovedAndFwdFailedWithPermanentError OBJECT-TYPE
        SYNTAX  Counter
        ACCESS  read-write
        STATUS  mandatory
        DESCRIPTION
            "Counter specifying the number of unconditional forward requests 
            that the RTR has approved and for which forwarding has 
            failed with a permanent error."
        ::= { fwdCounters 53 }

    fwdCntUnCndReqRefusedAsNotInForwardableState OBJECT-TYPE
        SYNTAX  Counter
        ACCESS  read-write
        STATUS  mandatory
        DESCRIPTION
            "Counter specifying the number of unconditional forward requests 
            that the RTR has refused because the original SM did not reach 
            a state in which it can be forwarded. Typically, this state is 
            not reached because the SM was blocked by an MT rule."
        ::= { fwdCounters 61 }

    fwdCntUnCndReqRefusedAsForwardAddressIsShortNumber OBJECT-TYPE 
        SYNTAX  Counter
        ACCESS  read-write
        STATUS  mandatory
        DESCRIPTION
            "Counter specifying the number of unconditional forward requests 
            that the RTR has refused because the forward address is a 
            short number. Forwarding to a short numbers is not (yet) 
            supported."
        ::= { fwdCounters 62 }

    fwdCntUnCndReqRefusedAsForwardAddressIsNotAssigned OBJECT-TYPE 
        SYNTAX  Counter
        ACCESS  read-write
        STATUS  mandatory
        DESCRIPTION
            "Counter specifying the number of unconditional forward requests 
            that the RTR has refused because the forward address has not 
            been assigned to a mobile."
        ::= { fwdCounters 63 }

    fwdCntUnCndReqRefusedAsForwardAddressNotFromHplmn OBJECT-TYPE 
        SYNTAX  Counter
        ACCESS  read-write
        STATUS  mandatory
        DESCRIPTION
            "Counter specifying the number of unconditional forward requests 
            that the RTR has refused because the forward address is not 
            a subscriber of the HPLMN."
        ::= { fwdCounters 64 }

    fwdCntUnCndReqDiscardedAsSimDataDownload OBJECT-TYPE
        SYNTAX  Counter
        ACCESS  read-write
        STATUS  mandatory
        DESCRIPTION
            "Counter specifying the number of unconditional forward requests 
            that the RTR has discarded because the request pertained to a 
            SM with data to be loaded on the SIM, whilst the RTR has been 
            configured not to forward such an SM."
        ::= { fwdCounters 71 }

    fwdCntUnCndReqDiscardedAsStatusReport OBJECT-TYPE
        SYNTAX  Counter
        ACCESS  read-write
        STATUS  mandatory
        DESCRIPTION
            "Counter specifying the number of unconditional forward requests 
            that the RTR has discarded because the request pertained to a 
            a SMS-STATUS-REPORT PDU, whilst the RTR has been configured not 
            to forward such an SM."
        ::= { fwdCounters 72 }

    fwdCntUnCndReqDiscardedAsIsCopiedSm OBJECT-TYPE
        SYNTAX  Counter
        ACCESS  read-write
        STATUS  mandatory
        DESCRIPTION
            "Counter specifying the number of unconditional forward requests 
            that the RTR has discarded because the original SM is a copy of 
            an SM. The RTR does not support forwarding of an SM that is a 
            copy of an SM." 
        ::= { fwdCounters 73 }

    fwdCntUnCndReqDiscardedAsOriginalRecipientNotFromHplmn OBJECT-TYPE 
        SYNTAX  Counter
        ACCESS  read-write
        STATUS  mandatory
        DESCRIPTION
            "Counter specifying the number of unconditional forward requests 
            that the RTR has discarded because the recipient from the 
            original SM does not belong to the HPLMN." 
        ::= { fwdCounters 74 }

    fwdCntUnCndReqDiscardedAsInvalidForwardAddress OBJECT-TYPE 
        SYNTAX  Counter
        ACCESS  read-write
        STATUS  mandatory
        DESCRIPTION
            "Counter specifying the number of unconditional forward requests 
            that the RTR has discarded because of an invalid forward 
            address."
        ::= { fwdCounters 75 }

    fwdCntUnCndReqDiscardedAsPotentialForwardLoopDetected OBJECT-TYPE 
        SYNTAX  Counter
        ACCESS  read-write
        STATUS  mandatory
        DESCRIPTION
            "Counter specifying the number of unconditional forward requests 
            that the RTR has discarded because it detected a potential 
            forward loop."
        ::= { fwdCounters 76 }

    fwdCntUnCndReqDiscardedUsingBlockWithAck OBJECT-TYPE 
        SYNTAX  Counter
        ACCESS  read-write
        STATUS  mandatory
        DESCRIPTION
            "Counter specifying the number of unconditional forward requests 
            that the RTR has discarded by blocking the SM in such a way that
            it seems (from the perspective from the point of origin) as if 
            the delivery attempt to the forward address has succeeded."
        ::= { fwdCounters 81 }

    fwdCntUnCndReqDiscardedUsingBlockWithTemporaryError OBJECT-TYPE 
        SYNTAX  Counter
        ACCESS  read-write
        STATUS  mandatory
        DESCRIPTION
            "Counter specifying the number of unconditional forward requests 
            that the RTR has discarded by blocking the SM in such a way that
            it seems (from the perspective from the point of origin) as if 
            the delivery attempt to the forward address has failed with a
            temporary error."
        ::= { fwdCounters 82 }

    fwdCntUnCndReqDiscardedUsingBlockWithPermanentError OBJECT-TYPE 
        SYNTAX  Counter
        ACCESS  read-write
        STATUS  mandatory
        DESCRIPTION
            "Counter specifying the number of unconditional forward requests 
            that the RTR has discarded by blocking the SM in such a way that
            it seems (from the perspective from the point of origin) as if 
            the delivery attempt to the forward address has failed with a
            permanent error."
        ::= { fwdCounters 83 }

    -- memory usage of rtg rules, apps, etc.
    memUsage OBJECT IDENTIFIER ::= { sms 121 }

    memMoRtg OBJECT-TYPE
        SYNTAX  Gauge
        ACCESS  read-only
        STATUS  mandatory
        DESCRIPTION
            "Memory used for mo_rtg."
        ::= { memUsage 1 }

    memMoRtgSmsc OBJECT-TYPE
        SYNTAX  Gauge
        ACCESS  read-only
        STATUS  mandatory
        DESCRIPTION
            "Memory used for mo_rtg_smsc."
        ::= { memUsage 2 }

    memMtRtg OBJECT-TYPE
        SYNTAX  Gauge
        ACCESS  read-only
        STATUS  mandatory
        DESCRIPTION
            "Memory used for mt_rtg."
        ::= { memUsage 3 }

    memRtgMod OBJECT-TYPE
        SYNTAX  Gauge
        ACCESS  read-only
        STATUS  mandatory
        DESCRIPTION
            "Memory used for rtg_mod."
        ::= { memUsage 4 }

    memMoCnt OBJECT-TYPE
        SYNTAX  Gauge
        ACCESS  read-only
        STATUS  mandatory
        DESCRIPTION
            "Memory used for mo_cnt."
        ::= { memUsage 5 }

    memMtCnt OBJECT-TYPE
        SYNTAX  Gauge
        ACCESS  read-only
        STATUS  mandatory
        DESCRIPTION
            "Memory used for mt_cnt."
        ::= { memUsage 6 }

    memCty OBJECT-TYPE
        SYNTAX  Gauge
        ACCESS  read-only
        STATUS  mandatory
        DESCRIPTION
            "Memory used for cty."
        ::= { memUsage 7 }

    memNet OBJECT-TYPE
        SYNTAX  Gauge
        ACCESS  read-only
        STATUS  mandatory
        DESCRIPTION
            "Memory used for net."
        ::= { memUsage 8 }

    memApp OBJECT-TYPE
        SYNTAX  Gauge
        ACCESS  read-only
        STATUS  mandatory
        DESCRIPTION
            "Memory used for app."
        ::= { memUsage 9 }

    memSmsc OBJECT-TYPE
        SYNTAX  Gauge
        ACCESS  read-only
        STATUS  mandatory
        DESCRIPTION
            "Memory used for smsc."
        ::= { memUsage 10 }

    memList OBJECT-TYPE
        SYNTAX  Gauge
        ACCESS  read-only
        STATUS  mandatory
        DESCRIPTION
            "Memory used for list."
        ::= { memUsage 11 }

    memListCond OBJECT-TYPE
        SYNTAX  Gauge
        ACCESS  read-only
        STATUS  mandatory
        DESCRIPTION
            "Memory used for listCond."
        ::= { memUsage 12 }


    logProperties OBJECT IDENTIFIER ::= { sms 131 }

    logPropDefaultProfileForMo OBJECT-TYPE
        SYNTAX  LogProfile
        ACCESS  read-write
        STATUS  mandatory
        DESCRIPTION
            "Identifier specifying which logging profile should be used for
            incoming MO messages as a default. By default, the object is set
            to 0 (referring to no profile).
            The value 1000 (i.e. 'default') does not apply for this object."
        ::= { logProperties 1 }

    logPropDefaultProfileForMt OBJECT-TYPE
        SYNTAX  LogProfile
        ACCESS  read-write
        STATUS  mandatory
        DESCRIPTION
            "Identifier specifying which logging profile should be used for
            incoming MT messages as a default. By default, the object is set
            to 0 (referring to no profile).
            The value 1000 (i.e. 'default') does not apply for this object."
        ::= { logProperties 2 }

    logPropDefaultProfileForAo OBJECT-TYPE
        SYNTAX  LogProfile
        ACCESS  read-write
        STATUS  mandatory
        DESCRIPTION
            "Identifier specifying which logging profile should be used for
            incoming AO messages as a default. By default, the object is set
            to 0 (referring to no profile).
            The value 1000 (i.e. 'default') does not apply for this object."
        ::= { logProperties 3 }

    logPropDefaultProfileForAt OBJECT-TYPE
        SYNTAX  LogProfile
        ACCESS  read-write
        STATUS  mandatory
        DESCRIPTION
            "Identifier specifying which logging profile should be used for
            incoming AT messages as a default. By default, the object is set
            to 0 (referring to no profile).
            The value 1000 (i.e. 'default') does not apply for this object."
        ::= { logProperties 4 }

    logPropDefaultProfileForCo OBJECT-TYPE
        SYNTAX  LogProfile
        ACCESS  read-write
        STATUS  mandatory
        DESCRIPTION
            "Identifier specifying which logging profile should be used for
            incoming CDMA MO messages as a default. By default, the object is
            set to 0 (referring to no profile).
            The value 1000 (i.e. 'default') does not apply for this object."
        ::= { logProperties 5 }

    logPropProfileForMoFatalProtocolViolation OBJECT-TYPE
        SYNTAX  LogProfile
        ACCESS  read-write
        STATUS  mandatory
        DESCRIPTION
            "Identifier specifying which logging profile should be used in
            case of a fatal procotocol violation in an MO/SM."
        ::= { logProperties 11 }

    logPropProfileForMtFatalProtocolViolation OBJECT-TYPE
        SYNTAX  LogProfile
        ACCESS  read-write
        STATUS  mandatory
        DESCRIPTION
            "Identifier specifying which logging profile should be used in
            case of a fatal procotocol violation in an MT/SM."
        ::= { logProperties 12 }

    logPropProfileForCoFatalProtocolViolation OBJECT-TYPE
        SYNTAX  LogProfile
        ACCESS  read-write
        STATUS  mandatory
        DESCRIPTION
            "Identifier specifying which logging profile should be used in
            case of a fatal procotocol violation in an CO/SM."
        ::= { logProperties 13 }

    logPropProfileForCommandMo OBJECT-TYPE
        SYNTAX  LogProfile
        ACCESS  read-write
        STATUS  mandatory
        DESCRIPTION
            "Identifier specifying which logging profile should be used for
            SMS commands mobile originated.
            The value 1000 (i.e. 'default') does not apply for this object."
        ::= { logProperties 14 }

    logPropProfileForCommandAo OBJECT-TYPE
        SYNTAX  LogProfile
        ACCESS  read-write
        STATUS  mandatory
        DESCRIPTION
            "Identifier specifying which logging profile should be used for
            SMS commands application originated.
            The value 1000 (i.e. 'default') does not apply for this object."
        ::= { logProperties 15 }

    logPropProfileForMnpViolation OBJECT-TYPE
        SYNTAX  LogProfile
        ACCESS  read-write
        STATUS  mandatory
        DESCRIPTION
            "Identifier specifying which logging profile should be used for
            MNP violations.
            The value 1000 (i.e. 'default') does not apply for this object."
        ::= { logProperties 16 }

    logPropResetSequenceNumberOfLoggingProfileUponDestroy OBJECT-TYPE     
        SYNTAX  Boolean
        ACCESS  read-write
        STATUS  mandatory
        DESCRIPTION
            "Boolean specifying whether destroying a logging profile should 
            imply a reset of the associated sequence number in the permanent 
            storage that TextPass maintains for logging profile sequence 
            numbers. Default is 'true'.      
            The sequence number that is maintained for a logging profile is 
            (optionally) used in the names of the CDR files that are generated
            for the logging profile.
            Resetting the logging profile sequence number is required to
            ensure that a newly added logging profile that is mapped to a
            table index that has been used before has a properly initialised
            sequence number (rather than the sequence number of the logging
            profile that was mapped to the same table index before).
            The value 'false' is typically used when a logging profile is
            temporary removed. Not resetting the sequence number will then
            ensure that the sequence number after removal will commence from
            the value before the removal."
        ::= { logProperties 21 }

    logPropTransparentUserDataLevel OBJECT-TYPE
        SYNTAX  LogTransparentUserDataLevel
        ACCESS  read-write
        STATUS  mandatory
        DESCRIPTION
            "Identifier specifying in which cases the user data in log files 
            should be shown transparently. Default is 'always'."
        ::= { logProperties 101 }    
        
    logProfileTable OBJECT-TYPE
        SYNTAX  SEQUENCE OF LogProfileEntry
        ACCESS  not-accessible
        STATUS  mandatory
        DESCRIPTION
            "A table containing profiles for logging."
        ::= { sms 132 }

    logProfileEntry OBJECT-TYPE
        SYNTAX  LogProfileEntry
        ACCESS  not-accessible
        STATUS  mandatory
        DESCRIPTION
            "Table entry specifying a single logging profile."
        INDEX   { logProfileIndex }
        ::= { logProfileTable 1 }

    LogProfileEntry ::=
        SEQUENCE {
            logProfileIndex                       LogProfileTableIndex,
            logProfileAdminState                  AdminState,
            logProfileName                        NameString,
            logProfileLastIoError                 ErrorString,
            logProfileProcessingDirectory         FileSpec,
            logProfileFinishedDirectory           FileSpec,
            logProfileFileNameTemplate            FileSpec,
            logProfileMaxFileSize                 LogFileSize,
            logProfileMaxFileDuration             LogFileDuration,
            logProfileMaxFileRecords              LogFileRecords,
            logProfileFileFormat                  LogFileFormat,
            logProfileStartingSequenceNumber      Gauge,
            logProfileAffectedMessageTypes        LogAffectedMessageTypes,
            logProfileSuspectAndTrustedMessages   LogSuspectAndTrustedMessages,
            logProfileFailedAndSucceededMessages  LogFailedAndSucceededMessages,
            logProfileAcceptedAndRejectedMessages LogAcceptedAndRejectedMessages,
            logProfileLegitimateAndViolatedMessages LogLegitimateAndViolatedMessages,
            logProfileExpirdDltdRplacdMessageTypes  LogExpirdDltdRplacdMessageTypes,
            logProfileStatusReportMessageTypes    LogStatusReportMessageTypes,
            logProfileCopiedForwardedMessageTypes LogCopiedForwardedMessageTypes,
            logProfileCopy1OfFinishedDirectory    FileSpec,
            logProfileCopy2OfFinishedDirectory    FileSpec,
            logProfileCopy3OfFinishedDirectory    FileSpec,
            logProfileCopy4OfFinishedDirectory    FileSpec,
            logProfileCopy5OfFinishedDirectory    FileSpec,
            logProfileCopy6OfFinishedDirectory    FileSpec,
            logProfileCopy7OfFinishedDirectory    FileSpec,
            logProfileCopy8OfFinishedDirectory    FileSpec,
            logProfileCopy9OfFinishedDirectory    FileSpec
        }

    logProfileIndex OBJECT-TYPE
        SYNTAX  LogProfileTableIndex
        ACCESS  read-write
        STATUS  mandatory
        DESCRIPTION
            "Index of entry in logging profile table."
        ::= { logProfileEntry 1 }

    logProfileAdminState OBJECT-TYPE
        SYNTAX  AdminState
        ACCESS  read-write
        STATUS  mandatory
        DESCRIPTION
            "Administrative state of logging profile."
        ::= { logProfileEntry 2 }

    logProfileName OBJECT-TYPE
        SYNTAX  NameString
        ACCESS  read-write
        STATUS  mandatory
        DESCRIPTION
            "Name of logging profile."
        ::= { logProfileEntry 3 }

    logProfileLastIoError OBJECT-TYPE
        SYNTAX  ErrorString
        ACCESS  read-write
        STATUS  mandatory
        DESCRIPTION
            "Information about last I/O error that occurred for the 
            logging profile. The information comprises timestamp, file name,
            and error description."
        ::= { logProfileEntry 4 }

    logProfileProcessingDirectory OBJECT-TYPE
        SYNTAX  FileSpec
        ACCESS  read-write
        STATUS  mandatory
        DESCRIPTION
            "Specification of the directory which is used for the logging
            files during the creation of these files. Default is
            /var/TextPass/log/processing.
            Note: this setting can only be changed when the device adminState
            is disabled."
        ::= { logProfileEntry 11 }

    logProfileFinishedDirectory OBJECT-TYPE
        SYNTAX  FileSpec
        ACCESS  read-write
        STATUS  mandatory
        DESCRIPTION
            "Specification of the directory where the logging files are stored
            when they are completed. This directory should be on the same disc
            partition as the logProfileProcessingDirectory.
            Default is /var/TextPass/log/available.
            Note: this setting can only be changed when the device adminState
            is disabled."
        ::= { logProfileEntry 12 }

    logProfileFileNameTemplate OBJECT-TYPE
        SYNTAX  FileSpec
        ACCESS  read-write
        STATUS  mandatory
        DESCRIPTION
            "String specifying the format for the name of the logging file.
            The following format specifiers are supported:
            %Y - year specified in four digits (e.g. 2004)
            %y - year specified in two digits (e.g. 04)
            %m - month specified in two digits (e.g. 01 for Jan, 10 for Oct)
            %d - day specified in two digits (e.g 01 for 1st day of month, 31
                                              for last day of month)
            %H - hour specified in two digits (e.g 00 for midnight, 12 for
                                               noon)
            %M - minute specified in two digits
            %S - second specified in two digits
            %h - hostname
            %1 - a one-digit sequence number
            %2 - a two-digit sequence number
            %3 - a three-digit sequence number
            %4 - a four-digit sequence number
            %5 - a five-digit sequence number
            %6 - a six-digit sequence number
            %7 - a seven-digit sequence number
            %8 - a eight-digit sequence number

            Default is: log_%h_%Y%m%d_%H%M%S_%3.dat"
        ::= { logProfileEntry 13 }

    logProfileMaxFileSize OBJECT-TYPE
        SYNTAX  LogFileSize
        ACCESS  read-write
        STATUS  mandatory
        DESCRIPTION
            "Specification of maximum length, expressed in bytes, for a
            logging file. Default is 1M."
        ::= { logProfileEntry 14 }

    logProfileMaxFileDuration OBJECT-TYPE
        SYNTAX  LogFileDuration
        ACCESS  read-write
        STATUS  mandatory
        DESCRIPTION
            "Specification of maximum duration, expressed in seconds, for a
            logging file. Default is 1 hour."
        ::= { logProfileEntry 15 }

    logProfileMaxFileRecords OBJECT-TYPE
        SYNTAX  LogFileRecords
        ACCESS  read-write
        STATUS  mandatory
        DESCRIPTION
            "Specification of maximum number of records in a logging file.
            Default is 10000."
        ::= { logProfileEntry 16 }

    logProfileFileFormat OBJECT-TYPE
        SYNTAX  LogFileFormat
        ACCESS  read-write
        STATUS  mandatory
        DESCRIPTION
            "Format of logging file. Default is
            'asn1ExtendedWithCountryAndNetworkInfo'."
        ::= { logProfileEntry 17 }

    logProfileStartingSequenceNumber OBJECT-TYPE
        SYNTAX  Gauge
        ACCESS  read-write
        STATUS  mandatory
        DESCRIPTION
            "Start of range of sequence numbers to be used in the logging
            file name. Default is 0."
        ::= { logProfileEntry 18 }

    logProfileAffectedMessageTypes OBJECT-TYPE
        SYNTAX  LogAffectedMessageTypes
        ACCESS  read-write
        STATUS  mandatory
        DESCRIPTION
            "Bitstring specifying the message types for which this profile
            applies."
        ::= { logProfileEntry 21 }

    logProfileSuspectAndTrustedMessages OBJECT-TYPE
        SYNTAX  LogSuspectAndTrustedMessages
        ACCESS  read-write
        STATUS  mandatory
        DESCRIPTION
            "Identifier specifying whether suspect and/or trusted messages
            should be logged. Default value is: 'suspectAndTrusted'."
        ::= { logProfileEntry 22 }

    logProfileFailedAndSucceededMessages OBJECT-TYPE
        SYNTAX  LogFailedAndSucceededMessages
        ACCESS  read-write
        STATUS  mandatory
        DESCRIPTION
            "Identifier specifying whether failed and/or succeeded messages
            should be logged. Default value is: 'failedAndSucceeded'."
        ::= { logProfileEntry 23 }

    logProfileAcceptedAndRejectedMessages OBJECT-TYPE
        SYNTAX  LogAcceptedAndRejectedMessages
        ACCESS  read-write
        STATUS  mandatory
        DESCRIPTION
            "Identifier specifying whether accepted and/or rejected messages
            should be logged. Default value is: 'acceptedAndRejected'."
        ::= { logProfileEntry 24 }

    logProfileLegitimateAndViolatedMessages OBJECT-TYPE
        SYNTAX  LogLegitimateAndViolatedMessages
        ACCESS  read-write
        STATUS  mandatory
        DESCRIPTION
            "Identifier specifying whether legitimate and/or violated messages
            should be logged. Default value is: 'legitimateAndViolated'."
        ::= { logProfileEntry 25 }

    logProfileExpirdDltdRplacdMessageTypes OBJECT-TYPE
        SYNTAX  LogExpirdDltdRplacdMessageTypes
        ACCESS  read-write
        STATUS  mandatory
        DESCRIPTION
            "Bitstring specifying the message types for which this profile
            applies."
        ::= { logProfileEntry 26 }

    logProfileStatusReportMessageTypes OBJECT-TYPE
        SYNTAX  LogStatusReportMessageTypes
        ACCESS  read-write
        STATUS  mandatory
        DESCRIPTION
            "Bitstring specifying the message types for which this profile
            applies."
        ::= { logProfileEntry 27 }

    logProfileCopiedForwardedMessageTypes OBJECT-TYPE
        SYNTAX  LogCopiedForwardedMessageTypes
        ACCESS  read-write
        STATUS  mandatory
        DESCRIPTION
            "Bitstring specifying the message types for which this profile
            applies."
        ::= { logProfileEntry 28 }

    logProfileCopy1OfFinishedDirectory OBJECT-TYPE
        SYNTAX  FileSpec
        ACCESS  read-write
        STATUS  mandatory
        DESCRIPTION
            "Specification of a directory in which to create hard links to
            the finished logging files. A hard link is created at the time
            that the logging file is moved from the processing directory to
            the finished directory. 
            The default for this specification is a zero-length string, which 
            implies that no hard links are to be created.
            When a directory is specified, it should reside on the same disc
            partition as the logProfileProcessingDirectory and 
            logProfileFinishedDirectory.
            Note: this setting can only be changed when the device adminState
            is disabled."
        ::= { logProfileEntry 501 }

    logProfileCopy2OfFinishedDirectory OBJECT-TYPE
        SYNTAX  FileSpec
        ACCESS  read-write
        STATUS  mandatory
        DESCRIPTION
            "Specification of a directory in which to create hard links to
            the finished logging files. A hard link is created at the time
            that the logging file is moved from the processing directory to
            the finished directory. 
            The default for this specification is a zero-length string, which 
            implies that no hard links are to be created.
            When a directory is specified, it should reside on the same disc
            partition as the logProfileProcessingDirectory and 
            logProfileFinishedDirectory.
            Note: this setting can only be changed when the device adminState
            is disabled."
        ::= { logProfileEntry 502 }

    logProfileCopy3OfFinishedDirectory OBJECT-TYPE
        SYNTAX  FileSpec
        ACCESS  read-write
        STATUS  mandatory
        DESCRIPTION
            "Specification of a directory in which to create hard links to
            the finished logging files. A hard link is created at the time
            that the logging file is moved from the processing directory to
            the finished directory. 
            The default for this specification is a zero-length string, which 
            implies that no hard links are to be created.
            When a directory is specified, it should reside on the same disc
            partition as the logProfileProcessingDirectory and 
            logProfileFinishedDirectory.
            Note: this setting can only be changed when the device adminState
            is disabled."
        ::= { logProfileEntry 503 }

    logProfileCopy4OfFinishedDirectory OBJECT-TYPE
        SYNTAX  FileSpec
        ACCESS  read-write
        STATUS  mandatory
        DESCRIPTION
            "Specification of a directory in which to create hard links to
            the finished logging files. A hard link is created at the time
            that the logging file is moved from the processing directory to
            the finished directory. 
            The default for this specification is a zero-length string, which 
            implies that no hard links are to be created.
            When a directory is specified, it should reside on the same disc
            partition as the logProfileProcessingDirectory and 
            logProfileFinishedDirectory.
            Note: this setting can only be changed when the device adminState
            is disabled."
        ::= { logProfileEntry 504 }

    logProfileCopy5OfFinishedDirectory OBJECT-TYPE
        SYNTAX  FileSpec
        ACCESS  read-write
        STATUS  mandatory
        DESCRIPTION
            "Specification of a directory in which to create hard links to
            the finished logging files. A hard link is created at the time
            that the logging file is moved from the processing directory to
            the finished directory. 
            The default for this specification is a zero-length string, which 
            implies that no hard links are to be created.
            When a directory is specified, it should reside on the same disc
            partition as the logProfileProcessingDirectory and 
            logProfileFinishedDirectory.
            Note: this setting can only be changed when the device adminState
            is disabled."
        ::= { logProfileEntry 505 }

    logProfileCopy6OfFinishedDirectory OBJECT-TYPE
        SYNTAX  FileSpec
        ACCESS  read-write
        STATUS  mandatory
        DESCRIPTION
            "Specification of a directory in which to create hard links to
            the finished logging files. A hard link is created at the time
            that the logging file is moved from the processing directory to
            the finished directory. 
            The default for this specification is a zero-length string, which 
            implies that no hard links are to be created.
            When a directory is specified, it should reside on the same disc
            partition as the logProfileProcessingDirectory and 
            logProfileFinishedDirectory.
            Note: this setting can only be changed when the device adminState
            is disabled."
        ::= { logProfileEntry 506 }

    logProfileCopy7OfFinishedDirectory OBJECT-TYPE
        SYNTAX  FileSpec
        ACCESS  read-write
        STATUS  mandatory
        DESCRIPTION
            "Specification of a directory in which to create hard links to
            the finished logging files. A hard link is created at the time
            that the logging file is moved from the processing directory to
            the finished directory. 
            The default for this specification is a zero-length string, which 
            implies that no hard links are to be created.
            When a directory is specified, it should reside on the same disc
            partition as the logProfileProcessingDirectory and 
            logProfileFinishedDirectory.
            Note: this setting can only be changed when the device adminState
            is disabled."
        ::= { logProfileEntry 507 }

    logProfileCopy8OfFinishedDirectory OBJECT-TYPE
        SYNTAX  FileSpec
        ACCESS  read-write
        STATUS  mandatory
        DESCRIPTION
            "Specification of a directory in which to create hard links to
            the finished logging files. A hard link is created at the time
            that the logging file is moved from the processing directory to
            the finished directory. 
            The default for this specification is a zero-length string, which 
            implies that no hard links are to be created.
            When a directory is specified, it should reside on the same disc
            partition as the logProfileProcessingDirectory and 
            logProfileFinishedDirectory.
            Note: this setting can only be changed when the device adminState
            is disabled."
        ::= { logProfileEntry 508 }

    logProfileCopy9OfFinishedDirectory OBJECT-TYPE
        SYNTAX  FileSpec
        ACCESS  read-write
        STATUS  mandatory
        DESCRIPTION
            "Specification of a directory in which to create hard links to
            the finished logging files. A hard link is created at the time
            that the logging file is moved from the processing directory to
            the finished directory. 
            The default for this specification is a zero-length string, which 
            implies that no hard links are to be created.
            When a directory is specified, it should reside on the same disc
            partition as the logProfileProcessingDirectory and 
            logProfileFinishedDirectory.
            Note: this setting can only be changed when the device adminState
            is disabled."
        ::= { logProfileEntry 509 }


    smsEventProperties OBJECT IDENTIFIER ::= { sms 133 }

    smsEventPropRogueTcapMessages OBJECT-TYPE
        SYNTAX  EventProfile
        ACCESS  read-write
        STATUS  mandatory
        DESCRIPTION
            "Identifier specifying which event logging profile should be used
            for rogue (i.e. unexpected) TCAP messages. Default is 0 for
            disabled"
        ::= { smsEventProperties 11 }

    --------------------------------------------------------------------------

    atiRtgRuleTable OBJECT-TYPE
        SYNTAX  SEQUENCE OF AtiRtgRuleEntry
        ACCESS  not-accessible
        STATUS  mandatory
        DESCRIPTION
            "A table containing properties, conditions, counters and action
            parameters for each ATI routing rule.

            An ATI routing rule matches when both of the following conditions
            are met:
            1) its administrative state is active;
            2) all of its conditions are met;

            In case multiple rules match, the priority of the ATI routing rule
            determines which rule applies. When multiple rules have the same
            priority, the ATI routing rule with the lowest index has
            precedence."
        ::= { sms 141 }

    atiRtgRuleEntry OBJECT-TYPE
        SYNTAX  AtiRtgRuleEntry
        ACCESS  not-accessible
        STATUS  mandatory
        DESCRIPTION
            "Table entry specifying a single ATI routing rule."
        INDEX   { atiRtgRuleIndex }
        ::= { atiRtgRuleTable 1 }

    AtiRtgRuleEntry ::=
        SEQUENCE {
            atiRtgRuleIndex                        AtiRuleTableIndex,
            atiRtgRuleAdminState                   AdminState,
            atiRtgRuleName                         NameString,
            atiRtgRulePriority                     Priority,
            atiRtgRuleLogProfile                   LogProfile,
            atiRtgRuleAppliedCounter               Counter,
            atiRtgRuleModifier                     AtModifierRef,
            atiRtgRuleAction                       AtiAction,
            atiRtgRuleDestinationApplication       AtiDestinationApplication,
            atiRtgRuleSpecifiedApplication         ApplicationTableIndex,
            atiRtgRuleAmsQueue                     AmsQueueIndex,
            atiRtgRuleAtAoSmscGroupIndex           SmscGroupIndex,
            atiRtgRuleApplicationCondition         ConditionSpec,
            atiRtgRuleApplicationGroupCondition    ConditionSpec,
            atiRtgRuleApplicationCategoryCondition ConditionSpec,
            atiRtgRuleServiceClassCondition        ConditionSpec,
            atiRtgRuleProtocolCondition            ConditionSpec,
            atiRtgRuleOperationCondition           ConditionSpec,
            atiRtgRuleOriginatorCondition          ConditionSpec,
            atiRtgRuleOriginatorTonCondition       ConditionSpec,
            atiRtgRuleOriginatorNpiCondition       ConditionSpec,
            atiRtgRuleRecipientCondition           ConditionSpec,
            atiRtgRuleRecipientTonCondition        ConditionSpec,
            atiRtgRuleRecipientNpiCondition        ConditionSpec,
            atiRtgRuleServiceCentreCondition       ConditionSpec,
            atiRtgRuleUserDataCondition            ConditionSpec,
            atiRtgRuleUserDataHeaderIndicationCondition ConditionSpec,
            atiRtgRuleUserDataHeaderCondition      ConditionSpec,
            atiRtgRuleMoreMessagesToSendCondition  ConditionSpec,
            atiRtgRulePriorityCondition            ConditionSpec,
            atiRtgRuleProtocolIdCondition          ConditionSpec,
            atiRtgRuleDataCodingSchemeCondition    ConditionSpec,
            atiRtgRuleMessageSegmentTypeCondition  ConditionSpec,
            atiRtgRuleScTimestampCondition         ConditionSpec,
            atiRtgRuleDeliveryStatusCondition      ConditionSpec,
            atiRtgRuleDeliveryTimestampCondition   ConditionSpec,
            atiRtgRuleExternalAttributesCondition  ConditionSpec,
            atiRtgRuleMessageTypeCondition         ConditionSpec
        }

    atiRtgRuleIndex OBJECT-TYPE
        SYNTAX  AtiRuleTableIndex
        ACCESS  read-write
        STATUS  mandatory
        DESCRIPTION
            "Index of entry in ATI routing rule table."
        ::= { atiRtgRuleEntry 1 }

    atiRtgRuleAdminState OBJECT-TYPE
        SYNTAX  AdminState
        ACCESS  read-write
        STATUS  mandatory
        DESCRIPTION
            "Administrative state of the ATI routing rule.

            Transition from 'inactive' to 'active' is only possible when:
            1) name has been supplied;
            2) name is not already in use by another rule;
            3) conditions of rule specifying a network refer to an 'active'
               country and an 'active' network;
            4) conditions of rule specifying a country refer to an 'active'
               country;

            For details, refer to the comment on the AdminState type."
        ::= { atiRtgRuleEntry 2 }

    atiRtgRuleName OBJECT-TYPE
        SYNTAX  NameString
        ACCESS  read-write
        STATUS  mandatory
        DESCRIPTION
            "Name of the ATI routing rule."
        ::= { atiRtgRuleEntry 3 }

    atiRtgRulePriority OBJECT-TYPE
        SYNTAX  Priority
        ACCESS  read-write
        STATUS  mandatory
        DESCRIPTION
            "Priority of the ATI routing rule.

            For details, refer to the comment on the Priority type."
        ::= { atiRtgRuleEntry 4 }

    atiRtgRuleLogProfile OBJECT-TYPE
        SYNTAX  LogProfile
        ACCESS  read-write
        STATUS  mandatory
        DESCRIPTION
            "Identifier specifying which logging profile should be used.
            Default is 0 (i.e. 'none')."
        ::= { atiRtgRuleEntry 5 }

    atiRtgRuleAppliedCounter OBJECT-TYPE
        SYNTAX  Counter
        ACCESS  read-write
        STATUS  mandatory
        DESCRIPTION
            "Counter specifying the number of times that the routing rule
            has been applied."
        ::= { atiRtgRuleEntry 11 }

    atiRtgRuleModifier OBJECT-TYPE
        SYNTAX  AtModifierRef
        ACCESS  read-write
        STATUS  mandatory
        DESCRIPTION
            "Reference to a modifier on ATI routing rule modifiers applied
            post routing."
        ::= { atiRtgRuleEntry 20 }

    atiRtgRuleAction OBJECT-TYPE
        SYNTAX  AtiAction
        ACCESS  read-write
        STATUS  mandatory
        DESCRIPTION
            "Action to execute when the ATI routing rule applies.

            For details, refer to the comments on the AtiAction type."
        ::= { atiRtgRuleEntry 21 }

    atiRtgRuleDestinationApplication OBJECT-TYPE
        SYNTAX  AtiDestinationApplication
        ACCESS  read-write
        STATUS  mandatory
        DESCRIPTION
            "This object controls how the destination application
            is to be determined when the routing action is any of the
            following actions:

                - routeToApplication
                - routeToApplicationFallbackToStorage
                - StoreForDeliveryToApplication
                - routeToSmscAsAo
                - routeToSmscAsAoFallbackToStorage
                - storeForForwardingToSmscAsAo

            For all other actions, the object's value is ignored.

            The value of the object has the following meaning:

                - 'incomingApplication': The destination application
                  is equal to the application, for which the AT message
                  has been received. This is the default value.
                - 'recipientBasedApplication': The destination application
                  is based on analysis of the recipient number in the SM.
                  The router will consult the provisioned
                  recipientShortNumberLists and the applicationAliases.
                - 'specifiedApplication': The destination application
                  is an application specified by the routing rule itself.
                - 'icacheApplication' : The destination application
                  is provided by Icache."
        ::= { atiRtgRuleEntry 22 }

    atiRtgRuleSpecifiedApplication OBJECT-TYPE
        SYNTAX  ApplicationTableIndex
        ACCESS  read-write
        STATUS  mandatory
        DESCRIPTION
            "This object specifies which destination application is to
            be used for delivering an incoming AT message. The object is
            ignored unless the atiRtgRuleDestinationApplication is set
            to 'specifiedApplication', in which case the value of the
            object must not be 0. By default, the object is set to 0."
        ::= { atiRtgRuleEntry 23 }

    atiRtgRuleAmsQueue OBJECT-TYPE
        SYNTAX  AmsQueueIndex
        ACCESS  read-write
        STATUS  mandatory
        DESCRIPTION
            "This object specifies the AMS queue in which an incoming
            AT message is to be stored in case of any of the following
            routing actions:

                - routeToApplicationFallbackToStorage
                - storeForDeliveryToApplication

            In these cases, the object's value must not be 0.
            For all other actions, the object's value is ignored.

            By default, the object is set to 0."
        ::= { atiRtgRuleEntry 24 }

    atiRtgRuleAtAoSmscGroupIndex OBJECT-TYPE
        SYNTAX  SmscGroupIndex
        ACCESS  read-write
        STATUS  mandatory
        DESCRIPTION
            "Specifier of an SMSC group.

            The type of the SMSC group should be 'ao'.

            Mandatory if the routing action is routeToSmscAsAo,
            routeToSmscAsAoFallbackToStorage or storeForDeliveryToSmscAsAo."
        ::= { atiRtgRuleEntry 25 }

    atiRtgRuleApplicationCondition OBJECT-TYPE
        SYNTAX  ConditionSpec
        ACCESS  read-write
        STATUS  mandatory
        DESCRIPTION
            "Condition pertaining to the application for which the AT
            message has been received. For the specification for this
            condition, the following formats apply:

            1) NONE
            2) APPLICATION

            Note that for this condition, the condition spec variant
            'by-name' is not supported, only 'by-index'.

            For details on these formats, refer to the comment on the
            ConditionSpec type."
        ::= { atiRtgRuleEntry 31 }

    atiRtgRuleApplicationGroupCondition OBJECT-TYPE
        SYNTAX  ConditionSpec
        ACCESS  read-write
        STATUS  mandatory
        DESCRIPTION
            "Condition pertaining to the application group associated with
            the application for which the AT message has been received.
            For the specification for this condition, the following formats
            apply:

            1) NONE
            2) BITSTRING

            When the format is BITSTRING, the relating bit string specifies
            which application groups apply. Each bit in the bit string
            relates to a specific application group. If the bit is 1, the
            application group applies. Otherwise, if the bit is 0, the
            application group does not apply. Up to 1000 application
            groups can be defined. As such, the bit string consists of 1000
            bits with the least significant (last) bit indicating whether
            application group with SNMP index 1 applies and the most
            significant (first) bit indicating whether application group with
            SNMP index 1000 applies.

            For further details on these formats, refer to the comment on the
            ConditionSpec type."
        ::= { atiRtgRuleEntry 32 }

    atiRtgRuleApplicationCategoryCondition OBJECT-TYPE
        SYNTAX  ConditionSpec
        ACCESS  read-write
        STATUS  mandatory
        DESCRIPTION
            "Condition pertaining to the application categories associated
            with the application for which the AT message has been received.
            For the specification of this condition, the following formats
            apply:

            1) NONE
            2) BITSTRING

            When the format is BITSTRING, the relating bit string specifies
            which application categories apply. Each bit in the bit string
            relates to a specific application category. If the bit is 1, the
            application category applies. Otherwise, if the bit is 0, the
            application category does not apply. Up to 1000 application
            categories can be defined. As such, the bit string consists of
            1000 bits with the least significant (last) bit indicating whether
            application category with SNMP index 1 applies and the most
            significant (first) bit indicating whether application category
            with SNMP index 1000 applies.

            The condition evaluates to true is at least one application
            category of the application, for which the AT message has been
            received, is specified in this conditions specification.

            For further details on these formats, refer to the comment on the
            ConditionSpec type."
        ::= { atiRtgRuleEntry 33 }

    atiRtgRuleServiceClassCondition OBJECT-TYPE
        SYNTAX  ConditionSpec
        ACCESS  read-write
        STATUS  mandatory
        DESCRIPTION
            "Condition pertaining to the service class associated with the
            application for which the AT message has been received. For the
            specification of this condition, the following formats apply:

            1) NONE
            2) BITSTRING

            When the format is BITSTRING, the relating bit string specifies
            which service classes apply. Each bit in the bit string relates
            to a specific service class. If the bit is 1, the service class
            applies. Otherwise, if the bit is 0, the service class does not
            apply. Up to 1000 service classes can be defined. As such, the
            bit string consists of 1000 bits with the least significant
            (last) bit indicating whether service class with SNMP index 1
            applies and the most significant (fist) bit indicating whether
            service class with SNMP index 1000 applies.

            For further details on these formats, refer to the comment on the
            ConditionSpec type."
        ::= { atiRtgRuleEntry 34 }

    atiRtgRuleProtocolCondition OBJECT-TYPE
        SYNTAX  ConditionSpec
        ACCESS  read-write
        STATUS  mandatory
        DESCRIPTION
            "Condition pertaining to the protocol used when receiving the AT
            message. For the specification of this condition, the following
            formats apply:

            1) NONE
            2) BITSTRING

            When the format is BITSTRING, the relating bit string specifies
            which protocols apply. Each bit in the bit string relates to a
            specific protocol. If the bit is 1, the protocol applies.
            Otherwise, if the bit is 0, the protocol does not apply. The bit
            string consists of 3 bits and has the following mapping:

              -------------
              bit  protocol
              -------------
               0   UCP
               1   SMPP
               2   CIMD
              -------------

            Note that bit 0 is the least significant (last) bit and bit 2 is
            the most significant (first) bit in the bitstring.

            For further details on these formats, refer to the comment on the
            ConditionSpec type."
        ::= { atiRtgRuleEntry 35 }

    atiRtgRuleOperationCondition OBJECT-TYPE
        SYNTAX  ConditionSpec
        ACCESS  read-write
        STATUS  mandatory
        DESCRIPTION
            "Condition pertaining to the operation used when receiving the AT
            message. For the specification for this condition, the following
            formats apply:

            1) NONE
            2) BITSTRING

            When the format is BITSTRING, the relating bit string specifies
            which operations apply. Not all bits of the bit string are used.
            Each bit in the bit string that is used relates to a specific
            operation. If the bit is 1, the operation applies. Otherwise, if
            the bit is 0, the operation does not apply. The bit string
            consists of 32 bits and has the following mapping:

              ---------------------------------------------------------------
              bit  operation
              ---------------------------------------------------------------
               0   UCP Call input operation -01
               5   UCP Deliver Short Message operation -52
               6   UCP Deliver Notification operation -53
               9   UCP operation other than the ones above
               11  SMPP DeliverSm
               13  SMPP DataSm
               19  SMPP operation other than the ones above
               21  CIMD DeliverMessage
               22  CIMD DeliverStatusReport
               29  CIMD operation other than the ones above
               30  operation from another protocol than UCP, SMPP and CIMD
              --------------------------------------------------------------

            Note that bit 0 is the least significant (last) bit and bit 31 is
            the most significant (first) bit.

            For further details on these formats, refer to the comment on the
            ConditionSpec type."
        ::= { atiRtgRuleEntry 36 }

    atiRtgRuleOriginatorCondition OBJECT-TYPE
        SYNTAX  ConditionSpec
        ACCESS  read-write
        STATUS  mandatory
        DESCRIPTION
            "Condition pertaining to the originator that is specified in the
            SM. For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST
            12) ALPHANUMADDRESS

            For details on these formats, refer to the comment on the
            ConditionSpec type."
        ::= { atiRtgRuleEntry 37 }

    atiRtgRuleOriginatorTonCondition OBJECT-TYPE
        SYNTAX  ConditionSpec
        ACCESS  read-write
        STATUS  mandatory
        DESCRIPTION
            "Condition pertaining to the type of number (TON) specified for
            the originator of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant (last) bit
            indicating whether TON value 0 applies and the most significant
            (first) bit indicating whether TON value 7 applies.

            For further details on these formats, refer to the comment on the
            ConditionSpec type.

            For details on the values supported for the TON, refer to 3GPP
            23.040."
        ::= { atiRtgRuleEntry 38 }

    atiRtgRuleOriginatorNpiCondition OBJECT-TYPE
        SYNTAX  ConditionSpec
        ACCESS  read-write
        STATUS  mandatory
        DESCRIPTION
            "Condition pertaining to the numbering plan identification (NPI)
            specified for the originator of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant (last) bit
            indicating whether NPI value 0 applies and the most significant
            (first) bit indicating whether NPI value 15 applies.

            For further details on these formats, refer to the comment on the
            ConditionSpec type.

            For details on the values supported for the NPI, refer to 3GPP
            23.040."
        ::= { atiRtgRuleEntry 39 }

    atiRtgRuleRecipientCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST
            12) ALPHANUMADDRESS

            For details on these formats, refer to the comment on the
            ConditionSpec type."
        ::= { atiRtgRuleEntry 40 }

    atiRtgRuleRecipientTonCondition OBJECT-TYPE
        SYNTAX  ConditionSpec
        ACCESS  read-write
        STATUS  mandatory
        DESCRIPTION
            "Condition pertaining to the type of number (TON) specified for
            the recipient of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant (last) bit
            indicating whether TON value 0 applies and the most significant
            (first) bit indicating whether TON value 7 applies.

            For further details on these formats, refer to the comment on the
            ConditionSpec type.

            For details on the values supported for the TON, refer to 3GPP
            23.040."
        ::= { atiRtgRuleEntry 41 }

    atiRtgRuleRecipientNpiCondition OBJECT-TYPE
        SYNTAX  ConditionSpec
        ACCESS  read-write
        STATUS  mandatory
        DESCRIPTION
            "Condition pertaining to the numbering plan identification (NPI)
            specified for the recipient of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant (last) bit
            indicating whether NPI value 0 applies and the most significant
            (first) bit indicating whether NPI value 15 applies.

            For further details on these formats, refer to the comment on the
            ConditionSpec type.

            For details on the values supported for the NPI, refer to 3GPP
            23.040."
        ::= { atiRtgRuleEntry 42 }

    atiRtgRuleServiceCentreCondition OBJECT-TYPE
        SYNTAX  ConditionSpec
        ACCESS  read-write
        STATUS  mandatory
        DESCRIPTION
            "Condition pertaining to the serviceCentre, from which the AT
            message has been received. For the specification of this
            condition, the following formats apply:

            1) NONE
            2) BITSTRING

            When the format is BITSTRING, the relating bit string specifies
            which service centres apply. Each bit in the bit string
            relates to a specific service centre. If the bit is 1, the
            service centre applies. Otherwise, if the bit is 0, the
            service centre does not apply. Up to 250 service centres can be
            defined. As such, the bit string consists of 250 bits with the
            least significant (last) bit indicating whether the service
            centre with SNMP index 1 applies and the most significant
            (first) bit indicating whether the service centre with SNMP
            index 250 applies.

            For details on these formats, refer to the comment on the
            ConditionSpec type."
        ::= { atiRtgRuleEntry 43 }

    atiRtgRuleUserDataCondition OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT
            5) TEXTLENGTH

            Note: this condition only supports the UTF-8-based condition
                  specs, and not the ASCII-based ones.

            For details on these formats, refer to the comment on the
            ConditionSpec type."
        ::= { atiRtgRuleEntry 44 }

    atiRtgRuleUserDataHeaderIndicationCondition OBJECT-TYPE
        SYNTAX  ConditionSpec
        ACCESS  read-write
        STATUS  mandatory
        DESCRIPTION
            "Condition pertaining to the user data header indication specified
            in the SM. For the specification for this condition, the following
            formats apply:

            1) NONE
            2) BITVALUE

            For details on these formats, refer to the comment on the
            ConditionSpec type."
        ::= { atiRtgRuleEntry 45 }

    atiRtgRuleUserDataHeaderCondition OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to 3GPP 23.040. The
            values for most common information element identifiers are:

            00 hex - Concatenated short message
            01 hex - Special SMS Message Indication
            04 hex - application port addressing scheme, 8 bit address
            05 hex - application port addressing scheme, 16 bit address
            06 hex - SMSC Control Parameters
            07 hex - UDH Source Indicator "
        ::= { atiRtgRuleEntry 46 }

    atiRtgRuleMoreMessagesToSendCondition OBJECT-TYPE
        SYNTAX  ConditionSpec
        ACCESS  read-write
        STATUS  mandatory
        DESCRIPTION
            "Condition pertaining to the more messages to send indicator
            specified in the SM. For the specification of this condition, the
            following formats apply:

            1) NONE
            2) BITVALUE

            For details on these formats, refer to the comment on the
            ConditionSpec type."
        ::= { atiRtgRuleEntry 47 }

    atiRtgRulePriorityCondition OBJECT-TYPE
        SYNTAX  ConditionSpec
        ACCESS  read-write
        STATUS  mandatory
        DESCRIPTION
            "Condition pertaining to the priority level that is specified in
            the SM. For the specification of this condition, the following
            formats apply:

            1) NONE
            2) BITSTRING

            When the format is BITSTRING, the relating bit string specifies
            which priority levels apply. Not all bits of the bit string are
            used. Each bit in the bit string that is used relates to a
            specific priority level. If the bit is 1, the priority level
            applies.
            Otherwise, if the bit is 0, the priority level does not apply. The
            bit string consists of 32 bits and has the following mapping:

              ---------------------------------------------------------------
              bit  operation
              ---------------------------------------------------------------
               10  SMPP no priority requested
               11  SMPP priority requested
              --------------------------------------------------------------

            Note that bit 0 is the least significant (last) bit and bit 31 is
            the most significant (first) bit.

            For further details on these formats, refer to the comment on the
            ConditionSpec type."
        ::= { atiRtgRuleEntry 48 }

    atiRtgRuleProtocolIdCondition OBJECT-TYPE
        SYNTAX  ConditionSpec
        ACCESS  read-write
        STATUS  mandatory
        DESCRIPTION
            "Condition pertaining to the protocol ID specified in the SM. For
            the specification of this condition, the following formats apply:

            1) NONE
            2) BYTEVALUE

            For details on these formats, refer to the comment on the
            ConditionSpec type.

            For details on the values supported for the protocol ID, refer to
            3GPP 23.040."
        ::= { atiRtgRuleEntry 49 }

    atiRtgRuleDataCodingSchemeCondition OBJECT-TYPE
        SYNTAX  ConditionSpec
        ACCESS  read-write
        STATUS  mandatory
        DESCRIPTION
            "Condition pertaining to the data coding scheme specified in the
            SM. For the specification of this condition, the following
            formats apply:

            1) NONE
            2) BYTEVALUE

            For details on these formats, refer to the comment on the
            ConditionSpec type.

            For details on the values supported for the data coding scheme,
            refer to 3GPP 23.040."
        ::= { atiRtgRuleEntry 50 }

    atiRtgRuleMessageSegmentTypeCondition OBJECT-TYPE
        SYNTAX  ConditionSpec
        ACCESS  read-write
        STATUS  mandatory
        DESCRIPTION
            "Condition pertaining to the segment sequence number of a
            concatenated SM. For the specification of this condition, the
            following formats apply:

            1) NONE
            2) BITSTRING

            When the format is BITSTRING, the relating bit string specifies
            which concatenated message segments apply. Each bit in the bit
            string relates to a specific segment of a concatenated message. If
            the bit is 1, the segment applies. Otherwise, if the bit is 0, the
            segment does not apply. The segments are categorised into three
            groups. As such, the bit string consists of 3 bits and has the
            following mapping:

                bit  segment group
                ------------------------------------------
                 0   first segment of a segmented message.
                 1   last segment of a segmented message.
                 2   nor the first nor the last segment
                     of a segmented message.
                ------------------------------------------

            Note that bit 0 is the least significant (last) bit and bit 2 is
            the most significant (first) bit.

            For further details on these formats, refer to the comment on the
            ConditionSpec type."
        ::= { atiRtgRuleEntry 51 }

    atiRtgRuleScTimestampCondition OBJECT-TYPE
        SYNTAX  ConditionSpec
        ACCESS  read-write
        STATUS  mandatory
        DESCRIPTION
            "Condition pertaining to the SC timestamp that is specified in
            the SM. For the specification of this condition, the following
            formats apply:

            1) NONE
            2) RELATIVETIME

            For details on these formats, refer to the comment on the
            ConditionSpec type."
        ::= { atiRtgRuleEntry 52 }

    atiRtgRuleDeliveryStatusCondition OBJECT-TYPE
        SYNTAX  ConditionSpec
        ACCESS  read-write
        STATUS  mandatory
        DESCRIPTION
            "Condition pertaining to the delivery status that is specified in
            a notification message. For the specification of this condition,
            the following formats apply:

            1) NONE
            2) BITSTRING

            When the format is BITSTRING, the relating bit string specifies
            which delivery status values match. Each bit in the bit string
            relates to a specific delivery status value. If the bit is 1, the
            corresponding delivery status value is checked against. Otherwise,
            if the bit is 0, the corresponding delivery status value is
            ignored.
            The bit string consists of 32 bits and has the following mapping:

              ---------------------------------------------------------------
              bit  address PID
              ---------------------------------------------------------------
               0   UCP: in progress
               1   UCP: delivery failed
               2   UCP: delivery successful
              10   SMPP: no status available
              11   SMPP: in progress
              12   SMPP: validity period expired
              13   SMPP: delivery failed
              14   SMPP: delivery successful
              15   SMPP: deleted
              16   SMPP: deleted by cancel
              17   SMPP: scheduled
              18   SMPP: accepted
              19   SMPP: rejected
              20   CIMD: no status available
              21   CIMD: in progress
              22   CIMD: validity period expired
              23   CIMD: delivery failed
              24   CIMD: delivery successful
              25   CIMD: no response
              26   CIMD: last no response
              27   CIMD: cancelled
              28   CIMD: deleted
              29   CIMD: deleted by cancel
              --------------------------------------------------------------

            Note that bit 0 is the least significant (last) bit and bit 2 is
            the most significant (first) bit.

            Note that if the AT message is not a notification message, and
            this condition has been specified, there corresponding rule will
            never match.

            For further details on these formats, refer to the comment on the
            ConditionSpec type."
        ::= { atiRtgRuleEntry 53 }

    atiRtgRuleDeliveryTimestampCondition OBJECT-TYPE
        SYNTAX  ConditionSpec
        ACCESS  read-write
        STATUS  mandatory
        DESCRIPTION
            "Condition pertaining to the delivery timestamp that is specified
            in the notification. For the specification of this condition,
            the following formats apply:

            1) NONE
            2) RELATIVETIME

            Note that if the AT message is not a notification message, and
            this condition has been specified, there corresponding rule will
            never match.

            For details on these formats, refer to the comment on the
            ConditionSpec type."
        ::= { atiRtgRuleEntry 54 }

    atiRtgRuleExternalAttributesCondition  OBJECT-TYPE
        SYNTAX  ConditionSpec
        ACCESS  read-write
        STATUS  mandatory
        DESCRIPTION
            "Condition on the 32 boolean atributes that can be set by an 
            EC application. For the specification of this condition, the
            following formats apply:

            1) NONE
            2) EXTERNALATTRIBUTES

            When the format is EXTERNALATTRIBUTES, the relating bit mask
            string specifies which external attributes apply and the relating
            bit value string specifies the values for the external
            attributes.
            Each bit in the bit strings relates to a specific attribute. The
            bit strings consist of 32 bits. The least significant (last) bit
            corresponds to attribute 0. The most significant (first) bit
            corresponds to attribute 31. 

            A bit with value 1 in the bit mask string indicates that the
            relating attribute applies and needs to be checked. A bit with
            value 0 in the bit mask string indicates that the relating
            attribute does not apply and does not need to be checked. 

            A bit with value 1 in the bit value string indicates that the
            relating attribute should be TRUE. A bit with value 0 in the bit
            value string indicates that the relating attribute should be
            FALSE.

            For further details on these formats, refer to the comment on the
            ConditionSpec type."
        ::= { atiRtgRuleEntry 55 }

    atiRtgRuleMessageTypeCondition OBJECT-TYPE
        SYNTAX  ConditionSpec
        ACCESS  read-write
        STATUS  mandatory
        DESCRIPTION
            "Condition pertaining to the message type applicable for this SM.
            For the specification of this condition, the following formats
            apply:

            1) NONE
            2) BITSTRING

            When the format is BITSTRING, the relating bit string specifies
            which values for the message type apply. Each bit in the bit
            string relates to a message type. If the bit is 1, the relating
            message type applies. Otherwise, if the bit is 0, the relating
            message type does not apply. The bit string consists of 2 bits
            and has the following mapping:

                ---------------------------
                bit  message type
                ---------------------------
                 0   normal AT message.
                 1   delivery notification.
                ---------------------------

            The bit string consists of 2 bits, with the least significant
            (last) bit indicating whether message type 0 applies and the
            most significant (first) bit indicating whether message type 2
            applies.

            For further details on these formats, refer to the comment on the
            ConditionSpec type."
        ::= { atiRtgRuleEntry 56 }

    -- AT incoming counting rules

    atiCntRuleTable OBJECT-TYPE
        SYNTAX  SEQUENCE OF AtiCntRuleEntry
        ACCESS  not-accessible
        STATUS  mandatory
        DESCRIPTION
            "A table containing properties, conditions and counters for each
            ATI counting rule.

            An ATI counting rule matches when both of the following conditions
            are met:
            1) its administrative state is active;
            2) all its conditions do satisfy."
        ::= { sms 142 }

    atiCntRuleEntry OBJECT-TYPE
        SYNTAX  AtiCntRuleEntry
        ACCESS  not-accessible
        STATUS  mandatory
        DESCRIPTION
            "Table entry specifying a single ATI counting rule."
        INDEX   { atiCntRuleIndex }
        ::= { atiCntRuleTable 1 }

    AtiCntRuleEntry ::=
        SEQUENCE {
            atiCntRuleIndex                        AtiRuleTableIndex,
            atiCntRuleAdminState                   AdminState,
            atiCntRuleName                         NameString,
            atiCntRuleLogProfile                   LogProfile,
            atiCntRuleTotalCounter                 Counter,
            atiCntRuleSuccessCounter               Counter,
            atiCntRuleTemporaryErrorCounter        Counter,
            atiCntRulePermanentMessageErrorCounter Counter,
            atiCntRulePermanentRecipientErrorCounter Counter,
            atiCntRuleApplicationCondition         ConditionSpec,
            atiCntRuleApplicationGroupCondition    ConditionSpec,
            atiCntRuleApplicationCategoryCondition ConditionSpec,
            atiCntRuleServiceClassCondition        ConditionSpec,
            atiCntRuleProtocolCondition            ConditionSpec,
            atiCntRuleOperationCondition           ConditionSpec,
            atiCntRuleOriginatorCondition          ConditionSpec,
            atiCntRuleOriginatorTonCondition       ConditionSpec,
            atiCntRuleOriginatorNpiCondition       ConditionSpec,
            atiCntRuleRecipientCondition           ConditionSpec,
            atiCntRuleRecipientTonCondition        ConditionSpec,
            atiCntRuleRecipientNpiCondition        ConditionSpec,
            atiCntRuleServiceCentreCondition       ConditionSpec,
            atiCntRuleUserDataCondition            ConditionSpec,
            atiCntRuleUserDataHeaderIndicationCondition ConditionSpec,
            atiCntRuleUserDataHeaderCondition      ConditionSpec,
            atiCntRuleMoreMessagesToSendCondition  ConditionSpec,
            atiCntRulePriorityCondition            ConditionSpec,
            atiCntRuleProtocolIdCondition          ConditionSpec,
            atiCntRuleDataCodingSchemeCondition    ConditionSpec,
            atiCntRuleMessageSegmentTypeCondition  ConditionSpec,
            atiCntRuleScTimestampCondition         ConditionSpec,
            atiCntRuleDeliveryStatusCondition      ConditionSpec,
            atiCntRuleDeliveryTimestampCondition   ConditionSpec,
            atiCntRuleExternalAttributesCondition  ConditionSpec,
            atiCntRuleMessageTypeCondition         ConditionSpec
        }

    atiCntRuleIndex OBJECT-TYPE
        SYNTAX  AtiRuleTableIndex
        ACCESS  read-write
        STATUS  mandatory
        DESCRIPTION
            "Index of entry in ATI counting rule table."
        ::= { atiCntRuleEntry 1 }

    atiCntRuleAdminState OBJECT-TYPE
        SYNTAX  AdminState
        ACCESS  read-write
        STATUS  mandatory
        DESCRIPTION
            "Administrative state of the ATI counting rule.

            Transition from 'inactive' to 'active' is only possible when:
            1) name has been supplied;
            2) name is not already in use by another rule;
            3) conditions of rule specifying a network refer to an 'active'
               country and an 'active' network;
            4) conditions of rule specifying a country refer to an 'active'
               country;

            For details, refer to the comment on the AdminState type."
        ::= { atiCntRuleEntry 2 }

    atiCntRuleName OBJECT-TYPE
        SYNTAX  NameString
        ACCESS  read-write
        STATUS  mandatory
        DESCRIPTION
            "Name of the ATI counting rule. Cannot be changed while the rule
            is active."
        ::= { atiCntRuleEntry 3 }

    atiCntRuleLogProfile OBJECT-TYPE
        SYNTAX  LogProfile
        ACCESS  read-write
        STATUS  mandatory
        DESCRIPTION
            "Identifier specifying which logging profile should be used.
            Default is 0 (i.e. 'none')."
        ::= { atiCntRuleEntry 5 }

    atiCntRuleTotalCounter OBJECT-TYPE
        SYNTAX  Counter
        ACCESS  read-write
        STATUS  mandatory
        DESCRIPTION
            "Counter specifying the number of times that a matching AT message
            was received on the RTR."
        ::= { atiCntRuleEntry 11 }

    atiCntRuleSuccessCounter OBJECT-TYPE
        SYNTAX  Counter
        ACCESS  read-write
        STATUS  mandatory
        DESCRIPTION
            "Counter specifying the number of times that a matching AT message
            was accepted."
        ::= { atiCntRuleEntry 12 }

    atiCntRuleTemporaryErrorCounter OBJECT-TYPE
        SYNTAX  Counter
        ACCESS  read-write
        STATUS  mandatory
        DESCRIPTION
            "Counter specifying the number of times that a matching AT message
            was rejected due to a 'temporary error'."
        ::= { atiCntRuleEntry 13 }

    atiCntRulePermanentMessageErrorCounter OBJECT-TYPE
        SYNTAX  Counter
        ACCESS  read-write
        STATUS  mandatory
        DESCRIPTION
            "Counter specifying the number of times that a matching AT message
            was rejected due to a 'permanent message error'."
        ::= { atiCntRuleEntry 14 }

    atiCntRulePermanentRecipientErrorCounter OBJECT-TYPE
        SYNTAX  Counter
        ACCESS  read-write
        STATUS  mandatory
        DESCRIPTION
            "Counter specifying the number of times that a matching AT message
            was rejected due to a 'permanent recipient error."
        ::= { atiCntRuleEntry 15 }

    atiCntRuleApplicationCondition OBJECT-TYPE
        SYNTAX  ConditionSpec
        ACCESS  read-write
        STATUS  mandatory
        DESCRIPTION
            "Condition pertaining to the application for which the AT
            message has been received. For the specification for this
            condition, the following formats apply:

            1) NONE
            2) APPLICATION

            Note that for this condition, the condition spec variant
            'by-name' is not supported, only 'by-index'.

            For details on these formats, refer to the comment on the
            ConditionSpec type."
        ::= { atiCntRuleEntry 31 }

    atiCntRuleApplicationGroupCondition OBJECT-TYPE
        SYNTAX  ConditionSpec
        ACCESS  read-write
        STATUS  mandatory
        DESCRIPTION
            "Condition pertaining to the application group associated with
            the application for which the AT message has been received.
            For the specification for this condition, the following formats
            apply:

            1) NONE
            2) BITSTRING

            When the format is BITSTRING, the relating bit string specifies
            which application groups apply. Each bit in the bit string
            relates to a specific application group. If the bit is 1, the
            application group applies. Otherwise, if the bit is 0, the
            application group does not apply. Up to 1000 application
            groups can be defined. As such, the bit string consists of 1000
            bits with the least significant (last) bit indicating whether
            application group with SNMP index 1 applies and the most
            significant (first) bit indicating whether application group with
            SNMP index 1000 applies.

            For further details on these formats, refer to the comment on the
            ConditionSpec type."
        ::= { atiCntRuleEntry 32 }

    atiCntRuleApplicationCategoryCondition OBJECT-TYPE
        SYNTAX  ConditionSpec
        ACCESS  read-write
        STATUS  mandatory
        DESCRIPTION
            "Condition pertaining to the application categories associated
            with the application for which the AT message has been received.
            For the specification of this condition, the following formats
            apply:

            1) NONE
            2) BITSTRING

            When the format is BITSTRING, the relating bit string specifies
            which application categories apply. Each bit in the bit string
            relates to a specific application category. If the bit is 1, the
            application category applies. Otherwise, if the bit is 0, the
            application category does not apply. Up to 1000 application
            categories can be defined. As such, the bit string consists of
            1000 bits with the least significant (last) bit indicating whether
            application category with SNMP index 1 applies and the most
            significant (first) bit indicating whether application category
            with SNMP index 1000 applies.

            The condition evaluates to true is at least one application
            category of the application, for which the AT message has been
            received, is specified in this conditions specification.

            For further details on these formats, refer to the comment on the
            ConditionSpec type."
        ::= { atiCntRuleEntry 33 }

    atiCntRuleServiceClassCondition OBJECT-TYPE
        SYNTAX  ConditionSpec
        ACCESS  read-write
        STATUS  mandatory
        DESCRIPTION
            "Condition pertaining to the service class associated with the
            application for which the AT message has been received. For the
            specification of this condition, the following formats apply:

            1) NONE
            2) BITSTRING

            When the format is BITSTRING, the relating bit string specifies
            which service classes apply. Each bit in the bit string relates
            to a specific service class. If the bit is 1, the service class
            applies. Otherwise, if the bit is 0, the service class does not
            apply. Up to 1000 service classes can be defined. As such, the
            bit string consists of 1000 bits with the least significant
            (last) bit indicating whether service class with SNMP index 1
            applies and the most significant (fist) bit indicating whether
            service class with SNMP index 1000 applies.

            For further details on these formats, refer to the comment on the
            ConditionSpec type."
        ::= { atiCntRuleEntry 34 }

    atiCntRuleProtocolCondition OBJECT-TYPE
        SYNTAX  ConditionSpec
        ACCESS  read-write
        STATUS  mandatory
        DESCRIPTION
            "Condition pertaining to the protocol used when receiving the AT
            message. For the specification of this condition, the following
            formats apply:

            1) NONE
            2) BITSTRING

            When the format is BITSTRING, the relating bit string specifies
            which protocols apply. Each bit in the bit string relates to a
            specific protocol. If the bit is 1, the protocol applies.
            Otherwise, if the bit is 0, the protocol does not apply. The bit
            string consists of 3 bits and has the following mapping:

              -------------
              bit  protocol
              -------------
               0   UCP
               1   SMPP
               2   CIMD
              -------------

            Note that bit 0 is the least significant (last) bit and bit 2 is
            the most significant (first) bit in the bitstring.

            For further details on these formats, refer to the comment on the
            ConditionSpec type."
        ::= { atiCntRuleEntry 35 }

    atiCntRuleOperationCondition OBJECT-TYPE
        SYNTAX  ConditionSpec
        ACCESS  read-write
        STATUS  mandatory
        DESCRIPTION
            "Condition pertaining to the operation used when receiving the AT
            message. For the specification for this condition, the following
            formats apply:

            1) NONE
            2) BITSTRING

            When the format is BITSTRING, the relating bit string specifies
            which operations apply. Not all bits of the bit string are used.
            Each bit in the bit string that is used relates to a specific
            operation. If the bit is 1, the operation applies. Otherwise, if
            the bit is 0, the operation does not apply. The bit string
            consists of 32 bits and has the following mapping:

              ---------------------------------------------------------------
              bit  operation
              ---------------------------------------------------------------
               0   UCP Call input operation -01
               5   UCP Deliver Short Message operation -52
               6   UCP Deliver Notification operation -53
               9   UCP operation other than the ones above
               11  SMPP DeliverSm
               13  SMPP DataSm
               19  SMPP operation other than the ones above
               21  CIMD DeliverMessage
               22  CIMD DeliverStatusReport
               29  CIMD operation other than the ones above
               30  operation from another protocol than UCP, SMPP and CIMD
              --------------------------------------------------------------

            Note that bit 0 is the least significant (last) bit and bit 31 is
            the most significant (first) bit.

            For further details on these formats, refer to the comment on the
            ConditionSpec type."
        ::= { atiCntRuleEntry 36 }

    atiCntRuleOriginatorCondition OBJECT-TYPE
        SYNTAX  ConditionSpec
        ACCESS  read-write
        STATUS  mandatory
        DESCRIPTION
            "Condition pertaining to the originator that is specified in the
            SM. For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST
            12) ALPHANUMADDRESS

            For details on these formats, refer to the comment on the
            ConditionSpec type."
        ::= { atiCntRuleEntry 37 }

    atiCntRuleOriginatorTonCondition OBJECT-TYPE
        SYNTAX  ConditionSpec
        ACCESS  read-write
        STATUS  mandatory
        DESCRIPTION
            "Condition pertaining to the type of number (TON) specified for
            the originator of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant (last) bit
            indicating whether TON value 0 applies and the most significant
            (first) bit indicating whether TON value 7 applies.

            For further details on these formats, refer to the comment on the
            ConditionSpec type.

            For details on the values supported for the TON, refer to 3GPP
            23.040."
        ::= { atiCntRuleEntry 38 }

    atiCntRuleOriginatorNpiCondition OBJECT-TYPE
        SYNTAX  ConditionSpec
        ACCESS  read-write
        STATUS  mandatory
        DESCRIPTION
            "Condition pertaining to the numbering plan identification (NPI)
            specified for the originator of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant (last) bit
            indicating whether NPI value 0 applies and the most significant
            (first) bit indicating whether NPI value 15 applies.

            For further details on these formats, refer to the comment on the
            ConditionSpec type.

            For details on the values supported for the NPI, refer to 3GPP
            23.040."
        ::= { atiCntRuleEntry 39 }

    atiCntRuleRecipientCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST
            12) ALPHANUMADDRESS

            For details on these formats, refer to the comment on the
            ConditionSpec type."
        ::= { atiCntRuleEntry 40 }

    atiCntRuleRecipientTonCondition OBJECT-TYPE
        SYNTAX  ConditionSpec
        ACCESS  read-write
        STATUS  mandatory
        DESCRIPTION
            "Condition pertaining to the type of number (TON) specified for
            the recipient of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant (last) bit
            indicating whether TON value 0 applies and the most significant
            (first) bit indicating whether TON value 7 applies.

            For further details on these formats, refer to the comment on the
            ConditionSpec type.

            For details on the values supported for the TON, refer to 3GPP
            23.040."
        ::= { atiCntRuleEntry 41 }

    atiCntRuleRecipientNpiCondition OBJECT-TYPE
        SYNTAX  ConditionSpec
        ACCESS  read-write
        STATUS  mandatory
        DESCRIPTION
            "Condition pertaining to the numbering plan identification (NPI)
            specified for the recipient of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant (last) bit
            indicating whether NPI value 0 applies and the most significant
            (first) bit indicating whether NPI value 15 applies.

            For further details on these formats, refer to the comment on the
            ConditionSpec type.

            For details on the values supported for the NPI, refer to 3GPP
            23.040."
        ::= { atiCntRuleEntry 42 }

    atiCntRuleServiceCentreCondition OBJECT-TYPE
        SYNTAX  ConditionSpec
        ACCESS  read-write
        STATUS  mandatory
        DESCRIPTION
            "Condition pertaining to the serviceCentre, from which the AT
            message has been received. For the specification of this
            condition, the following formats apply:

            1) NONE
            2) BITSTRING

            When the format is BITSTRING, the relating bit string specifies
            which service centres apply. Each bit in the bit string
            relates to a specific service centre. If the bit is 1, the
            service centre applies. Otherwise, if the bit is 0, the
            service centre does not apply. Up to 250 service centres can be
            defined. As such, the bit string consists of 250 bits with the
            least significant (last) bit indicating whether the service
            centre with SNMP index 1 applies and the most significant
            (first) bit indicating whether the service centre with SNMP
            index 250 applies.

            For details on these formats, refer to the comment on the
            ConditionSpec type."
        ::= { atiCntRuleEntry 43 }

    atiCntRuleUserDataCondition OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT
            5) TEXTLENGTH

            Note: this condition only supports the UTF-8-based condition
                  specs, and not the ASCII-based ones.

            For details on these formats, refer to the comment on the
            ConditionSpec type."
        ::= { atiCntRuleEntry 44 }

    atiCntRuleUserDataHeaderIndicationCondition OBJECT-TYPE
        SYNTAX  ConditionSpec
        ACCESS  read-write
        STATUS  mandatory
        DESCRIPTION
            "Condition pertaining to the user data header indication specified
            in the SM. For the specification for this condition, the following
            formats apply:

            1) NONE
            2) BITVALUE

            For details on these formats, refer to the comment on the
            ConditionSpec type."
        ::= { atiCntRuleEntry 45 }

    atiCntRuleUserDataHeaderCondition OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to 3GPP 23.040. The
            values for most common information element identifiers are:

            00 hex - Concatenated short message
            01 hex - Special SMS Message Indication
            04 hex - application port addressing scheme, 8 bit address
            05 hex - application port addressing scheme, 16 bit address
            06 hex - SMSC Control Parameters
            07 hex - UDH Source Indicator "
        ::= { atiCntRuleEntry 46 }

    atiCntRuleMoreMessagesToSendCondition OBJECT-TYPE
        SYNTAX  ConditionSpec
        ACCESS  read-write
        STATUS  mandatory
        DESCRIPTION
            "Condition pertaining to the more messages to send indicator
            specified in the SM. For the specification of this condition, the
            following formats apply:

            1) NONE
            2) BITVALUE

            For details on these formats, refer to the comment on the
            ConditionSpec type."
        ::= { atiCntRuleEntry 47 }

    atiCntRulePriorityCondition OBJECT-TYPE
        SYNTAX  ConditionSpec
        ACCESS  read-write
        STATUS  mandatory
        DESCRIPTION
            "Condition pertaining to the priority level that is specified in
            the SM. For the specification of this condition, the following
            formats apply:

            1) NONE
            2) BITSTRING

            When the format is BITSTRING, the relating bit string specifies
            which priority levels apply. Not all bits of the bit string are
            used. Each bit in the bit string that is used relates to a
            specific priority level. If the bit is 1, the priority level
            applies.
            Otherwise, if the bit is 0, the priority level does not apply. The
            bit string consists of 32 bits and has the following mapping:

              ---------------------------------------------------------------
              bit  operation
              ---------------------------------------------------------------
               10  SMPP no priority requested
               11  SMPP priority requested
              --------------------------------------------------------------

            Note that bit 0 is the least significant (last) bit and bit 31 is
            the most significant (first) bit.

            For further details on these formats, refer to the comment on the
            ConditionSpec type."
        ::= { atiCntRuleEntry 48 }

    atiCntRuleProtocolIdCondition OBJECT-TYPE
        SYNTAX  ConditionSpec
        ACCESS  read-write
        STATUS  mandatory
        DESCRIPTION
            "Condition pertaining to the protocol ID specified in the SM. For
            the specification of this condition, the following formats apply:

            1) NONE
            2) BYTEVALUE

            For details on these formats, refer to the comment on the
            ConditionSpec type.

            For details on the values supported for the protocol ID, refer to
            3GPP 23.040."
        ::= { atiCntRuleEntry 49 }

    atiCntRuleDataCodingSchemeCondition OBJECT-TYPE
        SYNTAX  ConditionSpec
        ACCESS  read-write
        STATUS  mandatory
        DESCRIPTION
            "Condition pertaining to the data coding scheme specified in the
            SM. For the specification of this condition, the following
            formats apply:

            1) NONE
            2) BYTEVALUE

            For details on these formats, refer to the comment on the
            ConditionSpec type.

            For details on the values supported for the data coding scheme,
            refer to 3GPP 23.040."
        ::= { atiCntRuleEntry 50 }

    atiCntRuleMessageSegmentTypeCondition OBJECT-TYPE
        SYNTAX  ConditionSpec
        ACCESS  read-write
        STATUS  mandatory
        DESCRIPTION
            "Condition pertaining to the segment sequence number of a
            concatenated SM. For the specification of this condition, the
            following formats apply:

            1) NONE
            2) BITSTRING

            When the format is BITSTRING, the relating bit string specifies
            which concatenated message segments apply. Each bit in the bit
            string relates to a specific segment of a concatenated message. If
            the bit is 1, the segment applies. Otherwise, if the bit is 0, the
            segment does not apply. The segments are categorised into three
            groups. As such, the bit string consists of 3 bits and has the
            following mapping:

                bit  segment group
                ------------------------------------------
                 0   first segment of a segmented message.
                 1   last segment of a segmented message.
                 2   nor the first nor the last segment
                     of a segmented message.
                ------------------------------------------

            Note that bit 0 is the least significant (last) bit and bit 2 is
            the most significant (first) bit.

            For further details on these formats, refer to the comment on the
            ConditionSpec type."
        ::= { atiCntRuleEntry 51 }

    atiCntRuleScTimestampCondition OBJECT-TYPE
        SYNTAX  ConditionSpec
        ACCESS  read-write
        STATUS  mandatory
        DESCRIPTION
            "Condition pertaining to the SC timestamp that is specified in
            the SM. For the specification of this condition, the following
            formats apply:

            1) NONE
            2) RELATIVETIME

            For details on these formats, refer to the comment on the
            ConditionSpec type."
        ::= { atiCntRuleEntry 52 }

    atiCntRuleDeliveryStatusCondition OBJECT-TYPE
        SYNTAX  ConditionSpec
        ACCESS  read-write
        STATUS  mandatory
        DESCRIPTION
            "Condition pertaining to the delivery status that is specified in
            a notification message. For the specification of this condition,
            the following formats apply:

            1) NONE
            2) BITSTRING

            When the format is BITSTRING, the relating bit string specifies
            which delivery status values match. Each bit in the bit string
            relates to a specific delivery status value. If the bit is 1, the
            corresponding delivery status value is checked against. Otherwise,
            if the bit is 0, the corresponding delivery status value is
            ignored.
            The bit string consists of 32 bits and has the following mapping:

              ---------------------------------------------------------------
              bit  address PID
              ---------------------------------------------------------------
               0   UCP: in progress
               1   UCP: delivery failed
               2   UCP: delivery successful
              10   SMPP: no status available
              11   SMPP: in progress
              12   SMPP: validity period expired
              13   SMPP: delivery failed
              14   SMPP: delivery successful
              15   SMPP: deleted
              16   SMPP: deleted by cancel
              17   SMPP: scheduled
              18   SMPP: accepted
              19   SMPP: rejected
              20   CIMD: no status available
              21   CIMD: in progress
              22   CIMD: validity period expired
              23   CIMD: delivery failed
              24   CIMD: delivery successful
              25   CIMD: no response
              26   CIMD: last no response
              27   CIMD: cancelled
              28   CIMD: deleted
              29   CIMD: deleted by cancel
              --------------------------------------------------------------

            Note that bit 0 is the least significant (last) bit and bit 2 is
            the most significant (first) bit.

            Note that if the AT message is not a notification message, and
            this condition has been specified, there corresponding rule will
            never match.

            For further details on these formats, refer to the comment on the
            ConditionSpec type."
        ::= { atiCntRuleEntry 53 }

    atiCntRuleDeliveryTimestampCondition OBJECT-TYPE
        SYNTAX  ConditionSpec
        ACCESS  read-write
        STATUS  mandatory
        DESCRIPTION
            "Condition pertaining to the delivery timestamp that is specified
            in the notification. For the specification of this condition,
            the following formats apply:

            1) NONE
            2) RELATIVETIME

            Note that if the AT message is not a notification message, and
            this condition has been specified, there corresponding rule will
            never match.

            For details on these formats, refer to the comment on the
            ConditionSpec type."
        ::= { atiCntRuleEntry 54 }

    atiCntRuleExternalAttributesCondition  OBJECT-TYPE
        SYNTAX  ConditionSpec
        ACCESS  read-write
        STATUS  mandatory
        DESCRIPTION
            "Condition on the 32 boolean atributes that can be set by an 
            EC application. For the specification of this condition, the
            following formats apply:

            1) NONE
            2) EXTERNALATTRIBUTES

            When the format is EXTERNALATTRIBUTES, the relating bit mask
            string specifies which external attributes apply and the relating
            bit value string specifies the values for the external
            attributes.
            Each bit in the bit strings relates to a specific attribute. The
            bit strings consist of 32 bits. The least significant (last) bit
            corresponds to attribute 0. The most significant (first) bit
            corresponds to attribute 31. 

            A bit with value 1 in the bit mask string indicates that the
            relating attribute applies and needs to be checked. A bit with
            value 0 in the bit mask string indicates that the relating
            attribute does not apply and does not need to be checked. 

            A bit with value 1 in the bit value string indicates that the
            relating attribute should be TRUE. A bit with value 0 in the bit
            value string indicates that the relating attribute should be
            FALSE.

            For further details on these formats, refer to the comment on the
            ConditionSpec type."
        ::= { atiCntRuleEntry 55 }

    atiCntRuleMessageTypeCondition OBJECT-TYPE
        SYNTAX  ConditionSpec
        ACCESS  read-write
        STATUS  mandatory
        DESCRIPTION
            "Condition pertaining to the message type applicable for this SM.
            For the specification of this condition, the following formats
            apply:

            1) NONE
            2) BITSTRING

            When the format is BITSTRING, the relating bit string specifies
            which values for the message type apply. Each bit in the bit
            string relates to a message type. If the bit is 1, the relating
            message type applies. Otherwise, if the bit is 0, the relating
            message type does not apply. The bit string consists of 2 bits
            and has the following mapping:

                ---------------------------
                bit  message type
                ---------------------------
                 0   normal AT message.
                 1   delivery notification.
                ---------------------------

            The bit string consists of 2 bits, with the least significant
            (last) bit indicating whether message type 0 applies and the
            most significant (first) bit indicating whether message type 2
            applies.

            For further details on these formats, refer to the comment on the
            ConditionSpec type."
        ::= { atiCntRuleEntry 56 }

    -- AT incoming external condition rules
    
    atiExtCondRuleTable OBJECT-TYPE
        SYNTAX  SEQUENCE OF AtiExtCondRuleEntry
        ACCESS  not-accessible
        STATUS  mandatory
        DESCRIPTION
            "A table containing properties, conditions, counters and action
            parameters for each ATI ExternalCondition rule.

            An ATI ExternalCondition rule matches when all of the following
            conditions are met:

            1) its administrative state is active;
            2) all its (internal) conditions do satisfy;

            In case multiple rules match, all matching rules are applied in
            order of priority of the rules.
            For each matching rule, the specified ExternalCondition is
            evaluated by sending an evaluationRequest to the ExternalCondition
            application, which will return a evaluationResponse.
            When the ExternalCondition evaluates to True, the next rule will
            be processed. When all matching ExternalCondition rules evaluate
            to True, the incoming AT SM will be routed according to the ATI
            routing rules.
            When during the processing of an ExternalCondition rule a rule
            evaluates to False, the FailureAction of that rule will be
            executed and further processing of the ExternalCondition rules
            is stopped for this SM."
        ::= { sms 143 }

    atiExtCondRuleEntry OBJECT-TYPE
        SYNTAX  AtiExtCondRuleEntry
        ACCESS  not-accessible
        STATUS  mandatory
        DESCRIPTION
            "Table entry specifying a single ATI ExternalCondition."
        INDEX   { atiExtCondRuleIndex }
        ::= { atiExtCondRuleTable 1 }

    AtiExtCondRuleEntry ::=
        SEQUENCE {
            atiExtCondRuleIndex                        AtiRuleTableIndex,
            atiExtCondRuleAdminState                   AdminState,
            atiExtCondRuleName                         NameString,
            atiExtCondRulePriority                     EciPriority,
            atiExtCondRuleLogProfile                   LogProfile,
            atiExtCondRuleTotalAppliedCounter          Counter,
            atiExtCondRulePassedCounter                Counter,
            atiExtCondRuleBlockedCounter               Counter,
            atiExtCondRuleFailureAction                ExtCondAtAction,
            atiExtCondRuleExternalCondition            ConditionSpec,
            atiExtCondRuleApplicationCondition         ConditionSpec,
            atiExtCondRuleApplicationGroupCondition    ConditionSpec,
            atiExtCondRuleApplicationCategoryCondition ConditionSpec,
            atiExtCondRuleServiceClassCondition        ConditionSpec,
            atiExtCondRuleProtocolCondition            ConditionSpec,
            atiExtCondRuleOperationCondition           ConditionSpec,
            atiExtCondRuleOriginatorCondition          ConditionSpec,
            atiExtCondRuleOriginatorTonCondition       ConditionSpec,
            atiExtCondRuleOriginatorNpiCondition       ConditionSpec,
            atiExtCondRuleRecipientCondition           ConditionSpec,
            atiExtCondRuleRecipientTonCondition        ConditionSpec,
            atiExtCondRuleRecipientNpiCondition        ConditionSpec,
            atiExtCondRuleServiceCentreCondition       ConditionSpec,
            atiExtCondRuleUserDataCondition            ConditionSpec,
            atiExtCondRuleUserDataHeaderIndicationCondition ConditionSpec,
            atiExtCondRuleUserDataHeaderCondition      ConditionSpec,
            atiExtCondRuleMoreMessagesToSendCondition  ConditionSpec,
            atiExtCondRulePriorityCondition            ConditionSpec,
            atiExtCondRuleProtocolIdCondition          ConditionSpec,
            atiExtCondRuleDataCodingSchemeCondition    ConditionSpec,
            atiExtCondRuleMessageSegmentTypeCondition  ConditionSpec,
            atiExtCondRuleScTimestampCondition         ConditionSpec,
            atiExtCondRuleDeliveryStatusCondition      ConditionSpec,
            atiExtCondRuleDeliveryTimestampCondition   ConditionSpec,
            atiExtCondRuleMessageTypeCondition         ConditionSpec
        }

    atiExtCondRuleIndex OBJECT-TYPE
        SYNTAX  AtiRuleTableIndex
        ACCESS  read-write
        STATUS  mandatory
        DESCRIPTION
            "Index of entry in ATI ExternalCondition table."
        ::= { atiExtCondRuleEntry 1 }

    atiExtCondRuleAdminState OBJECT-TYPE
        SYNTAX  AdminState
        ACCESS  read-write
        STATUS  mandatory
        DESCRIPTION
            "Administrative state of the ATI ExternalCondition.

            Transition from 'inactive' to 'active' is only possible when:
            1) name has been supplied;
            2) name is not already in use by another rule;
            3) conditions of rule specifying a network refer to an 'active'
               country and an 'active' network;
            4) conditions of rule specifying a country refer to an 'active'
               country;

            For details, refer to the comment on the AdminState type."
        ::= { atiExtCondRuleEntry 2 }

    atiExtCondRuleName OBJECT-TYPE
        SYNTAX  NameString
        ACCESS  read-write
        STATUS  mandatory
        DESCRIPTION
            "Name of the ATI ExternalCondition."
        ::= { atiExtCondRuleEntry 3 }

    atiExtCondRulePriority OBJECT-TYPE
        SYNTAX  EciPriority
        ACCESS  read-write
        STATUS  mandatory
        DESCRIPTION
            "Priority of the ATI ExternalCondition rule.
            For details, refer to the comment on the EciPriority type."
        ::= { atiExtCondRuleEntry 4 }

    atiExtCondRuleLogProfile OBJECT-TYPE
        SYNTAX  LogProfile
        ACCESS  read-write
        STATUS  mandatory
        DESCRIPTION
            "Identifier specifying which logging profile should be used. 
            Default is 0 (i.e. 'none')."
        ::= { atiExtCondRuleEntry 5 }
        
    atiExtCondRuleTotalAppliedCounter OBJECT-TYPE
        SYNTAX  Counter
        ACCESS  read-write
        STATUS  mandatory
        DESCRIPTION
            "Counter specifying the number of times that the ExternalCondition
            rule has been applied."
        ::= { atiExtCondRuleEntry 11 }

    atiExtCondRulePassedCounter OBJECT-TYPE
        SYNTAX  Counter
        ACCESS  read-write
        STATUS  mandatory
        DESCRIPTION
            "Counter specifying the number of times that the ExternalCondition
            rule has evaluated to true."
        ::= { atiExtCondRuleEntry 12 }

    atiExtCondRuleBlockedCounter OBJECT-TYPE
        SYNTAX  Counter
        ACCESS  read-write
        STATUS  mandatory
        DESCRIPTION
            "Counter specifying the number of times that the ExternalCondition
            rule has evaluated to false."
        ::= { atiExtCondRuleEntry 13 }

    atiExtCondRuleFailureAction OBJECT-TYPE
        SYNTAX  ExtCondAtAction
        ACCESS  read-write
        STATUS  mandatory
        DESCRIPTION
            "Action to execute when the ATI ExternalCondition rule matches,
            but the ExternalCondition evaluates to False. By default, this
            object is set to 'none'.
            For details, refer to the comments on the ExtCondAtAction type."
        ::= { atiExtCondRuleEntry 21 }

    atiExtCondRuleExternalCondition OBJECT-TYPE
        SYNTAX  ConditionSpec
        ACCESS  read-write
        STATUS  mandatory
        DESCRIPTION
            "Condition refering to an external condition application
            which has to validate this rule.
            The following formats apply:

            1) EXTERNALCONDITION

            For details, refer to the ConditionSpec type."
        ::= { atiExtCondRuleEntry 22 }

    atiExtCondRuleApplicationCondition OBJECT-TYPE
        SYNTAX  ConditionSpec
        ACCESS  read-write
        STATUS  mandatory
        DESCRIPTION
            "Condition pertaining to the application for which the AT
            message has been received. For the specification for this
            condition, the following formats apply:

            1) NONE
            2) APPLICATION

            Note that for this condition, the condition spec variant
            'by-name' is not supported, only 'by-index'.

            For details on these formats, refer to the comment on the
            ConditionSpec type."
        ::= { atiExtCondRuleEntry 31 }

    atiExtCondRuleApplicationGroupCondition OBJECT-TYPE
        SYNTAX  ConditionSpec
        ACCESS  read-write
        STATUS  mandatory
        DESCRIPTION
            "Condition pertaining to the application group associated with
            the application for which the AT message has been received.
            For the specification for this condition, the following formats
            apply:

            1) NONE
            2) BITSTRING

            When the format is BITSTRING, the relating bit string specifies
            which application groups apply. Each bit in the bit string
            relates to a specific application group. If the bit is 1, the
            application group applies. Otherwise, if the bit is 0, the
            application group does not apply. Up to 1000 application
            groups can be defined. As such, the bit string consists of 1000
            bits with the least significant (last) bit indicating whether
            application group with SNMP index 1 applies and the most
            significant (first) bit indicating whether application group with
            SNMP index 1000 applies.

            For further details on these formats, refer to the comment on the
            ConditionSpec type."
        ::= { atiExtCondRuleEntry 32 }

    atiExtCondRuleApplicationCategoryCondition OBJECT-TYPE
        SYNTAX  ConditionSpec
        ACCESS  read-write
        STATUS  mandatory
        DESCRIPTION
            "Condition pertaining to the application categories associated
            with the application for which the AT message has been received.
            For the specification of this condition, the following formats
            apply:

            1) NONE
            2) BITSTRING

            When the format is BITSTRING, the relating bit string specifies
            which application categories apply. Each bit in the bit string
            relates to a specific application category. If the bit is 1, the
            application category applies. Otherwise, if the bit is 0, the
            application category does not apply. Up to 1000 application
            categories can be defined. As such, the bit string consists of
            1000 bits with the least significant (last) bit indicating whether
            application category with SNMP index 1 applies and the most
            significant (first) bit indicating whether application category
            with SNMP index 1000 applies.

            The condition evaluates to true is at least one application
            category of the application, for which the AT message has been
            received, is specified in this conditions specification.

            For further details on these formats, refer to the comment on the
            ConditionSpec type."
        ::= { atiExtCondRuleEntry 33 }

    atiExtCondRuleServiceClassCondition OBJECT-TYPE
        SYNTAX  ConditionSpec
        ACCESS  read-write
        STATUS  mandatory
        DESCRIPTION
            "Condition pertaining to the service class associated with the
            application for which the AT message has been received. For the
            specification of this condition, the following formats apply:

            1) NONE
            2) BITSTRING

            When the format is BITSTRING, the relating bit string specifies
            which service classes apply. Each bit in the bit string relates
            to a specific service class. If the bit is 1, the service class
            applies. Otherwise, if the bit is 0, the service class does not
            apply. Up to 1000 service classes can be defined. As such, the
            bit string consists of 1000 bits with the least significant
            (last) bit indicating whether service class with SNMP index 1
            applies and the most significant (fist) bit indicating whether
            service class with SNMP index 1000 applies.

            For further details on these formats, refer to the comment on the
            ConditionSpec type."
        ::= { atiExtCondRuleEntry 34 }

    atiExtCondRuleProtocolCondition OBJECT-TYPE
        SYNTAX  ConditionSpec
        ACCESS  read-write
        STATUS  mandatory
        DESCRIPTION
            "Condition pertaining to the protocol used when receiving the AT
            message. For the specification of this condition, the following
            formats apply:

            1) NONE
            2) BITSTRING

            When the format is BITSTRING, the relating bit string specifies
            which protocols apply. Each bit in the bit string relates to a
            specific protocol. If the bit is 1, the protocol applies.
            Otherwise, if the bit is 0, the protocol does not apply. The bit
            string consists of 3 bits and has the following mapping:

              -------------
              bit  protocol
              -------------
               0   UCP
               1   SMPP
               2   CIMD
              -------------

            Note that bit 0 is the least significant (last) bit and bit 2 is
            the most significant (first) bit in the bitstring.

            For further details on these formats, refer to the comment on the
            ConditionSpec type."
        ::= { atiExtCondRuleEntry 35 }

    atiExtCondRuleOperationCondition OBJECT-TYPE
        SYNTAX  ConditionSpec
        ACCESS  read-write
        STATUS  mandatory
        DESCRIPTION
            "Condition pertaining to the operation used when receiving the AT
            message. For the specification for this condition, the following
            formats apply:

            1) NONE
            2) BITSTRING

            When the format is BITSTRING, the relating bit string specifies
            which operations apply. Not all bits of the bit string are used.
            Each bit in the bit string that is used relates to a specific
            operation. If the bit is 1, the operation applies. Otherwise, if
            the bit is 0, the operation does not apply. The bit string
            consists of 32 bits and has the following mapping:

              ---------------------------------------------------------------
              bit  operation
              ---------------------------------------------------------------
               0   UCP Call input operation -01
               5   UCP Deliver Short Message operation -52
               6   UCP Deliver Notification operation -53
               9   UCP operation other than the ones above
               11  SMPP DeliverSm
               13  SMPP DataSm
               19  SMPP operation other than the ones above
               21  CIMD DeliverMessage
               22  CIMD DeliverStatusReport
               29  CIMD operation other than the ones above
               30  operation from another protocol than UCP, SMPP and CIMD
              --------------------------------------------------------------

            Note that bit 0 is the least significant (last) bit and bit 31 is
            the most significant (first) bit.

            For further details on these formats, refer to the comment on the
            ConditionSpec type."
        ::= { atiExtCondRuleEntry 36 }

    atiExtCondRuleOriginatorCondition OBJECT-TYPE
        SYNTAX  ConditionSpec
        ACCESS  read-write
        STATUS  mandatory
        DESCRIPTION
            "Condition pertaining to the originator that is specified in the
            SM. For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST
            12) ALPHANUMADDRESS

            For details on these formats, refer to the comment on the
            ConditionSpec type."
        ::= { atiExtCondRuleEntry 37 }

    atiExtCondRuleOriginatorTonCondition OBJECT-TYPE
        SYNTAX  ConditionSpec
        ACCESS  read-write
        STATUS  mandatory
        DESCRIPTION
            "Condition pertaining to the type of number (TON) specified for
            the originator of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant (last) bit
            indicating whether TON value 0 applies and the most significant
            (first) bit indicating whether TON value 7 applies.

            For further details on these formats, refer to the comment on the
            ConditionSpec type.

            For details on the values supported for the TON, refer to 3GPP
            23.040."
        ::= { atiExtCondRuleEntry 38 }

    atiExtCondRuleOriginatorNpiCondition OBJECT-TYPE
        SYNTAX  ConditionSpec
        ACCESS  read-write
        STATUS  mandatory
        DESCRIPTION
            "Condition pertaining to the numbering plan identification (NPI)
            specified for the originator of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant (last) bit
            indicating whether NPI value 0 applies and the most significant
            (first) bit indicating whether NPI value 15 applies.

            For further details on these formats, refer to the comment on the
            ConditionSpec type.

            For details on the values supported for the NPI, refer to 3GPP
            23.040."
        ::= { atiExtCondRuleEntry 39 }

    atiExtCondRuleRecipientCondition OBJECT-TYPE
        SYNTAX  ConditionSpec
        ACCESS  read-write
        STATUS  mandatory
        DESCRIPTION
            "Condition pertaining to the originator that is specified in the
            SM.  For the specification for this condition, the following
            formats apply:

            1) NONE
            2) SINGLEMSISDN
            3) MSISDNRANGE
            4) MSISDNPREFIX
            5) COUNTRY
            6) NETWORK
            7) SINGLESHORTNUMBER
            8) SHORTNUMBERRANGE
            9) SHORTNUMBERPREFIX
            10) APPLICATION
            11) LIST
            12) ALPHANUMADDRESS

            For details on these formats, refer to the comment on the
            ConditionSpec type."
        ::= { atiExtCondRuleEntry 40 }

    atiExtCondRuleRecipientTonCondition OBJECT-TYPE
        SYNTAX  ConditionSpec
        ACCESS  read-write
        STATUS  mandatory
        DESCRIPTION
            "Condition pertaining to the type of number (TON) specified for
            the recipient of the SM. For the specification for this
            condition, the following formats apply:

            1) NONE
            2) BITSTRING

            When the format is BITSTRING, the relating bit string specifies
            which values for the TON apply. Each bit in the bit string relates
            to a TON value. If the bit is 1, the relating TON value applies.
            Otherwise, if the bit is 0, the relating TON value does not apply.
            The range of value for the TON is 0-7. As such, the bit string
            consists of 8 bits with the least significant (last) bit
            indicating whether TON value 0 applies and the most significant
            (first) bit indicating whether TON value 7 applies.

            For further details on these formats, refer to the comment on the
            ConditionSpec type.

            For details on the values supported for the TON, refer to 3GPP
            23.040."
        ::= { atiExtCondRuleEntry 41 }

    atiExtCondRuleRecipientNpiCondition OBJECT-TYPE
        SYNTAX  ConditionSpec
        ACCESS  read-write
        STATUS  mandatory
        DESCRIPTION
            "Condition pertaining to the numbering plan identification (NPI)
            specified for the recipient of the SM. For the specification for
            this condition, the following formats apply:

            1) NONE
            2) BITSTRING

            When the format is BITSTRING, the relating bit string specifies
            which values for the NPI apply. Each bit in the bit string relates
            to a NPI value. If the bit is 1, the relating NPI value applies.
            Otherwise, if the bit is 0, the relating NPI value does not apply.
            The range of value for the NPI is 0-15. As such, the bit string
            consists of 16 bits with the least significant (last) bit
            indicating whether NPI value 0 applies and the most significant
            (first) bit indicating whether NPI value 15 applies.

            For further details on these formats, refer to the comment on the
            ConditionSpec type.

            For details on the values supported for the NPI, refer to 3GPP
            23.040."
        ::= { atiExtCondRuleEntry 42 }

    atiExtCondRuleServiceCentreCondition OBJECT-TYPE
        SYNTAX  ConditionSpec
        ACCESS  read-write
        STATUS  mandatory
        DESCRIPTION
            "Condition pertaining to the serviceCentre, from which the AT
            message has been received. For the specification of this
            condition, the following formats apply:

            1) NONE
            2) BITSTRING

            When the format is BITSTRING, the relating bit string specifies
            which service centres apply. Each bit in the bit string
            relates to a specific service centre. If the bit is 1, the
            service centre applies. Otherwise, if the bit is 0, the
            service centre does not apply. Up to 250 service centres can be
            defined. As such, the bit string consists of 250 bits with the
            least significant (last) bit indicating whether the service
            centre with SNMP index 1 applies and the most significant
            (first) bit indicating whether the service centre with SNMP
            index 250 applies.

            For details on these formats, refer to the comment on the
            ConditionSpec type."
        ::= { atiExtCondRuleEntry 43 }

    atiExtCondRuleUserDataCondition OBJECT-TYPE
        SYNTAX  ConditionSpec
        ACCESS  read-write
        STATUS  mandatory
        DESCRIPTION
            "Condition pertaining to the text that is specified in the user
            data of the SM. For the specification for this condition, the
            following formats apply:

            1) NONE
            2) FULLTEXT
            3) TEXTTAG
            4) SUBTEXT
            5) TEXTLENGTH

            Note: this condition only supports the UTF-8-based condition
                  specs, and not the ASCII-based ones.

            For details on these formats, refer to the comment on the
            ConditionSpec type."
        ::= { atiExtCondRuleEntry 44 }

    atiExtCondRuleUserDataHeaderIndicationCondition OBJECT-TYPE
        SYNTAX  ConditionSpec
        ACCESS  read-write
        STATUS  mandatory
        DESCRIPTION
            "Condition pertaining to the user data header indication specified
            in the SM. For the specification for this condition, the following
            formats apply:

            1) NONE
            2) BITVALUE

            For details on these formats, refer to the comment on the
            ConditionSpec type."
        ::= { atiExtCondRuleEntry 45 }

    atiExtCondRuleUserDataHeaderCondition OBJECT-TYPE
        SYNTAX  ConditionSpec
        ACCESS  read-write
        STATUS  mandatory
        DESCRIPTION
            "Condition pertaining to the value that is specified in one of the
            information element identifiers of the user data header of the SM.
            For the specification for this condition, the following formats
            apply:

            1) NONE
            2) BYTEVALUE

            For details on these formats, refer to the comment on the
            ConditionSpec type.

            For details on the values supported for the information element
            identifiers of the user data header, refer to 3GPP 23.040. The
            values for most common information element identifiers are:

            00 hex - Concatenated short message
            01 hex - Special SMS Message Indication
            04 hex - application port addressing scheme, 8 bit address
            05 hex - application port addressing scheme, 16 bit address
            06 hex - SMSC Control Parameters
            07 hex - UDH Source Indicator "
        ::= { atiExtCondRuleEntry 46 }

    atiExtCondRuleMoreMessagesToSendCondition OBJECT-TYPE
        SYNTAX  ConditionSpec
        ACCESS  read-write
        STATUS  mandatory
        DESCRIPTION
            "Condition pertaining to the more messages to send indicator
            specified in the SM. For the specification of this condition, the
            following formats apply:

            1) NONE
            2) BITVALUE

            For details on these formats, refer to the comment on the
            ConditionSpec type."
        ::= { atiExtCondRuleEntry 47 }

    atiExtCondRulePriorityCondition OBJECT-TYPE
        SYNTAX  ConditionSpec
        ACCESS  read-write
        STATUS  mandatory
        DESCRIPTION
            "Condition pertaining to the priority level that is specified in
            the SM. For the specification of this condition, the following
            formats apply:

            1) NONE
            2) BITSTRING

            When the format is BITSTRING, the relating bit string specifies
            which priority levels apply. Not all bits of the bit string are
            used. Each bit in the bit string that is used relates to a
            specific priority level. If the bit is 1, the priority level
            applies.
            Otherwise, if the bit is 0, the priority level does not apply. The
            bit string consists of 32 bits and has the following mapping:

              ---------------------------------------------------------------
              bit  operation
              ---------------------------------------------------------------
               10  SMPP no priority requested
               11  SMPP priority requested
              --------------------------------------------------------------

            Note that bit 0 is the least significant (last) bit and bit 31 is
            the most significant (first) bit.

            For further details on these formats, refer to the comment on the
            ConditionSpec type."
        ::= { atiExtCondRuleEntry 48 }

    atiExtCondRuleProtocolIdCondition OBJECT-TYPE
        SYNTAX  ConditionSpec
        ACCESS  read-write
        STATUS  mandatory
        DESCRIPTION
            "Condition pertaining to the protocol ID specified in the SM. For
            the specification of this condition, the following formats apply:

            1) NONE
            2) BYTEVALUE

            For details on these formats, refer to the comment on the
            ConditionSpec type.

            For details on the values supported for the protocol ID, refer to
            3GPP 23.040."
        ::= { atiExtCondRuleEntry 49 }

    atiExtCondRuleDataCodingSchemeCondition OBJECT-TYPE
        SYNTAX  ConditionSpec
        ACCESS  read-write
        STATUS  mandatory
        DESCRIPTION
            "Condition pertaining to the data coding scheme specified in the
            SM. For the specification of this condition, the following
            formats apply:

            1) NONE
            2) BYTEVALUE

            For details on these formats, refer to the comment on the
            ConditionSpec type.

            For details on the values supported for the data coding scheme,
            refer to 3GPP 23.040."
        ::= { atiExtCondRuleEntry 50 }

    atiExtCondRuleMessageSegmentTypeCondition OBJECT-TYPE
        SYNTAX  ConditionSpec
        ACCESS  read-write
        STATUS  mandatory
        DESCRIPTION
            "Condition pertaining to the segment sequence number of a
            concatenated SM. For the specification of this condition, the
            following formats apply:

            1) NONE
            2) BITSTRING

            When the format is BITSTRING, the relating bit string specifies
            which concatenated message segments apply. Each bit in the bit
            string relates to a specific segment of a concatenated message. If
            the bit is 1, the segment applies. Otherwise, if the bit is 0, the
            segment does not apply. The segments are categorised into three
            groups. As such, the bit string consists of 3 bits and has the
            following mapping:

                bit  segment group
                ------------------------------------------
                 0   first segment of a segmented message.
                 1   last segment of a segmented message.
                 2   nor the first nor the last segment
                     of a segmented message.
                ------------------------------------------

            Note that bit 0 is the least significant (last) bit and bit 2 is
            the most significant (first) bit.

            For further details on these formats, refer to the comment on the
            ConditionSpec type."
        ::= { atiExtCondRuleEntry 51 }

    atiExtCondRuleScTimestampCondition OBJECT-TYPE
        SYNTAX  ConditionSpec
        ACCESS  read-write
        STATUS  mandatory
        DESCRIPTION
            "Condition pertaining to the SC timestamp that is specified in
            the SM. For the specification of this condition, the following
            formats apply:

            1) NONE
            2) RELATIVETIME

            For details on these formats, refer to the comment on the
            ConditionSpec type."
        ::= { atiExtCondRuleEntry 52 }

    atiExtCondRuleDeliveryStatusCondition OBJECT-TYPE
        SYNTAX  ConditionSpec
        ACCESS  read-write
        STATUS  mandatory
        DESCRIPTION
            "Condition pertaining to the delivery status that is specified in
            a notification message. For the specification of this condition,
            the following formats apply:

            1) NONE
            2) BITSTRING

            When the format is BITSTRING, the relating bit string specifies
            which delivery status values match. Each bit in the bit string
            relates to a specific delivery status value. If the bit is 1, the
            corresponding delivery status value is checked against. Otherwise,
            if the bit is 0, the corresponding delivery status value is
            ignored.
            The bit string consists of 32 bits and has the following mapping:

              ---------------------------------------------------------------
              bit  address PID
              ---------------------------------------------------------------
               0   UCP: in progress
               1   UCP: delivery failed
               2   UCP: delivery successful
              10   SMPP: no status available
              11   SMPP: in progress
              12   SMPP: validity period expired
              13   SMPP: delivery failed
              14   SMPP: delivery successful
              15   SMPP: deleted
              16   SMPP: deleted by cancel
              17   SMPP: scheduled
              18   SMPP: accepted
              19   SMPP: rejected
              20   CIMD: no status available
              21   CIMD: in progress
              22   CIMD: validity period expired
              23   CIMD: delivery failed
              24   CIMD: delivery successful
              25   CIMD: no response
              26   CIMD: last no response
              27   CIMD: cancelled
              28   CIMD: deleted
              29   CIMD: deleted by cancel
              --------------------------------------------------------------

            Note that bit 0 is the least significant (last) bit and bit 2 is
            the most significant (first) bit.

            Note that if the AT message is not a notification message, and
            this condition has been specified, there corresponding rule will
            never match.

            For further details on these formats, refer to the comment on the
            ConditionSpec type."
        ::= { atiExtCondRuleEntry 53 }

    atiExtCondRuleDeliveryTimestampCondition OBJECT-TYPE
        SYNTAX  ConditionSpec
        ACCESS  read-write
        STATUS  mandatory
        DESCRIPTION
            "Condition pertaining to the delivery timestamp that is specified
            in the notification. For the specification of this condition,
            the following formats apply:

            1) NONE
            2) RELATIVETIME

            Note that if the AT message is not a notification message, and
            this condition has been specified, there corresponding rule will
            never match.

            For details on these formats, refer to the comment on the
            ConditionSpec type."
        ::= { atiExtCondRuleEntry 54 }

    -- no external attributes condition for ATIX.

    atiExtCondRuleMessageTypeCondition OBJECT-TYPE
        SYNTAX  ConditionSpec
        ACCESS  read-write
        STATUS  mandatory
        DESCRIPTION
            "Condition pertaining to the message type applicable for this SM.
            For the specification of this condition, the following formats
            apply:

            1) NONE
            2) BITSTRING

            When the format is BITSTRING, the relating bit string specifies
            which values for the message type apply. Each bit in the bit
            string relates to a message type. If the bit is 1, the relating
            message type applies. Otherwise, if the bit is 0, the relating
            message type does not apply. The bit string consists of 2 bits
            and has the following mapping:

                ---------------------------
                bit  message type
                ---------------------------
                 0   normal AT message.
                 1   delivery notification.
                ---------------------------

            The bit string consists of 2 bits, with the least significant
            (last) bit indicating whether message type 0 applies and the
            most significant (first) bit indicating whether message type 2
            applies.

            For further details on these formats, refer to the comment on the
            ConditionSpec type."
        ::= { atiExtCondRuleEntry 56 }


    scrProperties OBJECT IDENTIFIER ::= { sms 201 }

    scrPropCatchSriSm OBJECT-TYPE
        SYNTAX  Boolean
        ACCESS  read-write
        STATUS  mandatory
        DESCRIPTION
            "Boolean specifying whether the MAP Screener should relay
            SendRoutingInfoForSm operations to the firewall. Default is
            'true'."
        ::= { scrProperties 1 }

    scrPropCatchMtFwdSm OBJECT-TYPE
        SYNTAX  Boolean
        ACCESS  read-write
        STATUS  mandatory
        DESCRIPTION
            "Boolean specifying whether the MAP Screener should relay 
            MtForwardSm operations to the firewall. Default is 'true'."
        ::= { scrProperties 2 }

    scrPropCatchMoFwdSm OBJECT-TYPE
        SYNTAX  Boolean
        ACCESS  read-write
        STATUS  mandatory
        DESCRIPTION
            "Boolean specifying whether the MAP Screener should relay 
            MoForwardSm operations to the firewall. Default is 'true'."
        ::= { scrProperties 3 }

    scrCounters OBJECT IDENTIFIER ::= { sms 202 }

    scrCntRoutedToFirewallCounter OBJECT-TYPE
        SYNTAX  Counter
        ACCESS  read-write
        STATUS  mandatory
        DESCRIPTION
            "Counter specifying the total number of times that the screening
            of a message resulted in the message being routed to the
            firewall."
        ::= { scrCounters 1 }

    scrCntRoutedToNetworkCounter OBJECT-TYPE
        SYNTAX  Counter
        ACCESS  read-write
        STATUS  mandatory
        DESCRIPTION
            "Counter specifying the total number of times that the screening 
            of a message resulted in the message being routed to the network."
        ::= { scrCounters 2 }
      
    scrCntDroppedCounter OBJECT-TYPE
        SYNTAX  Counter
        ACCESS  read-write
        STATUS  mandatory
        DESCRIPTION
            "Counter specifying the total number of times that the screening 
            of a message resulted in the message being dropped."
        ::= { scrCounters 3 }

    ----------------------------------------------------------------------------
    --                                T R A P S                               --
    ----------------------------------------------------------------------------

    ----------------------------------------------------------------------------
    --  These traps are generated by the Router                               --
    ----------------------------------------------------------------------------

    -- OIDs 1 to 10 have moved to the APP MIB and should NOT be re-used.

    smscOperationalStateChanged TRAP-TYPE
        ENTERPRISE sms
        VARIABLES { smscOperationalState, smscName, deviceType  }
        DESCRIPTION
            "Operational state of an SMSC has changed"
        ::= 11

    moRtgRuleSmscOperationalStateChanged TRAP-TYPE
        ENTERPRISE sms
        VARIABLES { moRtgRuleSmscOperationalState, moRtgRuleName, deviceType  }
        DESCRIPTION
            "Operational state of an SMSC for a particular MO routing rule
            has changed"
        ::= 12

    fcdrCreateFileError TRAP-TYPE
        ENTERPRISE sms
        DESCRIPTION
            "An error occurred during creation of an FCDR file."
        ::= 13

    fcdrWriteFileError TRAP-TYPE
        ENTERPRISE sms
        DESCRIPTION
            "An error occurred during writing of an FCDR file."
        ::= 14

    -- OIDs 15 to 16 have moved to the APP MIB and should NOT be re-used.

    fwSriSmWithUnknownSccpSmscAddress TRAP-TYPE
        ENTERPRISE sms
        VARIABLES { fwTrapUnknownSccpSmscAddress, deviceType  }
        DESCRIPTION
            "Inbound Send-Routing-Info-For-SM operation received with an SMSC
            address at SCCP layer that could not be associated with any of
            the defined mobile network entities."
        ::= 17

    fwSriSmWithUnknownMapSmscAddress TRAP-TYPE
        ENTERPRISE sms
        VARIABLES { fwTrapUnknownMapSmscAddress, deviceType   }
        DESCRIPTION
            "Inbound Send-Routing-Info-For-SM operation received with an SMSC
             address at MAP layer that could not be associated with any of the
             defined mobile network entities."
        ::= 18

    fwSriSmWithConflictingSmscAddress TRAP-TYPE
        ENTERPRISE sms
        VARIABLES { fwTrapConflictingSccpSmscAddress, fwTrapConflictingMapSmscAddress, deviceType  }
        DESCRIPTION
            "Inbound Send-Routing-Info-For-SM operation with conflicting SMSC
             addresses at SCCP layer and MAP layer. These addresses conflict
             when they are from:
             - different countries (determined on the basis of the country
               code)
             - different mobile networks (determined by associating the
               addresses with a mobile network)."
        ::= 19

    fwMtFwdSmWithUnknownSccpSmscAddress TRAP-TYPE
        ENTERPRISE sms
        VARIABLES { fwTrapUnknownSccpSmscAddress, deviceType  }
        DESCRIPTION
            "Inbound MT-Forward-SM operation received with an SMSC address at
            SCCP layer that could not be associated with any of the defined
            mobile network entities."
        ::= 20

    fwMtFwdSmWithUnknownMapSmscAddress TRAP-TYPE
        ENTERPRISE sms
        VARIABLES { fwTrapUnknownMapSmscAddress, deviceType  }
        DESCRIPTION
            "Inbound MT-Forward-SM operation received with an SMSC address at
            MAP layer that could not be associated with any of the defined
            mobile network entities."
        ::= 21

    fwMtFwdSmWithConflictingSmscAddress TRAP-TYPE
        ENTERPRISE sms
        VARIABLES { fwTrapConflictingSccpSmscAddress, fwTrapConflictingMapSmscAddress, deviceType  }
        DESCRIPTION
            "Inbound MT-Forward-SM operation received with:
             - conflicting SMSC addresses at SCCP layer and MAP layer, or
             - different SMSC addresses at SCCP layer used amongst the various
               TCAP messages of a segmented TCAP dialogue
             SMSC addresses at SCCP layer and MAP layer conflict when they are
             from:
               - different countries (determined on the basis of the country
                 code), or
               - different mobile networks (determined by associating the
                 addresses with a mobile network)."
        ::= 22

    fwMtFwdSmWithSpoofedSccpSmscAddress TRAP-TYPE
        ENTERPRISE sms
        VARIABLES { fwTrapSccpSmscAddressInSriSm, fwTrapSccpSmscAddressInMtFwdSm, deviceType   }
        DESCRIPTION
            "Inbound MT-Forward-SM operation received with spoofing of the
            SMSC address at SCCP level, i.e. using an SMSC address at SCCP
            level for MT-Forward-SM that conflicts with address used in
            relating Send- Routing-Info-For-SM operation. A conflict exist
            when the addresses are from:
               - different countries (determined on the basis of the country
                 code), or
               - different mobile networks (determined by associating the
                 addresses with a mobile network)."
        ::= 23

    fwMtFwdSmWithSpoofedMapSmscAddress TRAP-TYPE
        ENTERPRISE sms
        VARIABLES { fwTrapMapSmscAddressInSriSm, fwTrapMapSmscAddressInMtFwdSm, deviceType   }
        DESCRIPTION
            "Inbound MT-Forward-SM operation received with spoofing of the
            SMSC address at MAP level, i.e. using an SMSC address at MAP
            level for MT-Forward-SM that conflicts with address used in
            relating Send- Routing-Info-For-SM operation. A conflict exist
            when the addresses are from:
               - different countries (determined on the basis of the country
                 code), or
               - different mobile networks (determined by associating the
                 addresses with a mobile network)."
        ::= 24

    fwMoFwdSmWithSpoofedOriginatorAddress TRAP-TYPE
        ENTERPRISE sms
        VARIABLES { fwTrapOriginatorAddressInMoFwdSm, fwTrapMscOrSgsnAddressInMoFwdSm, fwTrapMscOrSgsnAddressInSriSm, fwTrapImsiInMoFwdSm, fwTrapImsiInSriSm, deviceType  }
        DESCRIPTION
            "Inbound MO-Forward-SM operation received with spoofing of the
             originator address."
        ::= 25

    fwMoFwdSmWithSpoofingExceedThresholdAlarmTrap TRAP-TYPE
        ENTERPRISE sms
        VARIABLES { fwPropMoFwdSmWithSpoofingThreshold, fwPropMoFwdSmWithSpoofingPeriod, deviceType  }
        DESCRIPTION
            "Number of inbound MO-Forward-SM operation received with spoofing
             exceeds the provisioned threshold 
             (fwPropMoFwdSmWithSpoofingThreshold) within the provisioned
             period (fwPropMoFwdSmWithSpoofingPeriod)."
        ::= 26

    fwMtFwdSmWithSpoofingExceedThresholdAlarmTrap TRAP-TYPE
        ENTERPRISE sms
        VARIABLES { fwPropMtFwdSmWithSpoofingThreshold, fwPropMtFwdSmWithSpoofingPeriod, deviceType  }
        DESCRIPTION
            "Number of inbound MT-Forward-SM operation received with spoofing
             exceeds the provisioned threshold 
             (fwPropMtFwdSmWithSpoofingThreshold) within the provisioned
             period (fwPropMtFwdSmWithSpoofingPeriod)."
        ::= 27
    
    fwMoFwdSmWithSpoofingExceedThresholdAlarmClearedTrap TRAP-TYPE
        ENTERPRISE sms
        VARIABLES { fwPropMoFwdSmWithSpoofingThreshold, fwPropMoFwdSmWithSpoofingPeriod, deviceType  }
        DESCRIPTION
            "The number of the inbound MO-Forward-SM spoofing attempts falls
             below the provisioned threshold 
             (fwPropMoFwdSmWithSpoofingThreshold) within the provisioned
             period (fwPropMoFwdSmWithSpoofingPeriod)."
        ::= 28

    fwMtFwdSmWithSpoofingExceedThresholdAlarmClearedTrap TRAP-TYPE
        ENTERPRISE sms
        VARIABLES { fwPropMtFwdSmWithSpoofingThreshold, fwPropMtFwdSmWithSpoofingPeriod, deviceType  }
        DESCRIPTION
            "The number of the inbound MT-Forward-SM spoofing attempts falls
             below the provisioned threshold 
             (fwPropMtFwdSmWithSpoofingThreshold) within the provisioned
             period (fwPropMtFwdSmWithSpoofingPeriod)."
        ::= 29

    externalConditionAvailableTrap TRAP-TYPE
        ENTERPRISE sms
        VARIABLES { externalConditionName, deviceType }
        DESCRIPTION
            "An external condition (application) has logged in and is
            available."
        ::= 31
        
    externalConditionUnavailableTrap TRAP-TYPE
        ENTERPRISE sms
        VARIABLES { externalConditionName, deviceType }
        DESCRIPTION
            "An external condition (application) has (been) logged out
            and is no longer availble."
        ::= 32

    icacheUnavailableTrap TRAP-TYPE
        ENTERPRISE sms
        DESCRIPTION
            "AMS Icache functionality is required by your configuration,
            but is unavailable."
        ::= 33

    icacheAvailabilityRestoredTrap TRAP-TYPE
        ENTERPRISE sms
        DESCRIPTION
            "AMS Icache functionality is required by your configuration,
            and has become available after an outage."
        ::= 34

    externalConditionClientAvailableTrap TRAP-TYPE
        ENTERPRISE sms
        VARIABLES { externalConditionClientExternalConditionName, externalConditionClientIpAddress, deviceType }
        DESCRIPTION
            "An external condition client has logged in and is available."
        ::= 41

    externalConditionClientUnavailableTrap TRAP-TYPE
        ENTERPRISE sms
        VARIABLES { externalConditionClientExternalConditionName, externalConditionClientIpAddress, deviceType }
        DESCRIPTION
            "An external condition client has (been) logged out and is no
            longer availble."
        ::= 42

    -- OIDs 51 to 95 have moved to the APP MIB and should NOT be re-used.

    -- OID 100 has moved to the APP MIB and should NOT be re-used.


END

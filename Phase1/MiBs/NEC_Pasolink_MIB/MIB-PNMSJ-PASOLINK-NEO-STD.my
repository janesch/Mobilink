-------------------------------------------------------------------------------
-- Release Date: <2006/05/12 10:50:30>
--    Version  : Ver.1.03 (Reference NEO STD MIB ;Ver.1.25)
-- Release Date: <2006/09/28 20:04:30>
--    Version  : Ver.1.04 (Reference NEO STD MIB ;Ver.1.25)
-- Release Date: <2006/10/24 20:33:30>
--    Version  : Ver.1.05 (Reference NEO STD MIB ;Ver.1.25)
-- Release Date: <2006/10/05 15:58:10>
--    Version  : Ver.1.06 (Reference NEO STD MIB ;Ver.1.51)
-- Release Date: <2006/10/25 16:16:30>
--    Version  : Ver.1.07 (Reference NEO STD MIB ;Ver.1.51)
-- Release Date: <2006/12/28 14:30:00>
--    Version  : Ver.1.08 (Reference NEO STD MIB ;Ver.1.71)
-- Release Date: <2007/01/12 18:15:00>
--    Version  : Ver.1.09 (Reference NEO STD MIB ;Ver.1.71)
-- Release Date: <2007/01/17 19:00:00>
--    Version  : Ver.1.10 (Reference NEO STD MIB ;Ver.1.71)
-- Release Date: <2007/01/18 17:41:00>
--    Version  : Ver.1.11 (Reference NEO STD MIB ;Ver.1.73)
-- Release Date: <2007/02/16 12:00:00>
--    Version  : Ver.1.12 (Reference NEO STD MIB ;Ver.1.75)
-- Release Date: <2007/08/02 18:00:00>
--    Version  : Ver.1.13 (Reference NEO STD MIB ;Ver.1.75)
-- Release Date: <2007/08/24 14:00:00>
--    Version  : Ver.1.14 (Reference NEO STD MIB ;Ver.1.75)
-- Release Date: <2007/09/13 17:00:00>
--    Version  : Ver.1.15 (Reference NEO STD MIB ;Ver.1.84)
-- Release Date: <2007/12/03 17:00:00>
--    Version  : Ver.1.16 (Reference NEO STD MIB ;Ver.1.85)
-- Release Date: <2008/01/28 11:45:00>
--    Version  : Ver.1.17 (Reference NEO STD MIB ;Ver.1.88)
-- Release Date: <2008/02/08 20:00:00>
--    Version  : Ver.1.18 (Reference NEO STD MIB ;Ver.1.88)
-------------------------------------------------------------------------------


MIB-PNMSJ-PASOLINK-NEO-STD DEFINITIONS ::= BEGIN

-----------------------------------------------
-- INPORTS Definitions
-----------------------------------------------

	IMPORTS
		enterprises,IpAddress,Counter,TimeTicks
			FROM RFC1155-SMI
		DisplayString
			FROM RFC1213-MIB
		OBJECT-TYPE
			FROM RFC-1212
		TEXTUAL-CONVENTION
			FROM SNMPv2-TC
		TRAP-TYPE
			FROM RFC-1215
		pnms
			FROM NEC-SMI;
			
-----------------------------------------------
-- Begin User MIB Object Definitions
-----------------------------------------------

	DATE32	::= TEXTUAL-CONVENTION
		STATUS		current
		DESCRIPTION	"Date Type (32Bit)"
		SYNTAX		INTEGER

	TIME32	::= TEXTUAL-CONVENTION
		STATUS		current
		DESCRIPTION	"Time Type (32Bit)"
		SYNTAX		INTEGER

	DateAndTime	::= TEXTUAL-CONVENTION
		STATUS		current
		DESCRIPTION	"Date and Time Type "
		SYNTAX		OCTET STRING ( SIZE (8) )
					

	SeverityValue	::= TEXTUAL-CONVENTION
		STATUS		current
		DESCRIPTION	"Severity (CCITT Rec. X.733)
					  0:invalid
					  1:clear,
					  2:minor
					  3:major,
					  4:critical
					"
		SYNTAX		INTEGER (0..4)

	AlarmTypeValue	::= TEXTUAL-CONVENTION
		STATUS		current
		DESCRIPTION	"Alaem Type (CCITT Rec. X.733)
					  0:invalid,
					  1:communicationAlarm,
					  2:qualityOfServiceAlarm,
					  3:processingErrorAlarm,
					  4:equipmentAlarm,
					  5:environmentalAlarm,
					  6:integrityViolationAlarm,
					  7:operationalViolationAlarm,
					  8:physicalViolationAlarm,
					  9:securityViolationAlarm,
					  10:timeDomainViolationAlarm
					"
		SYNTAX		INTEGER (0..10)

	ProbableCauseValue	::= TEXTUAL-CONVENTION
		STATUS		current
		DESCRIPTION	"Probable Cause (CCITT Rec. X.733)
					  0:invalid,
					  1:aIS,
					  2:callSetUpFailure,
					  3:degradedSignal,
					  4:farEndReceiverFailure,
					  5:framingError,
					  6:lossOfFrame,
					  7:lossOfPointer,
					  8:lossOfSignal,
					  9:payloadTypeMismatch,
					  10:transmissionError,
					  11:remoteAlarmInterface,
					  12:excessiveBER,
					  13:pathTraceMismatch,
					  51:backplaneFailure,
					  52:dataSetProblem,
					  53:equipmentIdentifierDuplication,
					  54:externalIFDeviceProblem,
					  55:lineCardProblem,
					  56:multiplexerProblem,
					  57:nEIdentifierDuplication,
					  58:powerProblem,
					  59:processorProblem,
					  60:protectionPathFailure,
					  61:receiverFailure,
					  62:replaceableUnitMissing,
					  63:replaceableUnitTypeMismatch,
					  64:synchronizationSourceMismatch,
					  65:terminalProblem,
					  66:timingProblem,
					  67:transmitterFailure,
					  68:trunkCardProblem,
					  69:replaceableUnitProblem,
					  101:airCompressorFailure,
					  102:airConditioningFailure,
					  103:airDryerFailure,
					  104:batteryDischarging,
					  105:batteryFailure,
					  106:commercialPowerFailure,
					  107:coolingFanFailure,
					  108:engineFailure,
					  109:fireDetectorFailure,
					  110:fuseFailure,
					  111:generatorFailure,
					  112:lowBatteryThreshold,
					  113:pumpFailure,
					  114:rectifierFailure,
					  115:rectifierHighVoltage,
					  116:rectifierLowFVoltage,
					  117:ventilationsSystemFailure,
					  118:enclosureDoorOpen,
					  119:explosiveGas,
					  120:fire,
					  121:flood,
					  122:highHumidity,
					  123:highTemperature,
					  124:highWind,
					  125:iceBuildUp,
					  126:intrusionDetection,
					  127:lowFuel,
					  128:lowHumidity,
					  129:lowCablePressure,
					  130:lowTemperature,
					  131:lowWater,
					  132:smoke,
					  133:toxicGas,
					  151:storageCapacityProblem,
					  152:memoryMismatch,
					  153:corruptData,
					  154:outOfCPUCycles,
					  155:sfwrEnvironmentProblem,
					  156:sfwrDownloadFailure,
					  157:communicationsProtocolError,
					  158:congestion,
					  159:heatingOrVentilationOrCoolingSystemProblem,
					  160:lANError,
					  161:performanceDegraded,
					  162:temperatureUnacceptable,
					  163:thresholdCrossed,
					  164:underlyingResourceUnavailable,
					  165:equipmentMalfunction,
					  166:configurationOrCustomizationError,
					  501:duplicateInformation,
					  502:informationMissing,
					  503:informationModificationDetected,
					  504:informationOutOfSequence,
					  505:unexpectedInformation,
					  506:denialOfService,
					  507:outOfService,
					  508:proceduralError,
					  509:cableTamper,
					  510:securityIntrusionDetection,
					  511:authenticationFailure,
					  512:breachOfConfidentiality,
					  513:unauthorisedAccessAttempt,
					  514:delayedInformation,
					  515:keyExpired,
					  516:outOfHoursActivity,
					  517:otherReasons,
					  518:bossHardwareFailure,
					  519:bossSystemSoftwareFailure,
					  520:bossApplicationSoftwareFailure,
					  521:bossDatabaseFailure,
					  522:bossNetworkFailure
					"
		SYNTAX		INTEGER (0..522)

	NormalAlarmValue	::= TEXTUAL-CONVENTION
		STATUS		current
		DESCRIPTION	"Normal/Alarm Type
					  0:Invalid,
					  1:Normal,
					  2:Alarm
					"
		SYNTAX		INTEGER (0..2)

	OffOnValue	::= TEXTUAL-CONVENTION
		STATUS		current
		DESCRIPTION	"Off/On Type
					  0:Invalid,
					  1:Off,
					  2:On
					"
		SYNTAX		INTEGER (0..2)

	NormalSendValue	::= TEXTUAL-CONVENTION
		STATUS		current
		DESCRIPTION	"Normal/Send Type
					  0:Invalid,
					  1:Normal,
					  2:Send
					"
		SYNTAX		INTEGER (0..2)

	NormalRcvdValue	::= TEXTUAL-CONVENTION
		STATUS		current
		DESCRIPTION	"Normal/Rcvd Type
					  0:Invalid,
					  1:Normal,
					  2:Rcvd
					"
		SYNTAX		INTEGER (0..2)

	ConnectDisconnectValue	::= TEXTUAL-CONVENTION
		STATUS		current
		DESCRIPTION	"Connect/Disconnect Type
					  Invalid(0),
					  Disconnect(1),
					  Connect(2)
					"
		SYNTAX		INTEGER (0..2)


-----------------------------------------------
-- enterprises Group Definitions
-----------------------------------------------

	pasolinkNeoStd OBJECT IDENTIFIER
		::= { pnms 113 }

        pasolinkNeoStdSystem OBJECT IDENTIFIER
		::= { pasolinkNeoStd 1 }

	pasolinkNeoStdInformation OBJECT IDENTIFIER
		::= { pasolinkNeoStd 2 }


-----------------------------------------------
-- system3 Group Definitions
-----------------------------------------------

	pnSystem OBJECT IDENTIFIER
		::= { pasolinkNeoStdSystem 1 }

	pnConfiguration OBJECT IDENTIFIER
		::= { pasolinkNeoStdSystem 2 }

	pnSys3Trap OBJECT IDENTIFIER
		::= { pasolinkNeoStdSystem 3 }


-----------------------------------------------
-- pnSystem Group Definitions
-----------------------------------------------

	pnSystemInfo OBJECT IDENTIFIER
		::= { pnSystem 1 }

        pnSystemEquipmentConfigTable OBJECT-TYPE
		SYNTAX		SEQUENCE OF PnSystemEquipmentConfigEntry
		ACCESS		not-accessible
		STATUS		mandatory
		DESCRIPTION	"Equipment Config"
		::= { pnSystemInfo 1 }

	pnSystemEquipmentConfigEntry OBJECT-TYPE
		SYNTAX		PnSystemEquipmentConfigEntry
		ACCESS		not-accessible
		STATUS		mandatory
		DESCRIPTION	"Equipment Config Entry"
		INDEX		{
					pnSysPasoIndex
					}
		::= { pnSystemEquipmentConfigTable 1 }

	PnSystemEquipmentConfigEntry ::= SEQUENCE {
		pnSysPasoIndex		IpAddress,
		pnSysEquipmentConfig        INTEGER
	}

	pnSysPasoIndex OBJECT-TYPE
		SYNTAX		IpAddress 
		ACCESS		read-only
		STATUS		mandatory
		DESCRIPTION	"Pasolink IP Address index"
		::= { pnSystemEquipmentConfigEntry 1 }

	pnSysEquipmentConfig OBJECT-TYPE
		SYNTAX		INTEGER (0..12)
		ACCESS		read-only
		STATUS		mandatory
		DESCRIPTION	"Equipment Config
					  0:Invalid,
					  1:1+0,
					  2:1+1,   -- Not used
					  3:1+1 HS,
					  4:1+1 TP,
					  5:1+0->1+1,  --Not used
					  7:1+0(4*2M),  -- Not used
					  8:1+0(20*2M),  -- Not used
					  9:2-WAY PDH,
					  10:2-WAY(TREE),  -- Not used
					  11:2-WAY(REP),  -- Not used
					  12:2-WAY(RING)  -- Not used
					"
		::= { pnSystemEquipmentConfigEntry 2 }


-----------------------------------------------
-- pnConfiguration Group Definitions
-----------------------------------------------

	pnCfgAux OBJECT IDENTIFIER
		::= { pnConfiguration 1 }

	pnCfgAuxInTable OBJECT-TYPE
		SYNTAX		SEQUENCE OF PnCfgAuxInEntry
		ACCESS		not-accessible
		STATUS		mandatory
		DESCRIPTION	"Aux Input Table"
		::= { pnCfgAux 1 }

	pnCfgAuxInEntry OBJECT-TYPE
		SYNTAX		PnCfgAuxInEntry
		ACCESS		not-accessible
		STATUS		mandatory
		INDEX		{
                                                pnCfgAuxInPasoIndex,
						pnCfgAuxInIndex
					}
		::= { pnCfgAuxInTable 1 }

	PnCfgAuxInEntry ::= SEQUENCE {
                                          pnCfgAuxInPasoIndex	   IpAddress,	
					  pnCfgAuxInIndex          INTEGER,
					  pnCfgAuxInItemName       DisplayString,
					  pnCfgAuxInItemType       INTEGER,
					  pnCfgAuxInOpenState      DisplayString,
					  pnCfgAuxInCloseState     DisplayString,
					  pnCfgAuxInSeverity       SeverityValue,
					  pnCfgAuxInAlarmType      AlarmTypeValue,
					  pnCfgAuxInProbableCause  ProbableCauseValue
					}

	pnCfgAuxInPasoIndex OBJECT-TYPE
		SYNTAX		IpAddress 
		ACCESS		read-only
		STATUS		mandatory
		DESCRIPTION	"Pasolink IP Address index"
		::= { pnCfgAuxInEntry 1 }

	pnCfgAuxInIndex OBJECT-TYPE
		SYNTAX		INTEGER (1..6)
		ACCESS		read-only
		STATUS		mandatory
		DESCRIPTION	"AUX Input Index"
		::= { pnCfgAuxInEntry 2 }

	pnCfgAuxInItemName OBJECT-TYPE
		SYNTAX		DisplayString (SIZE (0..32))
		ACCESS		read-only
		STATUS		mandatory
		DESCRIPTION	"AUX Input name.
					TRAP=configTrapPnSys3AuxInItemName"
		::= { pnCfgAuxInEntry 3 }

	pnCfgAuxInItemType OBJECT-TYPE
		SYNTAX		INTEGER (0..3)
		ACCESS		read-only
		STATUS		mandatory
		DESCRIPTION	"Configuration for AUX Input.
					  0:Invalid
					  1:Alarm with Open loop,
					  2:Alarm with Close loop,
					  3:Status
					
					TRAP=configTrapPnSys3AuxInItemType"
		::= { pnCfgAuxInEntry 4 }

	pnCfgAuxInOpenState OBJECT-TYPE
		SYNTAX		DisplayString (SIZE (0..32))
		ACCESS		read-only
		STATUS		mandatory
		DESCRIPTION	"Name when AUX Input is open status
					TRAP=configTrapPnSys3AuxInOpenState"
		::= { pnCfgAuxInEntry 5 }

	pnCfgAuxInCloseState OBJECT-TYPE
		SYNTAX		DisplayString (SIZE (0..32))
		ACCESS		read-only
		STATUS		mandatory
		DESCRIPTION	"Name when AUX Input is close status
					TRAP=configTrapPnSys3AuxInCloseState"
		::= { pnCfgAuxInEntry 6 }

	pnCfgAuxInSeverity OBJECT-TYPE
		SYNTAX		SeverityValue
		ACCESS		read-only
		STATUS		mandatory
		DESCRIPTION	"Sevirity when AUX Input is alarm.
					TRAP=configTrapPnSys3AuxInSeverity"
		::= { pnCfgAuxInEntry 7 }

	pnCfgAuxInAlarmType OBJECT-TYPE
		SYNTAX		AlarmTypeValue
		ACCESS		read-only
		STATUS		mandatory
		DESCRIPTION	"Alarm Type when AUX Input is alarm.
					TRAP=configTrapPnSys3AuxInAlarmType"
		::= { pnCfgAuxInEntry 8 }

	pnCfgAuxInProbableCause OBJECT-TYPE
		SYNTAX		ProbableCauseValue
		ACCESS		read-only
		STATUS		mandatory
		DESCRIPTION	"ProbableCause when AUX Input is alarm.
					TRAP=configTrapPnSys3AuxInProbableCause"
		::= { pnCfgAuxInEntry 9 }

	pnCfgAuxOutTable OBJECT-TYPE
		SYNTAX		SEQUENCE OF PnCfgAuxOutEntry
		ACCESS		not-accessible
		STATUS		mandatory
		DESCRIPTION	"AUX Output Table"
		::= { pnCfgAux 2 }

	pnCfgAuxOutEntry OBJECT-TYPE
		SYNTAX		PnCfgAuxOutEntry
		ACCESS		not-accessible
		STATUS		mandatory
		INDEX		{
                                                pnCfgAuxInPasoIndex,
						pnCfgAuxOutIndex
					}
		::= { pnCfgAuxOutTable 1 }

	PnCfgAuxOutEntry ::= SEQUENCE {
                                          pnCfgAuxOutPasoIndex	 IpAddress,
					  pnCfgAuxOutIndex       INTEGER,
					  pnCfgAuxOutItemName    DisplayString,
					  pnCfgAuxOutOpenState   DisplayString,
					  pnCfgAuxOutCloseState  DisplayString
					}

	pnCfgAuxOutPasoIndex OBJECT-TYPE
		SYNTAX		IpAddress 
		ACCESS		read-only
		STATUS		mandatory
		DESCRIPTION	"Pasolink IP Address index"
		::= { pnCfgAuxOutEntry 1 }

	pnCfgAuxOutIndex OBJECT-TYPE
		SYNTAX		INTEGER (1..4)
		ACCESS		read-only
		STATUS		mandatory
		DESCRIPTION	"AUX Output Index"
		::= { pnCfgAuxOutEntry 2 }

	pnCfgAuxOutItemName OBJECT-TYPE
		SYNTAX		DisplayString (SIZE (0..32))
		ACCESS		read-only
		STATUS		mandatory
		DESCRIPTION	"AUX Input name.
					TRAP=configTrapPnSys3AuxOutItemName"
		::= { pnCfgAuxOutEntry 3 }

	pnCfgAuxOutOpenState OBJECT-TYPE
		SYNTAX		DisplayString (SIZE (0..32))
		ACCESS		read-only
		STATUS		mandatory
		DESCRIPTION	"Name when AUX Output is open status
					TRAP=configTrapPnSys3AuxOutOpenState"
		::= { pnCfgAuxOutEntry 4 }

	pnCfgAuxOutCloseState OBJECT-TYPE
		SYNTAX		DisplayString (SIZE (0..32))
		ACCESS		read-only
		STATUS		mandatory
		DESCRIPTION	"Name when AUX Output is close status
					TRAP=configTrapPnSys3AuxOutCloseState"
		::= { pnCfgAuxOutEntry 5 }


-----------------------------------------------
-- pnSys3Trap Group Definitions
-----------------------------------------------

	pnSys3TrapCommon OBJECT IDENTIFIER
		::= { pnSys3Trap 1 }

	pnSys3TrapGenericVars OBJECT IDENTIFIER
		::= { pnSys3TrapCommon 1 }

	sys3PnTrapSequenceNumber OBJECT-TYPE
		SYNTAX		Counter
		ACCESS		read-only
		STATUS		mandatory
		DESCRIPTION	"PTR=trapGroupGroup.trapSequenceNumber"
		::= { pnSys3TrapGenericVars 1 }

	sys3PnTrapDate OBJECT-TYPE
		SYNTAX		DisplayString (SIZE (0..16))
		ACCESS		read-only
		STATUS		mandatory
		DESCRIPTION	"PTR=trapGroupGroup.trapDate"
		::= { pnSys3TrapGenericVars 2 }

	sys3PnTrapTime OBJECT-TYPE
		SYNTAX		DisplayString (SIZE (0..16))
		ACCESS		read-only
		STATUS		mandatory
		DESCRIPTION	"PTR=trapGroupGroup.trapTime"
		::= { pnSys3TrapGenericVars 3 }

	sys3PnTrapSource OBJECT-TYPE
		SYNTAX		OBJECT IDENTIFIER
		ACCESS		read-only
		STATUS		mandatory
		DESCRIPTION	"PTR=trapGroupGroup.trapSource"
		::= { pnSys3TrapGenericVars 4 }

	pnSys3TrapItemVar OBJECT IDENTIFIER
		::= { pnSys3Trap 2 }

	pnSys3ConfigTrapItemVar OBJECT IDENTIFIER
		::= { pnSys3TrapItemVar 1 }

	configItemPnSys3AuxInItemName OBJECT-TYPE
		SYNTAX		DisplayString (SIZE (0..32))
		ACCESS		read-only
		STATUS		mandatory
		DESCRIPTION	"AUX Input name."
		::= { pnSys3ConfigTrapItemVar 4 }

	configItemPnSys3AuxInItemType OBJECT-TYPE
		SYNTAX		INTEGER (0..3)
		ACCESS		read-only
		STATUS		mandatory
		DESCRIPTION	"Configuration for AUX Input.
					  0:Invalid
					  1:Alarm In Open state
					  2:Alarm In Close state
					  3:Status
					FLAG=SUMMARY_AUX"
		::= { pnSys3ConfigTrapItemVar 5 }

	configItemPnSys3AuxInOpenState OBJECT-TYPE
		SYNTAX		DisplayString (SIZE (0..32))
		ACCESS		read-only
		STATUS		mandatory
		DESCRIPTION	"Name of AUX input used in open state."
		::= { pnSys3ConfigTrapItemVar 6 }

	configItemPnSys3AuxInCloseState OBJECT-TYPE
		SYNTAX		DisplayString (SIZE (0..32))
		ACCESS		read-only
		STATUS		mandatory
		DESCRIPTION	"Name of AUX input used in close state."
		::= { pnSys3ConfigTrapItemVar 7 }

	configItemPnSys3AuxInSeverity OBJECT-TYPE
		SYNTAX		SeverityValue
		ACCESS		read-only
		STATUS		mandatory
		DESCRIPTION	"Severity when AUX Input is alarm.
				  Refer to SeverityValue of TEXTUAL-CONVENTION
					FLAG=SUMMARY_AUX"
		::= { pnSys3ConfigTrapItemVar 8 }

	configItemPnSys3AuxInAlarmType OBJECT-TYPE
		SYNTAX		AlarmTypeValue
		ACCESS		read-only
		STATUS		mandatory
		DESCRIPTION	"Alarm Type when AUX Input is alarm.
				  Refer to AlarmTypeValue of TEXTUAL-CONVENTION"
		::= { pnSys3ConfigTrapItemVar 9 }

	configItemPnSys3AuxInProbableCause OBJECT-TYPE
		SYNTAX		ProbableCauseValue
		ACCESS		read-only
		STATUS		mandatory
		DESCRIPTION	"ProbableCause when AUX Input is alarm.
		                      Refer to ProbableCauseValue of TEXTUAL-CONVENTION"
		::= { pnSys3ConfigTrapItemVar 10 }

	configItemPnSys3AuxOutItemName OBJECT-TYPE
		SYNTAX		DisplayString (SIZE (0..32))
		ACCESS		read-only
		STATUS		mandatory
		DESCRIPTION	"AUX Input name."
		::= { pnSys3ConfigTrapItemVar 11 }

	configItemPnSys3AuxOutOpenState OBJECT-TYPE
		SYNTAX		DisplayString (SIZE (0..32))
		ACCESS		read-only
		STATUS		mandatory
		DESCRIPTION	"Name of AUX output used in open state."
		::= { pnSys3ConfigTrapItemVar 12 }

	configItemPnSys3AuxOutCloseState OBJECT-TYPE
		SYNTAX		DisplayString (SIZE (0..32))
		ACCESS		read-only
		STATUS		mandatory
		DESCRIPTION	"Name of AUX output used in close state."
		::= { pnSys3ConfigTrapItemVar 13 }

	configTrapPnSys3AuxInItemName	TRAP-TYPE
		ENTERPRISE	pasolinkNeoStd
		VARIABLES	{
					  sys3PnTrapSequenceNumber,
					  sys3PnTrapDate,
					  sys3PnTrapTime,
					  sys3PnTrapSource,
					  configItemPnSys3AuxInItemName
					}
		DESCRIPTION "This trap is sent
					  when AUX Input name status is changed."
		::= 704

	configTrapPnSys3AuxInItemType	TRAP-TYPE
		ENTERPRISE	pasolinkNeoStd
		VARIABLES	{
					  sys3PnTrapSequenceNumber,
					  sys3PnTrapDate,
					  sys3PnTrapTime,
					  sys3PnTrapSource,
					  configItemPnSys3AuxInItemType
					}
		DESCRIPTION "This trap is sent
					  when Configuration for AUX Input status is changed."
		::= 705

	configTrapPnSys3AuxInOpenState	TRAP-TYPE
		ENTERPRISE	pasolinkNeoStd
		VARIABLES	{
					  sys3PnTrapSequenceNumber,
					  sys3PnTrapDate,
					  sys3PnTrapTime,
					  sys3PnTrapSource,
					  configItemPnSys3AuxInOpenState
					}
		DESCRIPTION "This trap is sent
					  when Name when AUX Input is open status status is changed."
		::= 706

	configTrapPnSys3AuxInCloseState	TRAP-TYPE
		ENTERPRISE	pasolinkNeoStd
		VARIABLES	{
					  sys3PnTrapSequenceNumber,
					  sys3PnTrapDate,
					  sys3PnTrapTime,
					  sys3PnTrapSource,
					  configItemPnSys3AuxInCloseState
					}
		DESCRIPTION "This trap is sent
					  when Name when AUX Input is close status status is changed."
		::= 707

	configTrapPnSys3AuxInSeverity	TRAP-TYPE
		ENTERPRISE	pasolinkNeoStd
		VARIABLES	{
					  sys3PnTrapSequenceNumber,
					  sys3PnTrapDate,
					  sys3PnTrapTime,
					  sys3PnTrapSource,
					  configItemPnSys3AuxInSeverity
					}
		DESCRIPTION "This trap is sent
					  when Sevirity when AUX Input is alarm status is changed."
		::= 708

	configTrapPnSys3AuxInAlarmType	TRAP-TYPE
		ENTERPRISE	pasolinkNeoStd
		VARIABLES	{
					  sys3PnTrapSequenceNumber,
					  sys3PnTrapDate,
					  sys3PnTrapTime,
					  sys3PnTrapSource,
					  configItemPnSys3AuxInAlarmType
					}
		DESCRIPTION "This trap is sent when Alarm Type when AUX Input is alarm status is changed."
		::= 709

	configTrapPnSys3AuxInProbableCause	TRAP-TYPE
		ENTERPRISE	pasolinkNeoStd
		VARIABLES	{
					  sys3PnTrapSequenceNumber,
					  sys3PnTrapDate,
					  sys3PnTrapTime,
					  sys3PnTrapSource,
					  configItemPnSys3AuxInProbableCause
					}
		DESCRIPTION "This trap is sent
					  when ProbableCause when AUX Input is alarm status is changed."
		::= 710

	configTrapPnSys3AuxOutItemName	TRAP-TYPE
		ENTERPRISE	pasolinkNeoStd
		VARIABLES	{
					  sys3PnTrapSequenceNumber,
					  sys3PnTrapDate,
					  sys3PnTrapTime,
					  sys3PnTrapSource,
					  configItemPnSys3AuxOutItemName
					}
		DESCRIPTION "This trap is sent
					  when AUX Input name status is changed."
		::= 711

	configTrapPnSys3AuxOutOpenState	TRAP-TYPE
		ENTERPRISE	pasolinkNeoStd
		VARIABLES	{
					  sys3PnTrapSequenceNumber,
					  sys3PnTrapDate,
					  sys3PnTrapTime,
					  sys3PnTrapSource,
					  configItemPnSys3AuxOutOpenState
					}
		DESCRIPTION "This trap is sent
					  when Name when AUX Output is open status status is changed."
		::= 712

	configTrapPnSys3AuxOutCloseState	TRAP-TYPE
		ENTERPRISE	pasolinkNeoStd
		VARIABLES	{
					  sys3PnTrapSequenceNumber,
					  sys3PnTrapDate,
					  sys3PnTrapTime,
					  sys3PnTrapSource,
					  configItemPnSys3AuxOutCloseState
					}
		DESCRIPTION "This trap is sent
					  when Name when AUX Output is close status status is changed."
		::= 713


-----------------------------------------------
-- pasoNeoSTD Group Definitions
-----------------------------------------------

	pnSummaryInfoGroup OBJECT IDENTIFIER
		::= { pasolinkNeoStdInformation 1 }

	pnTrapGroup OBJECT IDENTIFIER
		::= { pasolinkNeoStdInformation 2 }

	pnAlarmStatusGroup OBJECT IDENTIFIER
		::= { pasolinkNeoStdInformation 3 }

	pnEquipmentSetUpGroup OBJECT IDENTIFIER
		::= { pasolinkNeoStdInformation 4 }

	pnProvisioningGroup OBJECT IDENTIFIER
		::= { pasolinkNeoStdInformation 5 }

	pnMaintenanceGroup OBJECT IDENTIFIER
		::= { pasolinkNeoStdInformation 6 }

	pnInvEntryGroup OBJECT IDENTIFIER
		::= { pasolinkNeoStdInformation 7 }

	pnMeteringGroup OBJECT IDENTIFIER
		::= { pasolinkNeoStdInformation 8 }

	pnPmonGroup OBJECT IDENTIFIER
		::= { pasolinkNeoStdInformation 9 }

	pnPmonTxRxLevGroup OBJECT IDENTIFIER
		::= { pasolinkNeoStdInformation 10 }

	pnRmonGroup OBJECT IDENTIFIER
		::= { pasolinkNeoStdInformation 11 }

	pnGetMeasurementDataGroup OBJECT IDENTIFIER
		::= { pasolinkNeoStdInformation 12 }


-----------------------------------------------
-- pnSummaryInfoGroup Group Definitions
-----------------------------------------------

	pnSummaryItemTable OBJECT-TYPE
		SYNTAX		SEQUENCE OF PnSummaryItemEntry
		ACCESS		not-accessible
		STATUS		optional
		DESCRIPTION	"Summary Item Table"
		::= { pnSummaryInfoGroup 1 }

	pnSummaryItemEntry OBJECT-TYPE
		SYNTAX		PnSummaryItemEntry
		ACCESS		not-accessible
		STATUS		optional
		DESCRIPTION	"Summary Item Table Entry"
		INDEX		{
					pnSummaryItemPasoIndex	
					}
		::= { pnSummaryItemTable 1 }

	PnSummaryItemEntry ::= SEQUENCE {
					  pnSummaryItemPasoIndex 	IpAddress,
					  pnCtrlSummary			SeverityValue,
					  pnAuxIOSummary 		SeverityValue,
					  pnLinkPMONSummary 		SeverityValue,
					  pnIntfc1Summary 		SeverityValue,
					  pnIntfc2Summary 		SeverityValue
					 }					  
					         
	pnSummaryItemPasoIndex OBJECT-TYPE
		SYNTAX		IpAddress 
		ACCESS		read-only
		STATUS		mandatory
		DESCRIPTION	"Pasolink IP Address Index"
		::= { pnSummaryItemEntry 1 }

	pnCtrlSummary OBJECT-TYPE
		SYNTAX		SeverityValue
		ACCESS		read-only
		STATUS		mandatory
		DESCRIPTION	"CTRL Summary
				  Refer to SeverityValue of TEXTUAL-CONVENTION
					TRAP=partialSummaryTrapCTRL"
		::= { pnSummaryItemEntry 2 }

	pnAuxIOSummary OBJECT-TYPE
		SYNTAX		SeverityValue
		ACCESS		read-only
		STATUS		mandatory
		DESCRIPTION	"AUX IO Summary
				  Refer to SeverityValue of TEXTUAL-CONVENTION
					TRAP=partialSummaryTrapAux"
		::= { pnSummaryItemEntry 3 }

	pnLinkPMONSummary OBJECT-TYPE
		SYNTAX		SeverityValue
		ACCESS		read-only
		STATUS		mandatory
		DESCRIPTION	"Link Pmon Summary
				  Refer to SeverityValue of TEXTUAL-CONVENTION
					TRAP=partialSummaryTrapLpm"
		::= { pnSummaryItemEntry 4 }

	pnIntfc1Summary OBJECT-TYPE
		SYNTAX		SeverityValue
		ACCESS		read-only
		STATUS		mandatory
		DESCRIPTION	"INTFC1 Summary
				  Refer to SeverityValue of TEXTUAL-CONVENTION
					TRAP=partialSummaryTrapINTFC1"
		::= { pnSummaryItemEntry 5 }

	pnIntfc2Summary OBJECT-TYPE
		SYNTAX		SeverityValue
		ACCESS		read-only
		STATUS		mandatory
		DESCRIPTION	"INTFC2 Summary
				  Refer to SeverityValue of TEXTUAL-CONVENTION
					TRAP=partialSummaryTrapINTFC2"
		::= { pnSummaryItemEntry 6 }

	pnSummarySysInfoTable OBJECT-TYPE
		SYNTAX		SEQUENCE OF PnSummarySysInfoEntry
		ACCESS		not-accessible
		STATUS		mandatory
		DESCRIPTION	"Individual Summary"
		::= { pnSummaryInfoGroup 2 }

	pnSummarySysInfoEntry OBJECT-TYPE
		SYNTAX		PnSummarySysInfoEntry
		ACCESS		not-accessible
		STATUS		mandatory
		INDEX		{
					  pnSummarySysInfoPasoIndex,
					  pnSummarySysInfoIndex
					}
		::= { pnSummarySysInfoTable 1 }

	PnSummarySysInfoEntry ::= SEQUENCE {
					  pnSummarySysInfoPasoIndex	IpAddress,
					  pnSummarySysInfoIndex		INTEGER,
					  pnTruSummary			SeverityValue,
					  pnModemSummary		SeverityValue
					}

	pnSummarySysInfoPasoIndex OBJECT-TYPE
		SYNTAX		IpAddress 
		ACCESS		read-only
		STATUS		mandatory
		DESCRIPTION	"Pasolink IP Address Index"
		::= { pnSummarySysInfoEntry 1 }

	pnSummarySysInfoIndex OBJECT-TYPE
		SYNTAX		INTEGER{
					  no1-dirA(1),
					  no2-dirB(2)
					}
		ACCESS		read-only
		STATUS		mandatory
		DESCRIPTION	"No Index.
					 1:No.1 when EQUIPMENT CONFIG is TERM.
					   DIR-A when EQUIPMENT CONFIG is 2-WAY.
					 2:No.2 when EQUIPMENT CONFIG is TERM.
					   DIR-B when EQUIPMENT CONFIG is 2-WAY."
		::= { pnSummarySysInfoEntry 2 }

	pnTruSummary OBJECT-TYPE
		SYNTAX		SeverityValue
		ACCESS		read-only
		STATUS		mandatory
		DESCRIPTION	"TRU(ODU) Summary
				  Refer to SeverityValue of TEXTUAL-CONVENTION
					TRAP=partialSummaryTrapTRU"
		::= { pnSummarySysInfoEntry 3 }

	pnModemSummary OBJECT-TYPE
		SYNTAX		SeverityValue
		ACCESS		read-only
		STATUS		mandatory
		DESCRIPTION	"Modem Summary
				  Refer to SeverityValue of TEXTUAL-CONVENTION
					TRAP=partialSummaryTrapMODEM"
		::= { pnSummarySysInfoEntry 4 }


-----------------------------------------------
-- pnTrapGroup Group Definitions
-----------------------------------------------

	pnSTDTrapCommon OBJECT IDENTIFIER
		::= { pnTrapGroup 1 }

	pnSTDTrapGenericVars OBJECT IDENTIFIER
		::= { pnSTDTrapCommon 1 }

	pnTrapSequenceNumber OBJECT-TYPE
		SYNTAX		Counter
		ACCESS		read-only
		STATUS		mandatory
		DESCRIPTION	"Trap Sequence number(0..4294967295)"
		::= { pnSTDTrapGenericVars 1 }

	pnTrapDate OBJECT-TYPE
		SYNTAX		DisplayString (SIZE(10))
		ACCESS		read-only
		STATUS		mandatory
		DESCRIPTION	"Trap Generate Date
					 This value shows YYYY/MM/DD.
					 YYYY means 4-digit year.
					 MM means 2-digit month.
					 DD means 2-digit day."
		::= { pnSTDTrapGenericVars 2 }

	pnTrapTime OBJECT-TYPE
		SYNTAX		DisplayString(SIZE(8))
		ACCESS		read-only
		STATUS		mandatory
		DESCRIPTION	"Trap Generate Time
					 This value shows hh:mm:ss.
					 hh means 2-digit hour.
					 mm means 2-digit minute.
					 ss means 2-digit second."
		::= { pnSTDTrapGenericVars 3 }

	pnTrapSource OBJECT-TYPE
		SYNTAX		OBJECT IDENTIFIER
		ACCESS		read-only
		STATUS		mandatory
		DESCRIPTION	"TRAP Source"
		::= { pnSTDTrapGenericVars 4 }

	pnSTDTrapX733Vars OBJECT IDENTIFIER
		::= { pnSTDTrapCommon 2 }

	pnSeverity OBJECT-TYPE
		SYNTAX		SeverityValue
		ACCESS		read-only
		STATUS		mandatory
		DESCRIPTION	"Severity (CCITT Rec. X.733)
			 	  Refer to SeverityValue of TEXTUAL-CONVENTION"
		::= { pnSTDTrapX733Vars 1 }

	pnAlarmType OBJECT-TYPE
		SYNTAX		AlarmTypeValue
		ACCESS		read-only
		STATUS		mandatory
		DESCRIPTION	"Alaem Type (CCITT Rec. X.733)
				  Refer to AlarmTypeValue of TEXTUAL-CONVENTION"
		::= { pnSTDTrapX733Vars 2 }

	pnProbableCause OBJECT-TYPE
		SYNTAX		ProbableCauseValue
		ACCESS		read-only
		STATUS		mandatory
		DESCRIPTION	"Probable Cause (CCITT Rec. X.733)
				  Refer to ProbableCauseValue of TEXTUAL-CONVENTION"
		::= { pnSTDTrapX733Vars 3 }

	pnSTDTrapItemType OBJECT IDENTIFIER
		::= { pnTrapGroup 2 }

	pnSTDStatusTrapItemType OBJECT IDENTIFIER
		::= { pnSTDTrapItemType 1 }

	pnStatusTypeAux OBJECT-TYPE
		SYNTAX		INTEGER (0..3)
		ACCESS		read-only
		STATUS		mandatory
		DESCRIPTION	"Aux Status Type
					  Invalid(0),
					  Alarm In Open state(1),
					  Alarm In Close state(2),
					  Status(3)"
		::= { pnSTDStatusTrapItemType 1 }

	pnStatusTypeAis OBJECT-TYPE
		SYNTAX		INTEGER (0..2)
		ACCESS		read-only
		STATUS		mandatory
		DESCRIPTION	"AIS Status Type
					  Invalid(0),
					  Alarm Type(1),
					  Status Type(2)"
		::= { pnSTDStatusTrapItemType 2 }

	pnSTDTrapItemVar OBJECT IDENTIFIER
		::= { pnTrapGroup 3 }

	pnSTDPartialSummaryTrapItemVar OBJECT IDENTIFIER
		::= { pnSTDTrapItemVar 1 }

	partialSummaryItemTRU OBJECT-TYPE
		SYNTAX		SeverityValue
		ACCESS		read-only
		STATUS		mandatory
		DESCRIPTION	"TRU Summary
				  Refer to SeverityValue of TEXTUAL-CONVENTION"
		::= { pnSTDPartialSummaryTrapItemVar 1 }

	partialSummaryItemINTFC1 OBJECT-TYPE
		SYNTAX		SeverityValue
		ACCESS		read-only
		STATUS		mandatory
		DESCRIPTION	"INTFC1 Summary
				  Refer to SeverityValue of TEXTUAL-CONVENTION"
		::= { pnSTDPartialSummaryTrapItemVar 2 }

	partialSummaryItemCTRL OBJECT-TYPE
		SYNTAX		SeverityValue
		ACCESS		read-only
		STATUS		mandatory
		DESCRIPTION	"CTRL Summary
				  Refer to SeverityValue of TEXTUAL-CONVENTION"
		::= { pnSTDPartialSummaryTrapItemVar 3 }

	partialSummaryItemAux OBJECT-TYPE
		SYNTAX		SeverityValue
		ACCESS		read-only
		STATUS		mandatory
		DESCRIPTION	"AUX Summary
				  Refer to SeverityValue of TEXTUAL-CONVENTION"
		::= { pnSTDPartialSummaryTrapItemVar 4 }

	partialSummaryItemLpm OBJECT-TYPE
		SYNTAX		SeverityValue
		ACCESS		read-only
		STATUS		mandatory
		DESCRIPTION	"LPM(Link Performance Monitor) Summary
				  Refer to SeverityValue of TEXTUAL-CONVENTION"
		::= { pnSTDPartialSummaryTrapItemVar 5 }

	partialSummaryItemINTFC2 OBJECT-TYPE
		SYNTAX		SeverityValue
		ACCESS		read-only
		STATUS		mandatory
		DESCRIPTION	"INTFC2 Summary
				  Refer to SeverityValue of TEXTUAL-CONVENTION"
		::= { pnSTDPartialSummaryTrapItemVar 6 }

	partialSummaryItemMODEM OBJECT-TYPE
		SYNTAX		SeverityValue
		ACCESS		read-only
		STATUS		mandatory
		DESCRIPTION	"MODEM Summary
				  Refer to SeverityValue of TEXTUAL-CONVENTION"
		::= { pnSTDPartialSummaryTrapItemVar 7 }

	pnSTDAlarmTrapItemVar OBJECT IDENTIFIER
		::= { pnSTDTrapItemVar 2 }

	alarmItemPnSTDTxPowerAlarm OBJECT-TYPE
		SYNTAX		NormalAlarmValue
		ACCESS		read-only
		STATUS		mandatory
		DESCRIPTION	"TX POWER
					Refer to NormalAlarmValue of TEXTUAL-CONVENTION
					FLAG=SUMMARY_TRU
					severity=major
					alarmType=equipmentAlarm
					probableCause=transmitterFailure"
		::= { pnSTDAlarmTrapItemVar 1 }

	alarmItemPnSTDTxInputAlarm OBJECT-TYPE
		SYNTAX		NormalAlarmValue
		ACCESS		read-only
		STATUS		mandatory
		DESCRIPTION	"TX INPUT
					Refer to NormalAlarmValue of TEXTUAL-CONVENTION
					FLAG=SUMMARY_TRU
					severity=major
					alarmType=equipmentAlarm
					probableCause=transmitterFailure"
		::= { pnSTDAlarmTrapItemVar 2 }

	alarmItemPnSTDRxLevelAlarm OBJECT-TYPE
		SYNTAX		NormalAlarmValue
		ACCESS		read-only
		STATUS		mandatory
		DESCRIPTION	"RX LEVEL
					Refer to NormalAlarmValue of TEXTUAL-CONVENTION
					FLAG=SUMMARY_TRU
					severity=major
					alarmType=communicationAlarm
					probableCause=receiverFailure"
		::= { pnSTDAlarmTrapItemVar 3 }

	alarmItemPnSTDApcAlarm OBJECT-TYPE
		SYNTAX		NormalAlarmValue
		ACCESS		read-only
		STATUS		mandatory
		DESCRIPTION	"APC
					Refer to NormalAlarmValue of TEXTUAL-CONVENTION
					FLAG=SUMMARY_TRU
					severity=major
					alarmType=equipmentAlarm
					probableCause=equipmentMalfunction"
		::= { pnSTDAlarmTrapItemVar 4 }

	alarmItemPnSTDTRUCPUAlarm OBJECT-TYPE
		SYNTAX		NormalAlarmValue
		ACCESS		read-only
		STATUS		mandatory
		DESCRIPTION	"ODU CPU
					Refer to NormalAlarmValue of TEXTUAL-CONVENTION
					FLAG=SUMMARY_TRU
					severity=major
					alarmType=communicationAlarm
					probableCause=equipmentMalfunction"
		::= { pnSTDAlarmTrapItemVar 5 }

	alarmItemPnSTDModemAlarm OBJECT-TYPE
		SYNTAX		NormalAlarmValue
		ACCESS		read-only
		STATUS		mandatory
		DESCRIPTION	"MODEM MODULE
					Refer to NormalAlarmValue of TEXTUAL-CONVENTION
					FLAG=SUMMARY_MODEM
					severity=major
					alarmType=equipmentAlarm
					probableCause=equipmentMalfunction"
		::= { pnSTDAlarmTrapItemVar 6 }

	alarmItemPnSTDModemUneq OBJECT-TYPE
		SYNTAX		NormalAlarmValue
		ACCESS		read-only
		STATUS		mandatory
		DESCRIPTION	"MODEM UNEQUIPPED
					Refer to NormalAlarmValue of TEXTUAL-CONVENTION
					FLAG=SUMMARY_MODEM
					severity=major
					alarmType=equipmentAlarm
					probableCause=equipmentMalfunction"
		::= { pnSTDAlarmTrapItemVar 7 }

	alarmItemPnSTDHighBERAlarm OBJECT-TYPE
		SYNTAX		NormalAlarmValue
		ACCESS		read-only
		STATUS		mandatory
		DESCRIPTION	"HIGH BER
					Refer to NormalAlarmValue of TEXTUAL-CONVENTION
					FLAG=SUMMARY_MODEM
					severity=major
					alarmType=qualityOfServiceAlarm
					probableCause=excessiveBER"
		::= { pnSTDAlarmTrapItemVar 8 }

	alarmItemPnSTDLowBERAlarm OBJECT-TYPE
		SYNTAX		NormalAlarmValue
		ACCESS		read-only
		STATUS		mandatory
		DESCRIPTION	"LOW BER
					Refer to NormalAlarmValue of TEXTUAL-CONVENTION
					FLAG=SUMMARY_MODEM
					severity=minor
					alarmType=qualityOfServiceAlarm
					probableCause=degradedSignal"
		::= { pnSTDAlarmTrapItemVar 9 }

	alarmItemPnSTDModAlarm OBJECT-TYPE
		SYNTAX		NormalAlarmValue
		ACCESS		read-only
		STATUS		mandatory
		DESCRIPTION	"MOD
					Refer to NormalAlarmValue of TEXTUAL-CONVENTION
					FLAG=SUMMARY_MODEM
					severity=major
					alarmType=equipmentAlarm
					probableCause=transmitterFailure"
		::= { pnSTDAlarmTrapItemVar 10 }

	alarmItemPnSTDDemAlarm OBJECT-TYPE
		SYNTAX		NormalAlarmValue
		ACCESS		read-only
		STATUS		mandatory
		DESCRIPTION	"DEM
					Refer to NormalAlarmValue of TEXTUAL-CONVENTION
					FLAG=SUMMARY_MODEM
					severity=major
					alarmType=equipmentAlarm
					probableCause=receiverFailure"
		::= { pnSTDAlarmTrapItemVar 11 }

	alarmItemPnSTDXIfLevelAlarm OBJECT-TYPE
		SYNTAX		NormalAlarmValue
		ACCESS		read-only
		STATUS		mandatory
		DESCRIPTION	"XIF
					Refer to NormalAlarmValue of TEXTUAL-CONVENTION
					FLAG=SUMMARY_MODEM
					severity=major
					alarmType=communicationAlarm
					probableCause=lossOfSignal"
		::= { pnSTDAlarmTrapItemVar 12 }

	alarmItemPnSTDXContAlarm OBJECT-TYPE
		SYNTAX		NormalAlarmValue
		ACCESS		read-only
		STATUS		mandatory
		DESCRIPTION	"This item is not used.
				 XCTRL
					Refer to NormalAlarmValue of TEXTUAL-CONVENTION
					FLAG=SUMMARY_MODEM
					severity=major
					alarmType=equipmentAlarm
					probableCause=equipmentMalfunction"
		::= { pnSTDAlarmTrapItemVar 13 }

	alarmItemPnSTDPSAlarm OBJECT-TYPE
		SYNTAX		NormalAlarmValue
		ACCESS		read-only
		STATUS		mandatory
		DESCRIPTION	"POWER SUPPLY
					Refer to NormalAlarmValue of TEXTUAL-CONVENTION
					FLAG=SUMMARY_MODEM
					severity=major
					alarmType=equipmentAlarm
					probableCause=powerProblem"
		::= { pnSTDAlarmTrapItemVar 14 }

	alarmItemPnSTDIfCableShort OBJECT-TYPE
		SYNTAX		NormalAlarmValue
		ACCESS		read-only
		STATUS		mandatory
		DESCRIPTION	"IF CABLE SHORT
					Refer to NormalAlarmValue of TEXTUAL-CONVENTION
					FLAG=SUMMARY_MODEM
					severity=major
					alarmType=equipmentAlarm
					probableCause=equipmentMalfunction"
		::= { pnSTDAlarmTrapItemVar 15 }

	alarmItemPnSTDLof OBJECT-TYPE
		SYNTAX		NormalAlarmValue
		ACCESS		read-only
		STATUS		mandatory
		DESCRIPTION	"LOF
					Refer to NormalAlarmValue of TEXTUAL-CONVENTION
					FLAG=SUMMARY_MODEM
					severity=major
					alarmType=communicationAlarm
					probableCause=lossOfFrame"
		::= { pnSTDAlarmTrapItemVar 16 }

	alarmItemPnSTDCableEQLAlarm OBJECT-TYPE
		SYNTAX		NormalAlarmValue
		ACCESS		read-only
		STATUS		mandatory
		DESCRIPTION	"CABLE EQL
					Refer to NormalAlarmValue of TEXTUAL-CONVENTION
					FLAG=SUMMARY_MODEM
					severity=major
					alarmType=equipmentAlarm
					probableCause=equipmentMalfunction"
		::= { pnSTDAlarmTrapItemVar 17 }

	alarmItemPnSTDXRefAlarm OBJECT-TYPE
		SYNTAX		NormalAlarmValue
		ACCESS		read-only
		STATUS		mandatory
		DESCRIPTION	"XREF
					Refer to NormalAlarmValue of TEXTUAL-CONVENTION
					FLAG=SUMMARY_MODEM
					severity=minor
					alarmType=equipmentAlarm
					probableCause=equipmentMalfunction"
		::= { pnSTDAlarmTrapItemVar 18 }

	alarmItemPnSTDIntfcMAlarm OBJECT-TYPE
		SYNTAX		NormalAlarmValue
		ACCESS		read-only
		STATUS		mandatory
		DESCRIPTION	"INTFC(1) MODULE
					Refer to NormalAlarmValue of TEXTUAL-CONVENTION
					FLAG=SUMMARY_INTFC1
					severity=major
					alarmType=equipmentAlarm
					probableCause=equipmentMalfunction"
		::= { pnSTDAlarmTrapItemVar 19 }

	alarmItemPnSTDIntfcMUneq OBJECT-TYPE
		SYNTAX		NormalAlarmValue
		ACCESS		read-only
		STATUS		mandatory
		DESCRIPTION	"INTFC(1) UNEQUIPPED
					Refer to NormalAlarmValue of TEXTUAL-CONVENTION
					FLAG=SUMMARY_INTFC1
					severity=major
					alarmType=equipmentAlarm
					probableCause=equipmentMalfunction"
		::= { pnSTDAlarmTrapItemVar 20 }

	alarmItemPnSTDInputLos OBJECT-TYPE
		SYNTAX		OCTET STRING (SIZE (6))
		ACCESS		read-only
		STATUS		mandatory
		DESCRIPTION	"INPUT LOS CHxx
					(xx : 1-48)
					  0:Normal,
					  1:Alarm
					
					 [Bit Description]
					  Bit0 = CH01 (0: Normal,1: Alarm)
					  Bit1 = CH02
					  Bit2 = CH02
					  ...
					  Bit46 = CH47
					  Bit47 = CH48
					FLAG=SUMMARY_INTFC1
					severity=major
					alarmType=communicationAlarm
					probableCause=lossOfSignal"
		::= { pnSTDAlarmTrapItemVar 21 }

	alarmItemPnSTDLosMUXWork OBJECT-TYPE
		SYNTAX		NormalAlarmValue
		ACCESS		read-only
		STATUS		mandatory
		DESCRIPTION	"STM-1(1) LOS(MUX)
					Refer to NormalAlarmValue of TEXTUAL-CONVENTION
					FLAG=SUMMARY_INTFC1
					severity=major
					alarmType=communicationAlarm
					probableCause=lossOfSignal"
		::= { pnSTDAlarmTrapItemVar 23 }

	alarmItemPnSTDLosDMRWork OBJECT-TYPE
		SYNTAX		NormalAlarmValue
		ACCESS		read-only
		STATUS		mandatory
		DESCRIPTION	"STM-1(1) LOS(DMR)
					Refer to NormalAlarmValue of TEXTUAL-CONVENTION
					FLAG=SUMMARY_INTFC1
					severity=major
					alarmType=communicationAlarm
					probableCause=lossOfSignal"
		::= { pnSTDAlarmTrapItemVar 24 }

	alarmItemPnSTDUsageError OBJECT-TYPE
		SYNTAX		OCTET STRING (SIZE (6))
		ACCESS		read-only
		STATUS		mandatory
		DESCRIPTION	"USAGE ERROR CHxx
					(xx : 1-48)
					  0:Normal,
					  1:Alarm
					
					 [Bit Description]
					  Bit0 = CH01 (0: Normal,1: Alarm)
					  Bit1 = CH02
					  Bit2 = CH02
					  ...
					  Bit46 = CH47
					  Bit47 = CH48
					FLAG=SUMMARY_INTFC1
					severity=major
					alarmType=operationalViolationAlarm
					probableCause=callSetUpFailure"
		::= { pnSTDAlarmTrapItemVar 25 }

	alarmItemPnSTDLink OBJECT-TYPE
		SYNTAX		NormalAlarmValue
		ACCESS		read-only
		STATUS		mandatory
		DESCRIPTION	"LAN LINK PORTx
					(x : 1-4)
					Refer to NormalAlarmValue of TEXTUAL-CONVENTION
					FLAG=SUMMARY_INTFC1
					severity=major
					alarmType=communicationAlarm
					probableCause=lANError"
		::= { pnSTDAlarmTrapItemVar 26 }

	alarmItemPnSTDEBERMUXWork OBJECT-TYPE
		SYNTAX		NormalAlarmValue
		ACCESS		read-only
		STATUS		mandatory
		DESCRIPTION	"STM-1(1) E-BER(MUX)
					Refer to NormalAlarmValue of TEXTUAL-CONVENTION
					FLAG=SUMMARY_INTFC1
					severity=major
					alarmType=qualityOfServiceAlarm
					probableCause=excessiveBER"
		::= { pnSTDAlarmTrapItemVar 28 }

	alarmItemPnSTDEBERDMRWork OBJECT-TYPE
		SYNTAX		NormalAlarmValue
		ACCESS		read-only
		STATUS		mandatory
		DESCRIPTION	"STM-1(1) E-BER(DMR)
					Refer to NormalAlarmValue of TEXTUAL-CONVENTION
					FLAG=SUMMARY_INTFC1
					severity=major
					alarmType=qualityOfServiceAlarm
					probableCause=excessiveBER"
		::= { pnSTDAlarmTrapItemVar 29 }

	alarmItemPnSTDSDMUXWork OBJECT-TYPE
		SYNTAX		NormalAlarmValue
		ACCESS		read-only
		STATUS		mandatory
		DESCRIPTION	"STM-1(1) SD(MUX)
					Refer to NormalAlarmValue of TEXTUAL-CONVENTION
					FLAG=SUMMARY_INTFC1
					severity=minor
					alarmType=qualityOfServiceAlarm
					probableCause=degradedSignal"
		::= { pnSTDAlarmTrapItemVar 30 }

	alarmItemPnSTDSDDMRWork OBJECT-TYPE
		SYNTAX		NormalAlarmValue
		ACCESS		read-only
		STATUS		mandatory
		DESCRIPTION	"STM-1(1) SD(DMR)
					Refer to NormalAlarmValue of TEXTUAL-CONVENTION
					FLAG=SUMMARY_INTFC1
					severity=minor
					alarmType=qualityOfServiceAlarm
					probableCause=degradedSignal"
		::= { pnSTDAlarmTrapItemVar 31 }

	alarmItemPnSTDIntfcSAlarm OBJECT-TYPE
		SYNTAX		NormalAlarmValue
		ACCESS		read-only
		STATUS		mandatory
		DESCRIPTION	"INTFC(2) MODULE
					Refer to NormalAlarmValue of TEXTUAL-CONVENTION
					FLAG=SUMMARY_INTFC2
					severity=major
					alarmType=equipmentAlarm
					probableCause=equipmentMalfunction"
		::= { pnSTDAlarmTrapItemVar 32 }

	alarmItemPnSTDIntfcSUneq OBJECT-TYPE
		SYNTAX		NormalAlarmValue
		ACCESS		read-only
		STATUS		mandatory
		DESCRIPTION	"INTFC(2) UNEQUIPPED
					Refer to NormalAlarmValue of TEXTUAL-CONVENTION
					FLAG=SUMMARY_INTFC2
					severity=major
					alarmType=equipmentAlarm
					probableCause=equipmentMalfunction"
		::= { pnSTDAlarmTrapItemVar 33 }

	alarmItemPnSTDLosMUXProt OBJECT-TYPE
		SYNTAX		NormalAlarmValue
		ACCESS		read-only
		STATUS		mandatory
		DESCRIPTION	"STM-1(2) LOS(MUX)
					Refer to NormalAlarmValue of TEXTUAL-CONVENTION
					FLAG=SUMMARY_INTFC2
					severity=major
					alarmType=communicationAlarm
					probableCause=lossOfSignal"
		::= { pnSTDAlarmTrapItemVar 34 }

	alarmItemPnSTDEBERMUXProt OBJECT-TYPE
		SYNTAX		NormalAlarmValue
		ACCESS		read-only
		STATUS		mandatory
		DESCRIPTION	"STM-1(2) E-BER(MUX)
					Refer to NormalAlarmValue of TEXTUAL-CONVENTION
					FLAG=SUMMARY_INTFC2
					severity=major
					alarmType=qualityOfServiceAlarm
					probableCause=excessiveBER"
		::= { pnSTDAlarmTrapItemVar 35 }

	alarmItemPnSTDEBERDMRProt OBJECT-TYPE
		SYNTAX		NormalAlarmValue
		ACCESS		read-only
		STATUS		mandatory
		DESCRIPTION	"STM-1(2) E-BER(DMR)
					Refer to NormalAlarmValue of TEXTUAL-CONVENTION
					FLAG=SUMMARY_INTFC2
					severity=major
					alarmType=qualityOfServiceAlarm
					probableCause=excessiveBER"
		::= { pnSTDAlarmTrapItemVar 36 }

	alarmItemPnSTDSDMUXProt OBJECT-TYPE
		SYNTAX		NormalAlarmValue
		ACCESS		read-only
		STATUS		mandatory
		DESCRIPTION	"STM-1(2) SD(MUX)
					Refer to NormalAlarmValue of TEXTUAL-CONVENTION
					FLAG=SUMMARY_INTFC2
					severity=minor
					alarmType=qualityOfServiceAlarm
					probableCause=degradedSignal"
		::= { pnSTDAlarmTrapItemVar 37 }

	alarmItemPnSTDSDDMRProt OBJECT-TYPE
		SYNTAX		NormalAlarmValue
		ACCESS		read-only
		STATUS		mandatory
		DESCRIPTION	"STM-1(2) SD(DMR)
					Refer to NormalAlarmValue of TEXTUAL-CONVENTION
					FLAG=SUMMARY_INTFC2
					severity=minor
					alarmType=qualityOfServiceAlarm
					probableCause=degradedSignal"
		::= { pnSTDAlarmTrapItemVar 38 }

	alarmItemPnSTDWSLos OBJECT-TYPE
		SYNTAX		NormalAlarmValue
		ACCESS		read-only
		STATUS		mandatory
		DESCRIPTION	"WS INPUT LOS
					Refer to NormalAlarmValue of TEXTUAL-CONVENTION
					FLAG=SUMMARY_INTFC2
					severity=minor
					alarmType=communicationAlarm
					probableCause=lossOfSignal"
		::= { pnSTDAlarmTrapItemVar 39 }

	alarmItemPnSTDSCLanLink OBJECT-TYPE
		SYNTAX		NormalAlarmValue
		ACCESS		read-only
		STATUS		mandatory
		DESCRIPTION	"INTFC(2) LAN LINK PORTx
					(x : 1-2)
					Refer to NormalAlarmValue of TEXTUAL-CONVENTION
					FLAG=SUMMARY_INTFC2
					severity=minor
					alarmType=communicationAlarm
					probableCause=lANError"
		::= { pnSTDAlarmTrapItemVar 40 }

	alarmItemPnSTDCTRLAlarm OBJECT-TYPE
		SYNTAX		NormalAlarmValue
		ACCESS		read-only
		STATUS		mandatory
		DESCRIPTION	"CTRL MODULE
					Refer to NormalAlarmValue of TEXTUAL-CONVENTION
					FLAG=SUMMARY_CTRL
					severity=major
					alarmType=equipmentAlarm
					probableCause=equipmentMalfunction"
		::= { pnSTDAlarmTrapItemVar 42 }

	alarmItemPnSTDAPSSWFail OBJECT-TYPE
		SYNTAX		NormalAlarmValue
		ACCESS		read-only
		STATUS		mandatory
		DESCRIPTION	"APS SW FAIL
					Refer to NormalAlarmValue of TEXTUAL-CONVENTION
					FLAG=SUMMARY_CTRL
					severity=major
					alarmType=equipmentAlarm
					probableCause=equipmentMalfunction"
		::= { pnSTDAlarmTrapItemVar 44 }

	alarmItemPnSTDTcn15minTotalOFS OBJECT-TYPE
		SYNTAX		NormalAlarmValue
		ACCESS		read-only
		STATUS		mandatory
		DESCRIPTION	"TCN-OFS-15min TOTAL
					TCN-OFS-15min(DIR-A) TOTAL
					Refer to NormalAlarmValue of TEXTUAL-CONVENTION
					FLAG=SUMMARY_LPM
					severity=minor
					alarmType=qualityOfServiceAlarm
					probableCause=thresholdCrossed"
		::= { pnSTDAlarmTrapItemVar 46 }

	alarmItemPnSTDTcn15minTotalUAS OBJECT-TYPE
		SYNTAX		NormalAlarmValue
		ACCESS		read-only
		STATUS		mandatory
		DESCRIPTION	"TCN-UAS-15min TOTAL
					TCN-UAS-15min(DIR-A) TOTAL
					Refer to NormalAlarmValue of TEXTUAL-CONVENTION
					FLAG=SUMMARY_LPM
					severity=minor
					alarmType=qualityOfServiceAlarm
					probableCause=thresholdCrossed"
		::= { pnSTDAlarmTrapItemVar 47 }

	alarmItemPnSTDTcn15minTotalES OBJECT-TYPE
		SYNTAX		NormalAlarmValue
		ACCESS		read-only
		STATUS		mandatory
		DESCRIPTION	"TCN-ES-15min TOTAL
					TCN-ES-15min(DIR-A) TOTAL
					Refer to NormalAlarmValue of TEXTUAL-CONVENTION
					FLAG=SUMMARY_LPM
					severity=minor
					alarmType=qualityOfServiceAlarm
					probableCause=thresholdCrossed"
		::= { pnSTDAlarmTrapItemVar 48 }

	alarmItemPnSTDTcn15minTotalSES OBJECT-TYPE
		SYNTAX		NormalAlarmValue
		ACCESS		read-only
		STATUS		mandatory
		DESCRIPTION	"TCN-SES-15min TOTAL
					TCN-SES-15min(DIR-A) TOTAL
					Refer to NormalAlarmValue of TEXTUAL-CONVENTION
					FLAG=SUMMARY_LPM
					severity=minor
					alarmType=qualityOfServiceAlarm
					probableCause=thresholdCrossed"
		::= { pnSTDAlarmTrapItemVar 49 }

	alarmItemPnSTDTcn15minTotalBBE OBJECT-TYPE
		SYNTAX		NormalAlarmValue
		ACCESS		read-only
		STATUS		mandatory
		DESCRIPTION	"TCN-BBE-15min TOTAL
					TCN-BBE-15min(DIR-A) TOTAL
					Refer to NormalAlarmValue of TEXTUAL-CONVENTION
					FLAG=SUMMARY_LPM
					severity=minor
					alarmType=qualityOfServiceAlarm
					probableCause=thresholdCrossed"
		::= { pnSTDAlarmTrapItemVar 50 }

	alarmItemPnSTDTcn15minTotalSEP OBJECT-TYPE
		SYNTAX		NormalAlarmValue
		ACCESS		read-only
		STATUS		mandatory
		DESCRIPTION	"TCN-SEP-15min TOTAL
					TCN-SEP-15min(DIR-A) TOTAL
					Refer to NormalAlarmValue of TEXTUAL-CONVENTION
					FLAG=SUMMARY_LPM
					severity=minor
					alarmType=qualityOfServiceAlarm
					probableCause=thresholdCrossed"
		::= { pnSTDAlarmTrapItemVar 51 }

	alarmItemPnSTDTcn15minCHUAS OBJECT-TYPE
		SYNTAX		OCTET STRING (SIZE (1))
		ACCESS		read-only
		STATUS		mandatory
		DESCRIPTION	"This item is not used.
					TCN-UAS-15min CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnSTDAlarmTrapItemVar 53 }

	alarmItemPnSTDTcn15minCHES OBJECT-TYPE
		SYNTAX		OCTET STRING (SIZE (1))
		ACCESS		read-only
		STATUS		mandatory
		DESCRIPTION	"This item is not used.
				TCN-ES-15min CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnSTDAlarmTrapItemVar 54 }

	alarmItemPnSTDTcn15minCHSES OBJECT-TYPE
		SYNTAX		OCTET STRING (SIZE (1))
		ACCESS		read-only
		STATUS		mandatory
		DESCRIPTION	"This item is not used.
				TCN-SES-15min CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnSTDAlarmTrapItemVar 55 }

	alarmItemPnSTDTcn15minCHBBE OBJECT-TYPE
		SYNTAX		OCTET STRING (SIZE (1))
		ACCESS		read-only
		STATUS		mandatory
		DESCRIPTION	"This item is not used.
				TCN-BBE-15min CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnSTDAlarmTrapItemVar 56 }

	alarmItemPnSTDTcn15minCHSEP OBJECT-TYPE
		SYNTAX		OCTET STRING (SIZE (1))
		ACCESS		read-only
		STATUS		mandatory
		DESCRIPTION	"This item is not used.
				TCN-SEP-15min CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnSTDAlarmTrapItemVar 57 }

	alarmItemPnSTDTcn1dayTotalOFS OBJECT-TYPE
		SYNTAX		NormalAlarmValue
		ACCESS		read-only
		STATUS		mandatory
		DESCRIPTION	"TCN-OFS-1day TOTAL
					TCN-OFS-1day(DIR-A) TOTAL
					Refer to NormalAlarmValue of TEXTUAL-CONVENTION
					FLAG=SUMMARY_LPM
					severity=minor
					alarmType=qualityOfServiceAlarm
					probableCause=thresholdCrossed"
		::= { pnSTDAlarmTrapItemVar 58 }

	alarmItemPnSTDTcn1dayTotalUAS OBJECT-TYPE
		SYNTAX		NormalAlarmValue
		ACCESS		read-only
		STATUS		mandatory
		DESCRIPTION	"TCN-UAS-1day TOTAL
					TCN-UAS-1day(DIR-A) TOTAL
					Refer to NormalAlarmValue of TEXTUAL-CONVENTION
					FLAG=SUMMARY_LPM
					severity=minor
					alarmType=qualityOfServiceAlarm
					probableCause=thresholdCrossed"
		::= { pnSTDAlarmTrapItemVar 59 }

	alarmItemPnSTDTcn1dayTotalES OBJECT-TYPE
		SYNTAX		NormalAlarmValue
		ACCESS		read-only
		STATUS		mandatory
		DESCRIPTION	"TCN-ES-1day TOTAL
					TCN-ES-1day(DIR-A) TOTAL
					Refer to NormalAlarmValue of TEXTUAL-CONVENTION
					FLAG=SUMMARY_LPM
					severity=minor
					alarmType=qualityOfServiceAlarm
					probableCause=thresholdCrossed"
		::= { pnSTDAlarmTrapItemVar 60 }

	alarmItemPnSTDTcn1dayTotalSES OBJECT-TYPE
		SYNTAX		NormalAlarmValue
		ACCESS		read-only
		STATUS		mandatory
		DESCRIPTION	"TCN-SES-1day TOTAL
					TCN-SES-1day(DIR-A) TOTAL
					Refer to NormalAlarmValue of TEXTUAL-CONVENTION
					FLAG=SUMMARY_LPM
					severity=minor
					alarmType=qualityOfServiceAlarm
					probableCause=thresholdCrossed"
		::= { pnSTDAlarmTrapItemVar 61 }

	alarmItemPnSTDTcn1dayTotalBBE OBJECT-TYPE
		SYNTAX		NormalAlarmValue
		ACCESS		read-only
		STATUS		mandatory
		DESCRIPTION	"TCN-BBE-1day TOTAL
					TCN-BBE-1day(DIR-A) TOTAL
					Refer to NormalAlarmValue of TEXTUAL-CONVENTION
					FLAG=SUMMARY_LPM
					severity=minor
					alarmType=qualityOfServiceAlarm
					probableCause=thresholdCrossed"
		::= { pnSTDAlarmTrapItemVar 62 }

	alarmItemPnSTDTcn1dayTotalSEP OBJECT-TYPE
		SYNTAX		NormalAlarmValue
		ACCESS		read-only
		STATUS		mandatory
		DESCRIPTION	"TCN-SEP-1day TOTAL
					TCN-SEP-1day(DIR-A) TOTAL
					Refer to NormalAlarmValue of TEXTUAL-CONVENTION
					FLAG=SUMMARY_LPM
					severity=minor
					alarmType=qualityOfServiceAlarm
					probableCause=thresholdCrossed"
		::= { pnSTDAlarmTrapItemVar 63 }

	alarmItemPnSTDTcn1dayCHUAS OBJECT-TYPE
		SYNTAX		OCTET STRING (SIZE (1))
		ACCESS		read-only
		STATUS		mandatory
		DESCRIPTION	"This item is not used.
				TCN-UAS-1day CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnSTDAlarmTrapItemVar 65 }

	alarmItemPnSTDTcn1dayCHES OBJECT-TYPE
		SYNTAX		OCTET STRING (SIZE (1))
		ACCESS		read-only
		STATUS		mandatory
		DESCRIPTION	"This item is not used.
				TCN-ES-1day CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnSTDAlarmTrapItemVar 66 }

	alarmItemPnSTDTcn1dayCHSES OBJECT-TYPE
		SYNTAX		OCTET STRING (SIZE (1))
		ACCESS		read-only
		STATUS		mandatory
		DESCRIPTION	"This item is not used.
				TCN-SES-1day CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnSTDAlarmTrapItemVar 67 }

	alarmItemPnSTDTcn1dayCHBBE OBJECT-TYPE
		SYNTAX		OCTET STRING (SIZE (1))
		ACCESS		read-only
		STATUS		mandatory
		DESCRIPTION	"This item is not used.
				TCN-BBE-1day CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnSTDAlarmTrapItemVar 68 }

	alarmItemPnSTDTcn1dayCHSEP OBJECT-TYPE
		SYNTAX		OCTET STRING (SIZE (1))
		ACCESS		read-only
		STATUS		mandatory
		DESCRIPTION	"This item is not used.
				TCN-SEP-1day CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnSTDAlarmTrapItemVar 69 }

	alarmItemPnSTDTcnUAEDMRWork OBJECT-TYPE
		SYNTAX		NormalAlarmValue
		ACCESS		read-only
		STATUS		mandatory
		DESCRIPTION	"INTFC(1) Unavailable Event(DMR)
					Refer to NormalAlarmValue of TEXTUAL-CONVENTION
					FLAG=SUMMARY_LPM
					severity=minor
					alarmType=qualityOfServiceAlarm
					probableCause=thresholdCrossed"
		::= { pnSTDAlarmTrapItemVar 70 }

	alarmItemPnSTDTcnUAEDMRProt OBJECT-TYPE
		SYNTAX		NormalAlarmValue
		ACCESS		read-only
		STATUS		mandatory
		DESCRIPTION	"INTFC(2) Unavailable Event(DMR)
					Refer to NormalAlarmValue of TEXTUAL-CONVENTION
					FLAG=SUMMARY_LPM
					severity=minor
					alarmType=qualityOfServiceAlarm
					probableCause=thresholdCrossed"
		::= { pnSTDAlarmTrapItemVar 71 }

	alarmItemPnSTDTcnTCS15minRxLev OBJECT-TYPE
		SYNTAX		NormalAlarmValue
		ACCESS		read-only
		STATUS		mandatory
		DESCRIPTION	"TCN-RX LEV-15min
					Refer to NormalAlarmValue of TEXTUAL-CONVENTION
					FLAG=SUMMARY_LPM
					severity=minor
					alarmType=qualityOfServiceAlarm
					probableCause=thresholdCrossed"
		::= { pnSTDAlarmTrapItemVar 72 }

	alarmItemPnSTDTcnTCS1dayRxLev OBJECT-TYPE
		SYNTAX		NormalAlarmValue
		ACCESS		read-only
		STATUS		mandatory
		DESCRIPTION	"TCN-RX LEV-1day
					Refer to NormalAlarmValue of TEXTUAL-CONVENTION
					FLAG=SUMMARY_LPM
					severity=minor
					alarmType=qualityOfServiceAlarm
					probableCause=thresholdCrossed"
		::= { pnSTDAlarmTrapItemVar 73 }

	alarmItemPnSTDTRULORefAlarm OBJECT-TYPE
		SYNTAX		NormalAlarmValue
		ACCESS		read-only
		STATUS		mandatory
		DESCRIPTION	"LO REF
					Refer to NormalAlarmValue of TEXTUAL-CONVENTION
					FLAG=SUMMARY_TRU
					severity=minor
					alarmType=equipmentAlarm
					probableCause=equipmentMalfunction"
		::= { pnSTDAlarmTrapItemVar 74 }

	alarmItemPnSTDLofMUXWork OBJECT-TYPE
		SYNTAX		NormalAlarmValue
		ACCESS		read-only
		STATUS		mandatory
		DESCRIPTION	"STM-1(1) LOF(MUX)
					Refer to NormalAlarmValue of TEXTUAL-CONVENTION
					FLAG=SUMMARY_INTFC1
					severity=major
					alarmType=communicationAlarm
					probableCause=lossOfFrame"
		::= { pnSTDAlarmTrapItemVar 75 }

	alarmItemPnSTDLofDMRWork OBJECT-TYPE
		SYNTAX		NormalAlarmValue
		ACCESS		read-only
		STATUS		mandatory
		DESCRIPTION	"STM-1(1) LOF(DMR)
					Refer to NormalAlarmValue of TEXTUAL-CONVENTION
					FLAG=SUMMARY_INTFC1
					severity=major
					alarmType=communicationAlarm
					probableCause=lossOfFrame"
		::= { pnSTDAlarmTrapItemVar 76 }

	alarmItemPnSTDLosDMRProt OBJECT-TYPE
		SYNTAX		NormalAlarmValue
		ACCESS		read-only
		STATUS		mandatory
		DESCRIPTION	"STM-1(2) LOS(DMR)
					Refer to NormalAlarmValue of TEXTUAL-CONVENTION
					FLAG=SUMMARY_INTFC2
					severity=major
					alarmType=communicationAlarm
					probableCause=lossOfSignal"
		::= { pnSTDAlarmTrapItemVar 77 }

	alarmItemPnSTDLofMUXProt OBJECT-TYPE
		SYNTAX		NormalAlarmValue
		ACCESS		read-only
		STATUS		mandatory
		DESCRIPTION	"STM-1(2) LOF(MUX)
					Refer to NormalAlarmValue of TEXTUAL-CONVENTION
					FLAG=SUMMARY_INTFC2
					severity=major
					alarmType=communicationAlarm
					probableCause=lossOfFrame"
		::= { pnSTDAlarmTrapItemVar 78 }

	alarmItemPnSTDLofDMRProt OBJECT-TYPE
		SYNTAX		NormalAlarmValue
		ACCESS		read-only
		STATUS		mandatory
		DESCRIPTION	"STM-1(2) LOF(DMR)
					Refer to NormalAlarmValue of TEXTUAL-CONVENTION
					FLAG=SUMMARY_INTFC2
					severity=major
					alarmType=communicationAlarm
					probableCause=lossOfFrame"
		::= { pnSTDAlarmTrapItemVar 79 }

	alarmItemPnSTDStm1TFWorkAlarm OBJECT-TYPE
		SYNTAX		NormalAlarmValue
		ACCESS		read-only
		STATUS		mandatory
		DESCRIPTION	"INTFC(1) TF
					Refer to NormalAlarmValue of TEXTUAL-CONVENTION
					FLAG=SUMMARY_INTFC1
					severity=major
					alarmType=equipmentAlarm
					probableCause=equipmentMalfunction"
		::= { pnSTDAlarmTrapItemVar 80 }

	alarmItemPnSTDStm1TFProtAlarm OBJECT-TYPE
		SYNTAX		NormalAlarmValue
		ACCESS		read-only
		STATUS		mandatory
		DESCRIPTION	"INTFC(2) TF
					Refer to NormalAlarmValue of TEXTUAL-CONVENTION
					FLAG=SUMMARY_INTFC2
					severity=major
					alarmType=equipmentAlarm
					probableCause=equipmentMalfunction"
		::= { pnSTDAlarmTrapItemVar 81 }

	alarmItemPnSTDTcnUAEMUXWork OBJECT-TYPE
		SYNTAX		NormalAlarmValue
		ACCESS		read-only
		STATUS		mandatory
		DESCRIPTION	"STM-1(1) Unavailable Event(MUX)
					Refer to NormalAlarmValue of TEXTUAL-CONVENTION
					FLAG=SUMMARY_LPM
					severity=minor
					alarmType=qualityOfServiceAlarm
					probableCause=thresholdCrossed"
		::= { pnSTDAlarmTrapItemVar 82 }

	alarmItemPnSTDTcnUAEMUXProt OBJECT-TYPE
		SYNTAX		NormalAlarmValue
		ACCESS		read-only
		STATUS		mandatory
		DESCRIPTION	"STM-1(2) UAE(MUX)
					Refer to NormalAlarmValue of TEXTUAL-CONVENTION
					FLAG=SUMMARY_LPM
					severity=minor
					alarmType=qualityOfServiceAlarm
					probableCause=thresholdCrossed"
		::= { pnSTDAlarmTrapItemVar 83 }

	alarmItemPnSTDAuxClusterAlarm OBJECT-TYPE
		SYNTAX		NormalAlarmValue
		ACCESS		read-only
		STATUS		mandatory
		DESCRIPTION	"This item is not used.
				CLUSTERx ALARM
					(x : 1-4)
					Refer to NormalAlarmValue of TEXTUAL-CONVENTION
					FLAG=SUMMARY_AUX
					severity=major
					alarmType=equipmentAlarm
					probableCause=equipmentMalfunction"
		::= { pnSTDAlarmTrapItemVar 84 }

	alarmItemPnSTDLinearizerFail OBJECT-TYPE
		SYNTAX		NormalAlarmValue
		ACCESS		read-only
		STATUS		mandatory
		DESCRIPTION	"LINEARIZER
					Refer to NormalAlarmValue of TEXTUAL-CONVENTION
					FLAG=SUMMARY_MODEM
					severity=major
					alarmType=equipmentAlarm
					probableCause=equipmentMalfunction"
		::= { pnSTDAlarmTrapItemVar 85 }

	alarmItemPnSTDRouteID OBJECT-TYPE
		SYNTAX		NormalAlarmValue
		ACCESS		read-only
		STATUS		mandatory
		DESCRIPTION	"FRAME ID
					Refer to NormalAlarmValue of TEXTUAL-CONVENTION
					FLAG=SUMMARY_MODEM
					severity=major
					alarmType=communicationAlarm
					probableCause=equipmentMalfunction"
		::= { pnSTDAlarmTrapItemVar 86 }

	alarmItemPnSTDEarlyWarning OBJECT-TYPE
		SYNTAX		NormalAlarmValue
		ACCESS		read-only
		STATUS		mandatory
		DESCRIPTION	"EARLY WARNING
					Refer to NormalAlarmValue of TEXTUAL-CONVENTION
					FLAG=SUMMARY_MODEM
					severity=minor
					alarmType=qualityOfServiceAlarm
					probableCause=degradedSignal"
		::= { pnSTDAlarmTrapItemVar 87 }

	alarmItemPnSTDInputVoltage OBJECT-TYPE
		SYNTAX		NormalAlarmValue
		ACCESS		read-only
		STATUS		mandatory
		DESCRIPTION	"INPUT VOLTAGE
					Refer to NormalAlarmValue of TEXTUAL-CONVENTION
					FLAG=SUMMARY_MODEM
					severity=major
					alarmType=equipmentAlarm
					probableCause=powerProblem"
		::= { pnSTDAlarmTrapItemVar 88 }

	alarmItemPnSTDIntfcMTypeMismatch OBJECT-TYPE
		SYNTAX		NormalAlarmValue
		ACCESS		read-only
		STATUS		mandatory
		DESCRIPTION	"INTFC(1) TYPE MISMATCH
					Refer to NormalAlarmValue of TEXTUAL-CONVENTION
					FLAG=SUMMARY_INTFC1
					severity=major
					alarmType=equipmentAlarm
					probableCause=equipmentMalfunction"
		::= { pnSTDAlarmTrapItemVar 89 }

	alarmItemPnSTDIntfcSTypeMismatch OBJECT-TYPE
		SYNTAX		NormalAlarmValue
		ACCESS		read-only
		STATUS		mandatory
		DESCRIPTION	"INTFC(2) TYPE MISMATCH
					Refer to NormalAlarmValue of TEXTUAL-CONVENTION
					FLAG=SUMMARY_INTFC2
					severity=major
					alarmType=equipmentAlarm
					probableCause=equipmentMalfunction"
		::= { pnSTDAlarmTrapItemVar 90 }

	alarmItemPnSTDXpicModeMismatch OBJECT-TYPE
		SYNTAX		NormalAlarmValue
		ACCESS		read-only
		STATUS		mandatory
		DESCRIPTION	"XPIC MODE MISMATCH
					Refer to NormalAlarmValue of TEXTUAL-CONVENTION
					FLAG=SUMMARY_CTRL
					severity=major
					alarmType=equipmentAlarm
					probableCause=equipmentMalfunction"
		::= { pnSTDAlarmTrapItemVar 91 }

	alarmItemPnSTDXControlAlarm OBJECT-TYPE
		SYNTAX		NormalAlarmValue
		ACCESS		read-only
		STATUS		mandatory
		DESCRIPTION	"XPIC CTRL Alarm
					FLAG=SUMMARY_CTRL
					severity=major
					alarmType=equipmentAlarm
					probableCause=equipmentMalfunction"
		::= { pnSTDAlarmTrapItemVar 92 }

	alarmItemPnSTDGbELink OBJECT-TYPE
		SYNTAX		NormalAlarmValue
		ACCESS		read-only
		STATUS		mandatory
		DESCRIPTION	"GbE LAN Link Port
					FLAG=SUMMARY_INTFC1
					severity=major
					alarmType=communicationAlarm
					probableCause=lANError"
		::= { pnSTDAlarmTrapItemVar 93 }

	alarmItemPnSTDModemTypeMismatch OBJECT-TYPE
		SYNTAX		NormalAlarmValue
		ACCESS		read-only
		STATUS		mandatory
		DESCRIPTION	"Modem Type Mismatch
					FLAG=SUMMARY_MODEM
					severity=major
					alarmType=equipmentAlarm
					probableCause=equipmentMalfunction"
		::= { pnSTDAlarmTrapItemVar 94 }

	alarmItemPnSTDTRUTypeMismatch OBJECT-TYPE
		SYNTAX		NormalAlarmValue
		ACCESS		read-only
		STATUS		mandatory
		DESCRIPTION	"ODU Type Mismatch
					FLAG=SUMMARY_TRU
					severity=major
					alarmType=equipmentAlarm
					probableCause=equipmentMalfunction"
		::= { pnSTDAlarmTrapItemVar 95 }

        pnSTDEventTrapItemVar OBJECT IDENTIFIER
		::= { pnSTDTrapItemVar 3 }

	eventItemPnSTDConfigDataValid OBJECT-TYPE
		SYNTAX		INTEGER(0..1)
		ACCESS		read-only
		STATUS		mandatory
		DESCRIPTION	"EQUIPMENT CONFIG AVAILABILITY
					  0:Invalid,
					  1:Valid"
		::= { pnSTDEventTrapItemVar 1 }

	eventItemPnSTDConfigDataUp OBJECT-TYPE
		SYNTAX		INTEGER
		ACCESS		read-only
		STATUS		mandatory
		::= { pnSTDEventTrapItemVar 2 }

	eventItemPnSTDTxMuteStatus OBJECT-TYPE
		SYNTAX		OffOnValue
		ACCESS		read-only
		STATUS		mandatory
		DESCRIPTION	"MUTE STATUS
				Refer to OffOnValue of TEXTUAL-CONVENTION"
		::= { pnSTDEventTrapItemVar 3 }

	eventItemPnSTDTxSWStatus OBJECT-TYPE
		SYNTAX		INTEGER (0..2)
		ACCESS		read-only
		STATUS		mandatory
		DESCRIPTION	"TX SW STATUS
					  0:Invalid,
					  1:No.1,
					  2:No.2"
		::= { pnSTDEventTrapItemVar 4 }

	eventItemPnSTDRxSWStatus OBJECT-TYPE
		SYNTAX		INTEGER (0..2)
		ACCESS		read-only
		STATUS		mandatory
		DESCRIPTION	"RX SW STATUS
					  0:Invalid,
					  1:No.1,
					  2:No.2"
		::= { pnSTDEventTrapItemVar 5 }

	eventItemPnSTDXPICFuncStatus OBJECT-TYPE
		SYNTAX		INTEGER (0..2)
		ACCESS		read-only
		STATUS		mandatory
		DESCRIPTION	"XPIC STATUS
					  0:Invalid,
					  1:Normal,
					  2:Reset"
		::= { pnSTDEventTrapItemVar 6 }

	eventItemPnSTDLinearizerFunc OBJECT-TYPE
		SYNTAX		INTEGER (0..3)
		ACCESS		read-only
		STATUS		mandatory
		DESCRIPTION	"LINEARIZER FUNCTION
					  0:Invalid,
					  1:N/A,
					  2:Non Operation,
					  3:Operation"
		::= { pnSTDEventTrapItemVar 7 }

	eventItemPnSTDFadeDepthStatus OBJECT-TYPE
		SYNTAX		INTEGER (0..2)
		ACCESS		read-only
		STATUS		mandatory
		DESCRIPTION	"FADING STATUS
					  0:Invalid,
					  1:Normal,
					  2:Occurred"
		::= { pnSTDEventTrapItemVar 8 }

	eventItemPnSTDSTM1OutContWork OBJECT-TYPE
		SYNTAX		INTEGER (0..2)
		ACCESS		read-only
		STATUS		mandatory
		DESCRIPTION	"STM-1(1) OUTPUT CONTROL
					  0:Inavlid,
					  1:Normal,
					  2:Under Execution"
		::= { pnSTDEventTrapItemVar 9 }

	eventItemPnSTDAisGeneratedCH OBJECT-TYPE
		SYNTAX		OCTET STRING (SIZE (6))
		ACCESS		read-only
		STATUS		mandatory
		DESCRIPTION	"AIS GENERATED CHxx
					(xx : 1-48)
					  0:Normal,
					  1:Generated
					
					 [Bit Description]
					  Bit0 = CH01 (0: Normal,1: Alarm)
					  Bit1 = CH02
					  Bit2 = CH02
					  ...
					  Bit46 = CH47
					  Bit47 = CH48"
		::= { pnSTDEventTrapItemVar 10 }

	eventItemPnSTDAisReceivedCH OBJECT-TYPE
		SYNTAX		OCTET STRING (SIZE (6))
		ACCESS		read-only
		STATUS		mandatory
		DESCRIPTION	"AIS RECEIVED CHxx
					(xx : 1-48)
					  0:Normal,
					  1:Received
					
					 [Bit Description]
					  Bit0 = CH01 (0: Normal,1: Alarm)
					  Bit1 = CH02
					  Bit2 = CH02
					  ...
					  Bit46 = CH47
					  Bit47 = CH48"
		::= { pnSTDEventTrapItemVar 11 }

	eventItemPnSTDLinkLossForward OBJECT-TYPE
		SYNTAX		INTEGER (0..2)
		ACCESS		read-only
		STATUS		mandatory
		DESCRIPTION	"LINK LOSS FORWARDING PORTx
					(x : 1-4)
					  0:Invalid,
					  1:Normal,
					  2:Under Execution"
		::= { pnSTDEventTrapItemVar 12 }

	eventItemPnSTDSpeedDuplex OBJECT-TYPE
		SYNTAX		INTEGER (0..8)
		ACCESS		read-only
		STATUS		mandatory
		DESCRIPTION	"SPEED & DUPLEX PORTx
					(x : 1-4)
					  0:INVALID,
					  1:10M-HALF(MDI),
					  2:10M-FULL(MDI),
					  3:100M-HALF(MDI),
					  4:100M-FULL(MDI),
					  5:10M-HALF(MDIX),
					  6:10M-FULL(MDIX),
					  7:100M-HALF(MDIX),
					  8:100M-FULL(MDIX)"
		::= { pnSTDEventTrapItemVar 13 }

	eventItemPnSTDInphaseWork OBJECT-TYPE
		SYNTAX		INTEGER (0..2)
		ACCESS		read-only
		STATUS		mandatory
		DESCRIPTION	"INTFC(1) INPHASE
					  0:Invalid,
					  1:Out Phase,
					  2:In Phase"
		::= { pnSTDEventTrapItemVar 14 }

	eventItemPnSTDSTM1OutContProt OBJECT-TYPE
		SYNTAX		INTEGER (0..2)
		ACCESS		read-only
		STATUS		mandatory
		DESCRIPTION	"STM-1(2) OUTPUT CONTROL
					  0:Invalid,
					  1:Normal,
					  2:Under Execution"
		::= { pnSTDEventTrapItemVar 15 }

	eventItemPnSTDInphaseProt OBJECT-TYPE
		SYNTAX		INTEGER (0..2)
		ACCESS		read-only
		STATUS		mandatory
		DESCRIPTION	"INTFC(2) INPHASE
					  0:Invalid,
					  1:Out Phase,
					  2:In Phase"
		::= { pnSTDEventTrapItemVar 16 }

	eventItemPnSTDWSAisGeneratedCH OBJECT-TYPE
		SYNTAX		INTEGER (0..2)
		ACCESS		read-only
		STATUS		mandatory
		DESCRIPTION	"WS AIS GENERATED
					  0:Invalid,
					  1:Normal,
					  2:Generated"
		::= { pnSTDEventTrapItemVar 17 }

	eventItemPnSTDWSAisReceivedCH OBJECT-TYPE
		SYNTAX		INTEGER (0..2)
		ACCESS		read-only
		STATUS		mandatory
		DESCRIPTION	"WS AIS RECEIVED
					  0:Invalid,
					  1:Normal,
					  2:Received"
		::= { pnSTDEventTrapItemVar 18 }

	eventItemPnSTDSCLanLinkLossForward OBJECT-TYPE
		SYNTAX		INTEGER (0..2)
		ACCESS		read-only
		STATUS		mandatory
		DESCRIPTION	"INTFC(2) LINK LOSS FORWARDINGx
					(x : 1-2)
					  0:Invalid,
					  1:Normal,
					  2:Under Execution"
		::= { pnSTDEventTrapItemVar 19 }

	eventItemPnSTDSCLanSpeedDuplex OBJECT-TYPE
		SYNTAX		INTEGER (0..8)
		ACCESS		read-only
		STATUS		mandatory
		DESCRIPTION	"INTFC(2) SPEED & DUPLEX PORTx
					(x : 1-2)
					  0:INVALID,
					  1:10M-HALF(MDI),
					  2:10M-FULL(MDI),
					  3:100M-HALF(MDI),
					  4:100M-FULL(MDI),
					  5:10M-HALF(MDIX),
					  6:10M-FULL(MDIX),
					  7:100M-HALF(MDIX),
					  8:100M-FULL(MDIX)"
		::= { pnSTDEventTrapItemVar 20 }

	eventItemPnSTDCHUsage OBJECT-TYPE
		SYNTAX		OCTET STRING (SIZE (48))
		ACCESS		read-only
		STATUS		mandatory
		DESCRIPTION	"CH USAGE(CHxx)
					xx=1-48
					  0:Invalid,
					  1:Not Used,
					  2:Used(E1),
					  3:Used(LAN)
					
					  [Description]
					    Byte 0 = CH01(0:Invalid, 1:Not Used, 2:Used(E1), 3:Used(LAN))
					    Byte 1 = CH02
					    ...
					    Byte 46 = CH47
					    Byte 47 = CH48"
		::= { pnSTDEventTrapItemVar 21 }

	eventItemPnSTDCHCondition OBJECT-TYPE
		SYNTAX		OCTET STRING (SIZE (48))
		ACCESS		read-only
		STATUS		mandatory
		DESCRIPTION	"CH USAGE ERROR REPORT
					  0:Invalid, 
					  1:Disabled(Report),
					  2:Enabled(Not Report)
					
				 AIS Activation Condition
					  0:Invalid, 
					  1:LOF+HIGH BER,
					  2:LOF
					 
				 AIS ACTIVATION DELAY
					  0:Invalid,
					  1:Off,
					  2:On

				 AIS GENERATED REPORT
					  0:Invalid, 
					  1:Not Report, 
					  2:Report

				 AIS RECEIVED REPORT
					  0:Invalid, 
					  1:Not Report, 
					  2:Report

				 AIS RECEIVED CONDITION
					  0:Invalid, 
					  1:Alarm, 
					  2:Status
				
					  [Description]
					    Byte 0 = CH01(0:Invalid, 1:Disabled, 2:Enabled)
					    Byte 1 = CH02
					    ...
					    Byte 46 = CH47
					    Byte 47 = CH48"
		::= { pnSTDEventTrapItemVar 22 }

	eventItemPnSTDCHImpedance OBJECT-TYPE
		SYNTAX		OCTET STRING (SIZE (10))
		ACCESS		read-only
		STATUS		mandatory
		DESCRIPTION	"E1 PORT IMPEDANCE
					  0:Invalid,
					  1:120[ohm],
					  2:75[ohm]
					
					  [Description]
					    BYTE0 = E1 PORT IMPEDANCE(CH1) (0:Invalid, 1:120[ohm], 2:75[ohm])
					    BYTE1 = E1 PORT IMPEDANCE(CH2)
					    BYTE2 = E1 PORT IMPEDANCE(CH3)
					    BYTE3 = E1 PORT IMPEDANCE(CH4)
					    BYTE4 = E1 PORT IMPEDANCE(CH5-8)
					    BYTE5 = E1 PORT IMPEDANCE(CH9-16)
					    BYTE6 = E1 PORT IMPEDANCE(CH17-24)
					    BYTE7 = E1 PORT IMPEDANCE(CH25-32)
					    BYTE8 = E1 PORT IMPEDANCE(CH33-40)
					    BYTE9 = E1 PORT IMPEDANCE(CH41-48)
					"
		::= { pnSTDEventTrapItemVar 23 }

	eventItemPnSTDMSAisGeneration OBJECT-TYPE
		SYNTAX		INTEGER (0..2)
		ACCESS		read-only
		STATUS		mandatory
		DESCRIPTION	"MS-AIS GENERATION
					  0:Invalid,
					  1:Disabled,
					  2:Enabled"
		::= { pnSTDEventTrapItemVar 24 }

	eventItemPnSTDDxcFunction OBJECT-TYPE
		SYNTAX		INTEGER (0..2)
		ACCESS		read-only
		STATUS		mandatory
		DESCRIPTION	"DXC FUNCTION
					  0:Invalid,
					  1:Unavailable,
					  2:Available"
		::= { pnSTDEventTrapItemVar 25 }

	eventItemPnSTDDxcCHSetting OBJECT-TYPE
		SYNTAX		OCTET STRING (SIZE (156))
		ACCESS		read-only
		STATUS		mandatory
		DESCRIPTION	"DXC CH Setting

					  [Description]
					    Byte 0 = CH01
					    ...
					    Byte 47 = CH48
					    Byte 52 = DIR-A CH01 Setting
					    ...
					    Byte 99 = DIR-A CH48 Setting
					    Byte 104 = DIR-B CH01 Setting
					    ...
					    Byte 151 = DIR-B CH48 Setting

					    Bit 0-5 (000000=Invalid, 000001=CH1,...,110000=CH48)
					    Bit 6-7 (00=LINE,01=DIR-A,10=DIR-B,11=LAN)"
		::= { pnSTDEventTrapItemVar 26 }

	eventItemPnSTDDxcAssign OBJECT-TYPE
		SYNTAX		OCTET STRING (SIZE (48))
		ACCESS		read-only
		STATUS		mandatory
		DESCRIPTION	"This item is not used.
				 DXC ASSIGNMENT CHANGED
					  0:INVALID,
					  1:PORT1,
					  2:PORT2,
					  ...
					  47:PORT47,
					  48:PORT48
					
					  [Description]
					    Byte 0 = CH01 (0:Invalid, X:Port X,  x=1~48)
					    Byte 1 = CH02
					    ...
					    Byte 46 = CH47
					    Byte 47 = CH48"
		::= { pnSTDEventTrapItemVar 27 }

	eventItemPnSTDBERThreshold OBJECT-TYPE
		SYNTAX		OCTET STRING (SIZE (8))
		ACCESS		read-only
		STATUS		mandatory
		DESCRIPTION	"BER THRESHOLD SETTING
					  [Description]
					    Byte 0 = HIGH BER THRESHOLD/HIGH BER THRESHOLD(DIR-A)  
					                (0:INVALID, 1:1E-3, 2:1E-4, 3:1E-5)
					    Byte 1 = HIGH BER THRESHOLD(DIR-B) 
					                (0:INVALID, 1:1E-3, 2:1E-4, 3:1E-5)
					    Byte 2 = LOW BER THRESHOLD/LOW BER THRESHOLD(DIR-A) 
					                (0:INVALID, 1:1E-6, 2:1E-7, 3:1E-8, 4:1E-9)
					    Byte 3 = LOW BER THRESHOLD(DIR-B) 
					                (0:INVALID, 1:1E-6, 2:1E-7, 3:1E-8, 4:1E-9)
					    Byte 4 = E-BER(DMR)
					                (0:INVALID, 1:1E-3, 2:1E-4, 3:1E-5)
					    Byte 5 = SD(DMR)
					                (0:INVALID, 1:1E-6, 2:1E-7, 3:1E-8, 4:1E-9)
					    Byte 6 = E-BER(MUX)
					                 (0:INVALID, 1:1E-3, 2:1E-4, 3:1E-5)
					    Byte 7 = SD(MUX)
					                (0:INVALID, 1:1E-6, 2:1E-7, 3:1E-8, 4:1E-9)"
		::= { pnSTDEventTrapItemVar 28 }

	eventItemPnSTDSubIntfc OBJECT-TYPE
		SYNTAX		OCTET STRING (SIZE (4))
		ACCESS		read-only
		STATUS		mandatory
		DESCRIPTION	"SUB INTFC
					  0:INVALID
					  1:NOT USED
					  2:E1 WAYSIDE+SC LAN(SC)
					  3:E1 WAYSIDE
					  4:SC LAN(WAYSIDE)
					  5:SC LAN(SC)
				SUB INTFC is available in SDH system."
		::= { pnSTDEventTrapItemVar 29 }

	eventItemPnSTDSCAssign OBJECT-TYPE
		SYNTAX		OCTET STRING (SIZE (8))
		ACCESS		read-only
		STATUS		mandatory
		DESCRIPTION	"SC ASSIGNMENT
					  [Description]
					    Byte 0 = RS-232C-1
					         (0:INVALID, 1:NOT USED, 2:SC1, 3:SC2,
					          4:SC3, 5:SC4, 16:E1(MUX), 17:F1(MUX),
					          19:E1(DMR), 20:F1(DMR))
					    Byte 1 = RS-232C-2
					         (0:INVALID, 1:NOT USED, 2:SC1, 3:SC2,
					          4:SC3, 5:SC4, 16:E1(MUX), 17:F1(MUX),
					          19:E1(DMR), 20:F1(DMR))
					    Byte 2 = V11-1
					         (0:INVALID, 1:NOT USED, 2:SC1, 3:SC2, 
					          4:SC3, 5:SC4, 16:E1(MUX), 17:F1(MUX), 
					          18:DCCr(MUX), 19:E1(DMR), 20:F1(DMR), 
					          21:DCCr(DMR))
					    Byte 3 = V11-2
					         (0:INVALID, 1:NOT USED, 2:SC1, 3:SC2, 
					          4:SC3, 5:SC4, 16:E1(MUX), 17:F1(MUX), 
					          18:DCCr(MUX), 19:E1(DMR), 20:F1(DMR), 
					          21:DCCr(DMR))
					    Byte 4 = SC LAN1
					         (0:INVALID, 1:NOT USED, 2:SC1, 10:SC1-2,
					          14:SC1-4, 16:E1(MUX), 17:F1(MUX), 18:DCCr(MUX),
					          19:E1(DMR), 20:F1(DMR), 21:DCCr(DMR))
					    Byte 5 = SC LAN2
					         (0:INVALID, 1:NOT USED, 2:SC1, 10:SC1-2,
					          14:SC1-4, 16:E1(MUX), 17:F1(MUX), 18:DCCr(MUX),
					          19:E1(DMR), 20:F1(DMR), 21:DCCr(DMR))
					    Byte 6 = V11-1 DIRECTION SETTING
					         (0:INVALID, 1:CO-DIRECTIONAL, 2:CONTRA-DIRECTIONAL)
					    Byte 7 = V11-2 DIRECTION SETTING
					         (0:INVALID, 1:CO-DIRECTIONAL, 2:CONTRA-DIRECTIONAL)
					"
		::= { pnSTDEventTrapItemVar 30 }

	eventItemPnSTDLanPortSetting OBJECT-TYPE
		SYNTAX		OCTET STRING (SIZE (41))
		ACCESS		read-only
		STATUS		mandatory
		DESCRIPTION	"LAN PORT SETTING
					  [Description]
					  Byte 0 = SWITCHING FUNCTION
					       (0:INVALID, 1:DISABLED(Report), 2:ENABLED(Not Report))
					
					  Byte 1 = SPEED & DUPLEX PORT1
					  Byte 2 = SPEED & DUPLEX PORT2
					  Byte 3 = SPEED & DUPLEX PORT3
					  Byte 4 = SPEED & DUPLEX PORT4
					  Byte 5 = INTFC(2) SPEED & DUPLEX PORT1
					  Byte 6 = INTFC(2) SPEED & DUPLEX PORT2
					       (0:INVALID, 1:AUTONEG(AUTO-MDI/MDIX),
					        2:10M-HALF(MDI), 3:10M-FULL(MDI), 
					        4:100M-HALF(MDI), 5:100M-FULL(MDI), 
					        6:10M-HALF(MDIX), 7:10M-FULL(MDIX), 
					        8:100M-HALF(MDIX), 9:100M-FULL(MDIX))
					
					  Byte 7 = FLOW CONTROL PORT1
					  Byte 8 = FLOW CONTROL PORT2
					  Byte 9 = FLOW CONTROL PORT3
					  Byte 10 = FLOW CONTROL PORT4
					  Byte 11 = INTFC(2) FLOW CONTROL PORT1
					  Byte 12 = INTFC(2) FLOW CONTROL PORT2
					       (0:INVALID, 1:OFF, 2:ON)
					
					  Byte 13 = COLLISION REPORT PORT1
					  Byte 14 = COLLISION REPORT PORT2
					  Byte 15 = COLLISION REPORT PORT3
					  Byte 16 = COLLISION REPORT PORT4
					  Byte 17 = INTFC(2) COLLISION REPORT PORT1
					  Byte 18 = INTFC(2) COLLISION REPORT PORT2
					       (0:INVALID, 1:DISABLED, 2:ENABLED)
					
					  Byte 19 = LINK LOSS FORWARDING PORT1
					  Byte 20 = LINK LOSS FORWARDING PORT2
					  Byte 21 = LINK LOSS FORWARDING PORT3
					  Byte 22 = LINK LOSS FORWARDING PORT4
					  Byte 23 = INTFC(2) LINK LOSS FWD PORT1
					  Byte 24 = INTFC(2) LINK LOSS FWD PORT2
					       (0:INVALID, 1:DISABLED, 2:ENABLED)
					
					  Byte 25 = LOCK SOURCE SETTING
					       (0:INVALID, 1:INTERNAL CLOCK, 
					        2:DMR -> INTERNAL CLOCK)
					
					  Byte 26 = 2M FRAMING PORT1
					  Byte 27 = 2M FRAMING PORT2
					  Byte 28 = 2M FRAMING PORT3
					  Byte 29 = 2M FRAMING PORT4
					       (0:INVALID, 1:UNFRAMED,2:PCM31C(FAS+CRC)
						3:PCM31(FAS),4:PCM30C(MFAS+CRC)
						5:PCM30(MFAS))
					
					  Byte 30 = PORT1 USAGE
					  Byte 31 = PORT2 USAGE
					  Byte 32 = PORT3 USAGE
					  Byte 33 = PORT4 USAGE
					  Byte 34 = INTFC(2) PORT1 USAGE
					  Byte 35 = INTFC(2) PORT2 USAGE
					       (0:INVALID, 1:NOT USED, 2:USED)
					  Byte 36 = SUB SWITCHING FUNCTION
						(0:INVALID, 1:DISABLED, 2:ENABLED)
					  Byte 37 = MEDIA TYPE
						(0:INVALID, 1:SFP, 2:RJ-45)
					  Byte 38 = GbE SPEED & DUPLEX
						(0:INVALID, 
						 1:RESERVE1, 
						 2:AUTONEG(AUTO 1000MB FULL DUPLEX), 
						 3:AUTONEG(AUTO MDI/MDIX), 
						 4:RESERVE4, 
						 5:RESERVE5, 
						 6:100MB-FULL(MDI), 
						 7:100MB-FULL(MDIX), 
						 8:100MB-HALF(MDI), 
						 9:100MB-HALF(MDIX), 
						 10:10MB-FULL(MDI), 
						 11:10MB-FULL(MDIX), 
						 12:10MB-HALF(MDI), 
						 13:10MB-HALF(MDIX))
					  Byte 39 = GbE LINK LOSS FORWARDING
						(0:INVALID, 1:DISABLED, 2:ENABLED)
					  Byte 40 = GbE FLOW CONTROL(0:INVALID, 1:OFF, 2:ON)"
		::= { pnSTDEventTrapItemVar 31 }

	eventItemPnSTDAlsFunction OBJECT-TYPE
		SYNTAX		OCTET STRING (SIZE (2))
		ACCESS		read-only
		STATUS		mandatory
		DESCRIPTION	"ALS
				   [Description]
					Byte0 = ALS FUNCTION
					   0:Invalid,
					   1:Disabled,
					   2:Enabled
					 Byte1 = ALS INTERVAL
					   0:Invalid,
					   1:60sec,
					   2:180sec,
					   3:300sec
				This function is available in Optical Interface."
		::= { pnSTDEventTrapItemVar 32 }

	eventItemPnSTDTxPowerContValue OBJECT-TYPE
		SYNTAX		OCTET STRING (SIZE (9))
		ACCESS		read-only
		STATUS		mandatory
		DESCRIPTION	"TX POWER CTRL
					  [Description]
					  Byte 0 = MTPC TX POWER 
					      (0 - 255)
					  Byte 1 = ATPC THRESHOLD LEVEL integral number(signed char) 
					      (-128 - 127)
					  Byte 2 = ATPC THRESHOLD LEVEL a place of decimal
					      (0 - 9) 
					  Byte 3 = ADDITIONAL ATT 
					      (0 - 255)
					  Byte 4 = ATPC(MAX)
					      (0 - 255)
					  Byte 5 = ATPC(MIN)
					      (0 - 255)
					  Byte 6 = HYSTERESIS
					      (0 - 255)
					  Byte 7 = ATPC POWER MODE
					      (0:INVALID, 1:HOLD, 2:MAX, 3:MIN)
					  Byte 8 = ODU COMM ALARM MODE
					      (0:INVALID, 1:HOLD, 2:MUTE)"
		::= { pnSTDEventTrapItemVar 33 }

	eventItemPnSTDAtpcPowerMode OBJECT-TYPE
		SYNTAX		INTEGER (0..3)
		ACCESS		read-only
		STATUS		mandatory
		DESCRIPTION	"ATPC POWER MODE
					  0:Invalid,
					  1:Hold,
					  2:MAX,
					  3:MIN
				Number 2 is not used."
		::= { pnSTDEventTrapItemVar 34 }

	eventItemPnSTDCommAlarmMode OBJECT-TYPE
		SYNTAX		INTEGER (0..2)
		ACCESS		read-only
		STATUS		mandatory
		DESCRIPTION	"This item is not used.
				ODU COMM ALARM MODE
					  0:Invalid,
					  1:Hold,
					  2:Mute"
		::= { pnSTDEventTrapItemVar 35 }

	eventItemPnSTDSWCondTxRx OBJECT-TYPE
		SYNTAX		OCTET STRING (SIZE (5))
		ACCESS		read-only
		STATUS		mandatory
		DESCRIPTION	"CONDITION
					for TX/RX SW 
					  
					  [Description]
					  Byte 0 = TX SW PRIORITY
					      (0:INVALID, 1:NON PRIORITY, 2:PRIORITY No.1)
					  Byte 1 = RX SW PRIORITY
					      (0:INVALID, 1:NON PRIORITY, 2:PRIORITY No.1)
					  Byte 2 = RX SW MAINTENANCE MODE
					      (0:INVALID, 1:MANUAL, 2:FORCED)
					  Byte 3 = RX SW CONDITION-EARLY WARNING
					      (0:INVALID, 1:INCLUDED EW, 2:EXCLUDED EW)
					  Byte 4 = RX SW CONDITION-XPIC RESET
					      (0:INVALID, 1:INCLUDED CROSS RESET, 2:EXCLUDED CROSS RESET)"
		::= { pnSTDEventTrapItemVar 36 }

	eventItemPnSTDSWCondAPS OBJECT-TYPE
		SYNTAX		OCTET STRING (SIZE (7))
		ACCESS		read-only
		STATUS		mandatory
		DESCRIPTION	"
					CONDITION
					for APS
					
					  [Description]
					  Byte 0 = APS ALARM PRIORITY 
					      (0:INVALID, 1:AUTO, 2:FORCED)
					  Byte 1 = APS CONDITION-SF
					      (0:INVALID, 1:PRIORITY HIGH, 2:PRIORITY LOW)
					  Byte 2 = APS CONDITION-SD
					      (0:INVALID, 1:INCLUDED SD, 2:EXCLUDED SD)
					  Byte 3 = LOCK IN USAGE (0:INVALID, 1:NOT USED, 2:USED)
					  Byte 4 = LOCK IN COUNT (VALUE(INT 0-255))
					  Byte 5 = LOCK IN DETECT TIM (VALUE(INT 0-60))
					  Byte 6 = LOCK IN HOLD TIME (VALUE(INT 0-48))"
		::= { pnSTDEventTrapItemVar 37 }

	eventItemPnSTDRelayConfigData OBJECT-TYPE
		SYNTAX		OCTET STRING (SIZE (48))
		ACCESS		read-only
		STATUS		mandatory
		DESCRIPTION	"RELAY CONFIGURATION CHANGED
					  [Description]
					  (Relay x (x:1~6))
					   [START BIT] = 64 * (x - 1)
					
					    Bit (0 + [START BIT]) = MAINT (Remark1)
					    Bit (1 + [START BIT]) = PS ALARM1 (Remark2)
					    Bit (2 + [START BIT]) = PS ALARM2 (Remark2)
					    Bit (3 + [START BIT]) = (FIXED to 0)
					    Bit (4 + [START BIT]) = (FIXED to 0)
					    Bit (5 + [START BIT]) = (FIXED to 0)
					    Bit (6 + [START BIT]) = (FIXED to 0)
					    Bit (7 + [START BIT]) = CPU ALARM (Remark2)
					    Bit (8 + [START BIT]) = ODU ALARM1 (Remark7)
					    Bit (9 + [START BIT]) = ODU ALARM2 (Remark7)
					    Bit (10 + [START BIT]) = IDU ALARM (Remark7)
					    Bit (11 + [START BIT]) = (FIXED to 0)
					    Bit (12 + [START BIT]) = (FIXED to 0)
					    Bit (13 + [START BIT]) = (FIXED to 0)
					    Bit (14 + [START BIT]) = (FIXED to 0)
					    Bit (15 + [START BIT]) = (FIXED to 0)
					    Bit (16 + [START BIT]) = TX POWER ALARM1 (Remark7)
					    Bit (17 + [START BIT]) = TX POWER ALARM2 (Remark7)
					    Bit (18 + [START BIT]) = TX IN LEV ALARM1 (Remark7)
					    Bit (19 + [START BIT]) = TX IN LEV ALARM2 (Remark7)
					    Bit (20 + [START BIT]) = RX LEV ALARM1 (Remark7)
					    Bit (21 + [START BIT]) = RX LEV ALARM2 (Remark7)
					    Bit (22 + [START BIT]) = APC ALARM1 (Remark7)
					    Bit (23 + [START BIT]) = APC ALARM2 (Remark7)
					    Bit (24 + [START BIT]) = IF CABLE SHORT ALARM1 (Remark7)
					    Bit (25 + [START BIT]) = IF CABLE SHORT ALARM2 (Remark7)
					    Bit (26 + [START BIT]) = ODU CPU ALARM1 (Remark7)
					    Bit (27 + [START BIT]) = ODU CPU ALARM2 (Remark7)
					    Bit (28 + [START BIT]) = (FIXED to 0)
					    Bit (29 + [START BIT]) = (FIXED to 0)
					    Bit (30 + [START BIT]) = (FIXED to 0)
					    Bit (31 + [START BIT]) = (FIXED to 0)
					    Bit (32 + [START BIT]) = MOD ALARM1 (Remark7)
					    Bit (33 + [START BIT]) = MOD ALARM2 (Remark7)
					    Bit (34 + [START BIT]) = DEM ALARM1 (Remark7)
					    Bit (35 + [START BIT]) = DEM ALARM2 (Remark7)
					    Bit (36 + [START BIT]) = CH INPUT LOSS (Remark7)
					    Bit (37 + [START BIT]) = CH AIS RECEIVED (Remark7)
					    Bit (38 + [START BIT]) = CH AIS GENERATED (Remark7)
					    Bit (39 + [START BIT]) = CH USAGE ERROR (Remark7)
					    Bit (40 + [START BIT]) = LOW BER ALARM1 (Remark7)
					    Bit (41 + [START BIT]) = LOW BER ALARM2 (Remark7)
					    Bit (42 + [START BIT]) = HIGH BER ALARM1 (Remark7)
					    Bit (43 + [START BIT]) = HIGH BER ALARM2 (Remark7)
					    Bit (44 + [START BIT]) = STM-1 TF ALARM (Remark7)
					    Bit (45 + [START BIT]) = STM-1 SLOS (Remark7)
					    Bit (46 + [START BIT]) = STM-1 RLOS (Remark7)
					    Bit (47 + [START BIT]) = LAN LINK ALARM (Remark7)
					    Bit (48 + [START BIT]) = LOF1 (Remark7)
					    Bit (49 + [START BIT]) = LOF2 (Remark7)
					    Bit (50 + [START BIT]) = X REF ALARM1 (Remark7)
					    Bit (51 + [START BIT]) = X REF ALARM2 (Remark7)
					    Bit (52 + [START BIT]) = X CTRL ALARM1 (Remark7)
					    Bit (53 + [START BIT]) = X CTRL ALARM2 (Remark7)
					    Bit (54 + [START BIT]) = SC LAN LINK ALARM (Remark7)
					    Bit (55 + [START BIT]) = WS INPUT LOSS (Remark7)
					    Bit (56 + [START BIT]) = CLUSTER ALARM1 (Remark6)
					    Bit (57 + [START BIT]) = CLUSTER ALARM2 (Remark5)
					    Bit (58 + [START BIT]) = CLUSTER ALARM3 (Remark4)
					    Bit (59 + [START BIT]) = CLUSTER ALARM4 (Remark3)
					    Bit (60 + [START BIT]) = HK1 OUTPUT (Remark6)
					    Bit (61 + [START BIT]) = HK2 OUTPUT (Remark5)
					    Bit (62 + [START BIT]) = HK3 OUTPUT (Remark4)
					    Bit (63 + [START BIT]) = HK4 OUTPUT (Remark3)
					
					  Remark1 : The value of Relay 1 is fixed to  1. 
					            The value of the other Relay is fixed to 0.
					  Remark2 : The value of Relay 3 is fixed to 1. 
					            The value of the other Relay is fixed to 0.
					  Remark3 : The value of Relay 3 is fixed to 1. 
					            The value of the other Relay is fixed to 0.
					  Remark4 : The value of Relay 4 is fixed to 1. 
					            The value of the other Relay is fixed to 0.
					  Remark5 : The value of Relay 5 is fixed to 1. 
					            The value of the other Relay is fixed to 0.
					  Remark6 : The value of Relay 6 is fixed to 1. 
					            The value of the other Relay is fixed to 0.
					  Remark7 : The value of Relay 1 and Relay 2 is fixed to 0. 
					            The value of the other Relay is 0 and 1.
					"
		::= { pnSTDEventTrapItemVar 38 }

	eventItemPnSTDRelayClusterAssign OBJECT-TYPE
		SYNTAX		OCTET STRING (SIZE (4))
		ACCESS		read-only
		STATUS		mandatory
		DESCRIPTION	"CLUSTER INPUT
					  0:Invalid,
					  1:Disabled,
					  2:Enabled)
					
					  [Description]
					  Byte 0 = CLUSTER1 INPUT (0:Invalid, 1:Disabled, 2:Enabled)
					  Byte 1 = CLUSTER2 INPUT
					  Byte 2 = CLUSTER3 INPUT
					  Byte 3 = CLUSTER4 INPUT"
		::= { pnSTDEventTrapItemVar 39 }

	eventItemPnSTDTCNTreshold15minTotal OBJECT-TYPE
		SYNTAX		OCTET STRING (SIZE (24))
		ACCESS		read-only
		STATUS		mandatory
		DESCRIPTION	"TCN THRESHOLD 15MIN TOTAL
					  [Description]
					  (Byte 0 - Byte 3)   = OFS TCN THRESHOLD TOTAL-15min (0 - 900)
					  (Byte 4 - Byte 7)   = UAS TCN THRESHOLD TOTAL-15min (0 - 900)
					  (Byte 8 - Byte 11)  = ES TCN THRESHOLD TOTAL-15min  (0 - 900)
					  (Byte 12 - Byte 15) = SES TCN THRESHOLD TOTAL-15min (0 - 900)
					  (Byte 16 - Byte 19) = BBE TCN THRESHOLD TOTAL-15min 
					                       (PDH(Bit Rate = 10MB)  : 0 - 804600   
					                        PDH(Bit Rate = 20MB)  : 0 - 804600
					                        PDH(Bit Rate = 40MB)  : 0 - 804600
					                        PDH(Bit Rate = 80MB)  : 0 - 1611000
					                        PDH(Bit Rate = 100MB) : 0 - 1611000
					                        SDH(Bit Rate = 156MB) : 0 - 2159100)
					  (Byte 20 - Byte 23) = SEP TCN THRESHOLD TOTAL-15min (0 - 900)
"
		::= { pnSTDEventTrapItemVar 40 }

	eventItemPnSTDTCNTreshold15minCH OBJECT-TYPE
		SYNTAX		OCTET STRING (SIZE (24))
		ACCESS		read-only
		STATUS		mandatory
		DESCRIPTION	"This item is not used.
				  TCN THRESHOLD 15MIN CH
				  This item is available in PDH system.
					  [Description]
					  (Byte 0 - Byte 3)   = (Fixed to 0)
					  (Byte 4 - Byte 7)   = UAS TCN THRESHOLD TOTAL-15min (0 - 900)
					  (Byte 8 - Byte 11)  = ES TCN THRESHOLD TOTAL-15min  (0 - 900)
					  (Byte 12 - Byte 15) = SES TCN THRESHOLD TOTAL-15min (0 - 900)
					  (Byte 16 - Byte 19) = BBE TCN THRESHOLD TOTAL-15min (0 - 402300)
					  (Byte 20 - Byte 23) = SEP TCN THRESHOLD TOTAL-15min (0 - 900)
"
		::= { pnSTDEventTrapItemVar 41 }

	eventItemPnSTDTCNTreshold1dayTotal OBJECT-TYPE
		SYNTAX		OCTET STRING (SIZE (24))
		ACCESS		read-only
		STATUS		mandatory
		DESCRIPTION	"TCN THRESHOLD 1DAY TOTAL
					  [Description]
					  (Byte 0 - Byte 3) = OFS TCN THRESHOLD TOTAL-1day (0 - 86400)
					  (Byte 4 - Byte 7) = UAS TCN THRESHOLD TOTAL-1day (0 - 86400)
					  (Byte 8 - Byte 11) = ES TCN THRESHOLD TOTAL-1day (0 - 86400)
					  (Byte 12 - Byte 15) = SES TCN THRESHOLD TOTAL-1day (0 - 86400)
					  (Byte 16 - Byte 19) = BBE TCN THRESHOLD TOTAL-1day 
					                       (PDH(Bit Rate = 10MB)  : 0 - 77241600
					                        PDH(Bit Rate = 20MB)  : 0 - 77241600
					                        PDH(Bit Rate = 40MB)  : 0 - 77241600
					                        PDH(Bit Rate = 80MB)  : 0 - 154656000
					                        PDH(Bit Rate = 100MB) : 0 - 154656000
					                        SDH(Bit Rate = 156MB) : 0 - 207273600)
					  (Byte 20 - Byte 23) = SEP TCN THRESHOLD TOTAL-1day (0 - 86400)
"
		::= { pnSTDEventTrapItemVar 42 }

	eventItemPnSTDTCNTreshold1dayCH OBJECT-TYPE
		SYNTAX		OCTET STRING (SIZE (24))
		ACCESS		read-only
		STATUS		mandatory
		DESCRIPTION	"This item is not used.
				TCN THRESHOLD 1DAY CH
				 This item is available in PDH system.
					
					  [Description]
					  (Byte 0 - Byte 3)   = (Fixed to 0)
					  (Byte 4 - Byte 7)   = UAS TCN THRESHOLD TOTAL-1day (0 - 86400)
					  (Byte 8 - Byte 11)  = ES TCN THRESHOLD TOTAL-1day  (0 - 86400)
					  (Byte 12 - Byte 15) = SES TCN THRESHOLD TOTAL-1day (0 - 86400)
					  (Byte 16 - Byte 19) = BBE TCN THRESHOLD TOTAL-1day (0 - 38620800)
					  (Byte 20 - Byte 23) = SEP TCN THRESHOLD TOTAL-1day (0 - 86400)
"
		::= { pnSTDEventTrapItemVar 43 }

	eventItemPnSTDFadingDepthThreshold OBJECT-TYPE
		SYNTAX		OCTET STRING (SIZE (2))
		ACCESS		read-only
		STATUS		mandatory
		DESCRIPTION	"This item is not used.
				 FADING STATUS THRESHOLD
					  [Description]
					  Byte 1 = FADING DEPTH THRESHOLD(No.1/DIR-A)
					  Byte 2 = FADING DEPTH THRESHOLD(No.2/DIR-B)
					       (0:Invalid, 1:5[dB], 2:10[dB], 3:15[dB],
					        4:20[dB], 5:25[dB], 6:30[dB])
					   Byte 2 is fixed to 0, when Redundancy is 1+0 TERM."
		::= { pnSTDEventTrapItemVar 44 }

	eventItemPnSTDXpicCondLOSignalFail OBJECT-TYPE
		SYNTAX		INTEGER (0..2)
		ACCESS		read-only
		STATUS		mandatory
		DESCRIPTION	"XPIC CONDITION-LOCAL FAIL 
					  0:Invalid,
					  1:From RF to Self LO Signal,
					  2:Mute
				This item is available in XPIC system."
		::= { pnSTDEventTrapItemVar 45 }

	eventItemPnSTDEOWIntfcType OBJECT-TYPE
		SYNTAX		INTEGER (0..2)
		ACCESS		read-only
		STATUS		mandatory
		DESCRIPTION	"EOW2 EXTERNAL SETTING
					  0:Invalid,
					  1:Normal,
					  2:Invert"
		::= { pnSTDEventTrapItemVar 46 }

	eventItemPnSTDAlarmCorrelation OBJECT-TYPE
		SYNTAX		INTEGER (0..2)
		ACCESS		read-only
		STATUS		mandatory
		DESCRIPTION	"ALARM CORRELATION CAPABILITY
					  0:Invalid,
					  1:Off,
					  2:On"
		::= { pnSTDEventTrapItemVar 47 }

	eventItemPnSTDPmonSelect OBJECT-TYPE
		SYNTAX		OCTET STRING (SIZE (10))
		ACCESS		read-only
		STATUS		mandatory
		DESCRIPTION	"PMON SELECT
					  [Description]
					  Byte 0 = SES COUNT ACTIVATION(DIR-A) (1:30[%], 2:15[%])
					  Byte 1 = SES COUNT ACTIVATION(DIR-B) (1:30[%], 2:15[%])
					  Byte 2 = PMON E1-A SELECT (0:Not Select, x: CHx(x:1-48))
					  Byte 3 = PMON E1-B SELECT (0:Not Select, x: CHx(x:1-48))
					  Byte 4 = PMON E1-C SELECT (0:Not Select, x: CHx(x:1-48))
					  Byte 5 = PMON E1-D SELECT (0:Not Select, x: CHx(x:1-48))
					  Byte 6 = RX LEVEL TCN THRESHOLD(No.1/DIR-A) integral number
					           (signed char: -128 - 127)
					  Byte 7 = RX LEVEL TCN THRESHOLD(No.1/DIR-A)a place of decimal
					           (0-9)
					  Byte 6 = RX LEVEL TCN THRESHOLD(No.2/DIR-B) integral number
					           (signed char: -128 - 127)
					  Byte 7 = RX LEVEL TCN THRESHOLD(No.2/DIR-B)a place of decimal
					           (0-9)
					
					  *) The values of No.2/DIR-B side are fixed to 0 when
					     Redundancy is 1+0 TERM."
		::= { pnSTDEventTrapItemVar 48 }

	eventItemPnSTDMaintMode OBJECT-TYPE
		SYNTAX		OffOnValue
		ACCESS		read-only
		STATUS		mandatory
		DESCRIPTION	"MAINTENANCE
					  0:Off,
					  1:On"
		::= { pnSTDEventTrapItemVar 49 }

	eventItemPnSTDMaintLoopback1CH OBJECT-TYPE
		SYNTAX		OCTET STRING (SIZE (6))
		ACCESS		read-only
		STATUS		mandatory
		DESCRIPTION	"MAIN CH LOOPBACK-1(CHxx)
					(xx:01-48)
					  0:Off,
					  1:On
					
					  [Description]
					  Bit 0 = MAIN CH LOOPBACK-1(CH01) (0:Off, 1:On)
					  Bit 1 = MAIN CH LOOPBACK-1(CH02)
					  ...
					  Bit 46 = MAIN CH LOOPBACK-1(CH47) for E1 interface
						    MAIN CH LOOPBACK-1(E3 CH1) for E3 interface
					  Bit 47 = MAIN CH LOOPBACK-1(CH48) for E1 interface
					              MAIN CH LOOPBACK-1(E3 CH2) for E3 interface
					
					  *) The value of CHxx is fixed to 0, when CHxx Usage is not used. (xx: 01 - 48)"
		::= { pnSTDEventTrapItemVar 53 }

	eventItemPnSTDMaintLoopback2CH OBJECT-TYPE
		SYNTAX		OCTET STRING (SIZE (6))
		ACCESS		read-only
		STATUS		mandatory
		DESCRIPTION	"MAIN CH LOOPBACK-2(CHxx)
					(xx:01-48)
					  0:Off,
					  1:On
					
					  [Description]
					  Bit 0 = MAIN CH LOOPBACK-2(CH01) (0:Off, 1:On)
					  Bit 1 = MAIN CH LOOPBACK-2(CH02)
					  ...
					  Bit 46 = MAIN CH LOOPBACK-2(CH47) for E1 interface
					  	    MAIN CH LOOPBACK-2(E3 CH1) for E3 interface
					  Bit 47 = MAIN CH LOOPBACK-2(CH48) for E1 interface
						    MAIN CH LOOPBACK-2(E3 CH2) for E3 interface
					
					  *) The value of CHxx is fixed to 0, when CHxx Usage is not used. (xx: 01 - 48)"
		::= { pnSTDEventTrapItemVar 54 }

	eventItemPnSTDMaintLoopback1Work OBJECT-TYPE
		SYNTAX		OffOnValue
		ACCESS		read-only
		STATUS		mandatory
		DESCRIPTION	"MAIN LOOPBACK-1 INTFC(1)
				  Refer to OffOnValue of TEXTUAL-CONVENTION"
		::= { pnSTDEventTrapItemVar 55 }

	eventItemPnSTDMaintLoopback2 OBJECT-TYPE
		SYNTAX		OffOnValue
		ACCESS		read-only
		STATUS		mandatory
		DESCRIPTION	"MAIN LOOPBACK-2
				  Refer to OffOnValue of TEXTUAL-CONVENTION"
		::= { pnSTDEventTrapItemVar 56 }

	eventItemPnSTDMaintDADEAdjust OBJECT-TYPE
		SYNTAX		INTEGER (0..3)
		ACCESS		read-only
		STATUS		mandatory
		DESCRIPTION	"This item is not used.
				 DADE ADJUST
					  0:Invalid,
					  1:DADE,
					  2:Off Set DADE,
					  3:DADE OFF"
		::= { pnSTDEventTrapItemVar 57 }

	eventItemPnSTDMaintDADEAdjustEn OBJECT-TYPE
		SYNTAX		INTEGER (0..2)
		ACCESS		read-only
		STATUS		mandatory
		DESCRIPTION	"This item is not used.
				 DADE ADJUST ENABLE
					  0:Invalid,
					  1:Off,
					  2:Executing DADE Adjust"
		::= { pnSTDEventTrapItemVar 58 }

	eventItemPnSTDMaintLanDeviceReset OBJECT-TYPE
		SYNTAX		INTEGER (0..7)
		ACCESS		read-only
		STATUS		mandatory
		DESCRIPTION	"This item is not used.
				 LAN DEVICE RESET
					  0:Invalid,
					  1:Not Selected,
					  2:INTFC1(Port1),
					  3:INTFC1(Port2),
					  4:INTFC1(Port3),
					  5:INTFC1(Port4),
					  6:INTFC2(Port1),
					  7:INTFC2(Port2)
				 This item is available for LAN interface."
		::= { pnSTDEventTrapItemVar 59 }

	eventItemPnSTDMaintAlsRestart OBJECT-TYPE
		SYNTAX		INTEGER (0..5)
		ACCESS		read-only
		STATUS		mandatory
		DESCRIPTION	"This item is not used.
				 ALS RESTART
					  0:Invalid,
					  1:Not Selected,
					  2:2sec(INTFC1),
					  3:90sec(INTFC1),
					  4:2sec(INTFC2) for APS,
					  5:90sec(INTFC2) for APS
				 This item is available when ALS Function is enabled."
		::= { pnSTDEventTrapItemVar 60 }

	eventItemPnSTDMaintAlsManualRestart OBJECT-TYPE
		SYNTAX		INTEGER (0..3)
		ACCESS		read-only
		STATUS		mandatory
		DESCRIPTION	"This item is not used.
				 MANUAL RESTART
					  0:Invalid,
					  1:Off,
					  2:ON(INTFC1),
					  3:ON(INTFC2) for APS
				 ON means emitting a LASER signal.
				 This item is available when ALS Function is enabled."
		::= { pnSTDEventTrapItemVar 61 }

	eventItemPnSTDMaintATPCManualControl OBJECT-TYPE
		SYNTAX		OffOnValue
		ACCESS		read-only
		STATUS		mandatory
		DESCRIPTION	"ATPC MANUAL CONTROL
				 Refer to OffOnValue of TEXTUAL-CONVENTION"
		::= { pnSTDEventTrapItemVar 62 }

	eventItemPnSTDMaintATPCManualContPower OBJECT-TYPE
		SYNTAX		INTEGER
		ACCESS		read-only
		STATUS		mandatory
		DESCRIPTION	"ATPC MANUAL POWER[dB]"
		::= { pnSTDEventTrapItemVar 63 }

	eventItemPnSTDMaintTxMuteControl OBJECT-TYPE
		SYNTAX		OffOnValue
		ACCESS		read-only
		STATUS		mandatory
		DESCRIPTION	"TX MUTE CONTROL
				 Refer to OffOnValue of TEXTUAL-CONVENTION"
		::= { pnSTDEventTrapItemVar 64 }

	eventItemPnSTDMaintTxMuteContReleaseTime OBJECT-TYPE
		SYNTAX		INTEGER
		ACCESS		read-only
		STATUS		mandatory
		DESCRIPTION	"TX MUTE OFF TIMER[sec]"
		::= { pnSTDEventTrapItemVar 65 }

	eventItemPnSTDMaintCW OBJECT-TYPE
		SYNTAX		OffOnValue
		ACCESS		read-only
		STATUS		mandatory
		DESCRIPTION	"CW CONTROL
				Refer to OffOnValue of TEXTUAL-CONVENTION "
		::= { pnSTDEventTrapItemVar 66 }

	eventItemPnSTDMaintIfLoopback OBJECT-TYPE
		SYNTAX		OffOnValue
		ACCESS		read-only
		STATUS		mandatory
		DESCRIPTION	"IF LOOPBACK
				 Refer to OffOnValue of TEXTUAL-CONVENTION"
		::= { pnSTDEventTrapItemVar 67 }

	eventItemPnSTDMaintForcedXPICCont OBJECT-TYPE
		SYNTAX		INTEGER (0..2)
		ACCESS		read-only
		STATUS		mandatory
		DESCRIPTION	"XPIC CONTROL
					  0:Invalid,
					  1:Auto,
					  2:Force Reset"
		::= { pnSTDEventTrapItemVar 68 }

	eventItemPnSTDMaintForcedLinearizerCont OBJECT-TYPE
		SYNTAX		INTEGER (0..2)
		ACCESS		read-only
		STATUS		mandatory
		DESCRIPTION	"LINEARIZER CONTROL
					  0:Invalid,
					  1:Auto,
					  2:Force Reset"
		::= { pnSTDEventTrapItemVar 69 }

	eventItemPnSTDMaintRFShiftFreqSet OBJECT-TYPE
		SYNTAX		DisplayString (SIZE (4))
		ACCESS		read-only
		STATUS		mandatory
		DESCRIPTION	"This item is not used.
				 RF SHIFT FREQUENCY[MHz]
					 This value is only 1008 or 1010"
		::= { pnSTDEventTrapItemVar 71 }

	eventItemPnSTDMaintAntennaAlignMode OBJECT-TYPE
		SYNTAX		OffOnValue
		ACCESS		read-only
		STATUS		mandatory
		DESCRIPTION	"ANTENNA ALIGNMENT MODE
				Refer to OffOnValue of TEXTUAL-CONVENTION "
		::= { pnSTDEventTrapItemVar 72 }

	eventItemPnSTDinvUpdateMainWorkModule OBJECT-TYPE
		SYNTAX		INTEGER (0..12)
		ACCESS		read-only
		STATUS		mandatory
		DESCRIPTION	"Main Work Module
					  0:INVALID,
					  1:BLANK,
					  2:16xE1 BASIC PKG,
					  3:16xE1 STANDARD PKG(E/W LAN),
					  4:32xE1 PKG(E/W LAN),
					  5:48xE1 PKG,
					  6:4PORT LAN WITH E1,
					  7:STM-1(OPTICAL),
					  8:STM-1(ELECTRICAL),
					  9:2PORT LAN OVER STM-1,
					  10:GbE OVER STM-1,
					  11:E3 PKG(E/W LAN),
					  12:16E1 2-WAY/XC PKG(E/W LAN),
					  14:GbE(10/100/1000B) OVER STM-1"
		::= { pnSTDEventTrapItemVar 73 }

	eventItemPnSTDinvUpdateSubProtModule OBJECT-TYPE
		SYNTAX		INTEGER (0..255)
		ACCESS		read-only
		STATUS		mandatory
		DESCRIPTION	"SUB PROT Module
					  0:Invalid,
					  1:Not Used,
					  2:STM-1(OPTICAL),
					  3:WS/LAN,
					  4:WS"
		::= { pnSTDEventTrapItemVar 74 }

	eventItemPnSTDinvUpdateSummary OBJECT-TYPE
		SYNTAX		OCTET STRING (SIZE (2))
		ACCESS		read-only
		STATUS		mandatory
		DESCRIPTION	"Update Summary
					
					  [Description]
					  Bit 0 = CTRL (0:Not Update, 1:Updated)
					  Bit 1 = MODEM1
					  Bit 2 = MODEM2
					  Bit 3 = MAIN(WORK)
					  Bit 4 = SUB(PROT)
					  Bit 5 = ODU1
					  Bit 6 = ODU2
					  Bit 7 = CTRL PROGRAM VERSION
					  Bit 8 = TRU PROVISIONING INFO
					  Bit 9 = TRU FREQ INFO
					  Bit 10 = SUPPORTABILITY
					  Bit 11 = (FIXED to 0)
					  Bit 12 = (FIXED to 0)
					  Bit 13 = (FIXED to 0)
					  Bit 14 = (FIXED to 0)
					  Bit 15 = (FIXED to 0)"
		::= { pnSTDEventTrapItemVar 75 }

	eventItemPnSTDLanCollision OBJECT-TYPE
		SYNTAX		INTEGER (0..2)
		ACCESS		read-only
		STATUS		mandatory
		DESCRIPTION	"LAN COLLISION PORTx
					(x : 1-4)
					  0:Invalid,
					  1:Normal,
					  2:Collision"
		::= { pnSTDEventTrapItemVar 76 }

	eventItemPnSTDSCLanCollision OBJECT-TYPE
		SYNTAX		INTEGER (0..2)
		ACCESS		read-only
		STATUS		mandatory
		DESCRIPTION	"INTFC(2) LAN COLLISION PORTx
					(x : 1-2)
					  0:Invalid,
					  1:Normal,
					  2:Collision"
		::= { pnSTDEventTrapItemVar 77 }

	eventItemPnSTDAPSStatus OBJECT-TYPE
		SYNTAX		INTEGER (0..2)
		ACCESS		read-only
		STATUS		mandatory
		DESCRIPTION	"APS STATUS
					  0:Invalid,
					  1:Working,
					  2:Protection"
		::= { pnSTDEventTrapItemVar 78 }

	eventItemPnSTDAtpcPowerModeStatus OBJECT-TYPE
		SYNTAX		INTEGER (0..2)
		ACCESS		read-only
		STATUS		mandatory
		DESCRIPTION	"ATPC POWER MODE
					  0:Invalid,
					  1:Active,
					  2:Stop"
		::= { pnSTDEventTrapItemVar 80 }

	eventItemPnSTDAuxOutput OBJECT-TYPE
		SYNTAX		INTEGER (0..2)
		ACCESS		read-only
		STATUS		mandatory
		DESCRIPTION	"ITEM NAME(OUTPUT-x)
					(x : 1-4)
					  0:Invalid,
					  1:(ON),
					  2:(OFF)"
		::= { pnSTDEventTrapItemVar 81 }

	eventItemPnSTDMMCMount OBJECT-TYPE
		SYNTAX		OffOnValue
		ACCESS		read-only
		STATUS		mandatory
		DESCRIPTION	"MMC MOUNT
				 Refer to OffOnValue of TEXTUAL-CONVENTION"
		::= { pnSTDEventTrapItemVar 82 }

	eventItemPnSTDAPSLockinStatus OBJECT-TYPE
		SYNTAX		INTEGER (0..2)
		ACCESS		read-only
		STATUS		mandatory
		DESCRIPTION	"APS LOCK IN STATUS
					  0:Invalid,
					  1:Normal,
					  2:Lock IN"
		::= { pnSTDEventTrapItemVar 83 }

	eventItemPnSTDMaintLoopback1Prot OBJECT-TYPE
		SYNTAX		OffOnValue
		ACCESS		read-only
		STATUS		mandatory
		DESCRIPTION	"MAIN LOOPBACK-1 INTFC(2)"
		::= { pnSTDEventTrapItemVar 84 }

	eventItemPnSTDMaintTxSWMode OBJECT-TYPE
		SYNTAX		INTEGER (0..2)
		ACCESS		read-only
		STATUS		mandatory
		DESCRIPTION     "TX SW MODE
					  0:Invalid,
					  1:Auto(No.1),
					  2:Auto(No.2),
					  3:Manual(No.1),
					  4:Manual(No.2)"
		::= { pnSTDEventTrapItemVar 85 }

	eventItemPnSTDMaintRxSWMode OBJECT-TYPE
		SYNTAX		INTEGER (0..2)
		ACCESS		read-only
		STATUS		mandatory
		DESCRIPTION     "RX SW MODE
					  0:Invalid,
					  1:Auto(No.1),
					  2:Auto(No.2),
					  3:Manual(No.1),
					  4:Manual(No.2)"
		::= { pnSTDEventTrapItemVar 86 }

	eventItemPnSTDMaintAPSSWMode OBJECT-TYPE
		SYNTAX		INTEGER (0..2)
		ACCESS		read-only
		STATUS		mandatory
		DESCRIPTION     "APS SW MODE
					  0:Invalid,
					  1:Auto(Working),
					  2:Auto(Protection),
					  3:Manual(Working),
					  4:Manual(Protection)"
		::= { pnSTDEventTrapItemVar 87 }

	eventItemPnSTDGbELinkLossForward OBJECT-TYPE
		SYNTAX		INTEGER (0..2)
		ACCESS		read-only
		STATUS		mandatory
		DESCRIPTION     "GbE Link Loss Forward
					0:Invalid,
					1:Normal,
					2:Under Execution"
		::= { pnSTDEventTrapItemVar 88 }

	eventItemPnSTDGbESpeedDuplex OBJECT-TYPE
		SYNTAX		OCTET STRING (SIZE (1))
		ACCESS		read-only
		STATUS		mandatory
		DESCRIPTION	"GbE Speed & Duplex
					 [Description]
					 Bit 0 = MASTER/SLAVE (0:SLAVE, 1:MASTER)
					 Bit 1 = FULL DUPLEX (0:HALF, 1:FULL)
					 Bit 2 = FORCED SETTING MODE (0:AUTONEGO, 1:FORCED)
					 Bit 3 = MDIX (0:MDI, 1:MDIX)
					 Bit 4, 5 = SPEED (00:10M, 01:100M, 10:1000M, 11:1000M-INI)"
		::= { pnSTDEventTrapItemVar 89 }

	eventItemPnSTDMaintLoopback3CH OBJECT-TYPE
		SYNTAX		OCTET STRING (SIZE (6))
		ACCESS		read-only
		STATUS		mandatory
		DESCRIPTION	"Main CH Loopback-2(DIR-B)(CHxx)
				 (xx:01-48)
					  0:Invalid,
					  1:Off,
					  2:On"
		::= { pnSTDEventTrapItemVar 90 }

	pnSTDStatusTrapItemVar OBJECT IDENTIFIER
		::= { pnSTDTrapItemVar 4 }

	statusItemPnSTDAuxInput OBJECT-TYPE
		SYNTAX		INTEGER (0..2)
		ACCESS		read-only
		STATUS		mandatory
		DESCRIPTION	"ITEM NAME(INPUT-x)
					(x : 1-6)
					  0:Invalid,
					  1:Open State,
					  2:Close State
					FLAG=SUMMARY_AUX
					probableCause=invalid"
		::= { pnSTDStatusTrapItemVar 1 }

	pnSTDSystemTrapItemVar OBJECT IDENTIFIER
		::= { pnSTDTrapItemVar 5 }

	systemItemPnSTDLocalUpdate OBJECT-TYPE
		SYNTAX		INTEGER (0..2)
		ACCESS		read-only
		STATUS		mandatory
		DESCRIPTION	"EQUIPMENT CONFIGURATION
					  0:Invalid,
					  1:NO CHANGE,
					  2:UPDATED"
		::= { pnSTDSystemTrapItemVar 2 }

	partialSummaryTrapTRU	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  partialSummaryItemTRU
					}
		DESCRIPTION "This trap is sent
					  when TRU(ODU) Summary status is changed."
		::= 201

	partialSummaryTrapINTFC1	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  partialSummaryItemINTFC1
					}
		DESCRIPTION "This trap is sent
					  when INTFC1 Summary status is changed."
		::= 202

	partialSummaryTrapCTRL	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  partialSummaryItemCTRL
					}
		DESCRIPTION "This trap is sent
					  when CTRL Summary status is changed."
		::= 203

	partialSummaryTrapAux	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  partialSummaryItemAux
					}
		DESCRIPTION "This trap is sent
					  when AUX IO Summary status is changed."
		::= 204

	partialSummaryTrapLpm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  partialSummaryItemLpm
					}
		DESCRIPTION "This trap is sent
					  when Link Pmon Summary status is changed."
		::= 205

	partialSummaryTrapINTFC2	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  partialSummaryItemINTFC2
					}
		DESCRIPTION "This trap is sent
					  when INTFC2 Summary status is changed."
		::= 206

	partialSummaryTrapMODEM	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  partialSummaryItemMODEM
					}
		DESCRIPTION "This trap is sent
					  when Modem Summary status is changed."
		::= 207

	alarmTrapPnSTDTxPowerAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTxPowerAlarm
					}
		DESCRIPTION "This trap is sent
					  when TX POWER status is changed."
		::= 301

	alarmTrapPnSTDTxInputAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTxInputAlarm
					}
		DESCRIPTION "This trap is sent
					  when TX INPUT status is changed."
		::= 302

	alarmTrapPnSTDRxLevelAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDRxLevelAlarm
					}
		DESCRIPTION "This trap is sent
					  when RX LEVEL status is changed."
		::= 303

	alarmTrapPnSTDApcAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDApcAlarm
					}
		DESCRIPTION "This trap is sent
					  when APC status is changed."
		::= 304

	alarmTrapPnSTDTRUCPUAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTRUCPUAlarm
					}
		DESCRIPTION "This trap is sent
					  when ODU CPU/CABLE OPEN status is changed."
		::= 305

	alarmTrapPnSTDModemAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDModemAlarm
					}
		DESCRIPTION "This trap is sent
					  when MODEM MODULE status is changed."
		::= 306

	alarmTrapPnSTDModemUneq	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDModemUneq
					}
		DESCRIPTION "This trap is sent
					  when MODEM UNEQUIPPED status is changed."
		::= 307

	alarmTrapPnSTDHighBERAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDHighBERAlarm
					}
		DESCRIPTION "This trap is sent
					  when HIGH BER status is changed."
		::= 308

	alarmTrapPnSTDLowBERAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDLowBERAlarm
					}
		DESCRIPTION "This trap is sent
					  when LOW BER status is changed."
		::= 309

	alarmTrapPnSTDModAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDModAlarm
					}
		DESCRIPTION "This trap is sent
					  when MOD status is changed."
		::= 310

	alarmTrapPnSTDDemAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDDemAlarm
					}
		DESCRIPTION "This trap is sent
					  when DEM status is changed."
		::= 311

	alarmTrapPnSTDXIfLevelAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDXIfLevelAlarm
					}
		DESCRIPTION "This trap is sent
					  when XIF status is changed."
		::= 312

	alarmTrapPnSTDXContAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDXContAlarm
					}
		DESCRIPTION "This item is not used."
		::= 313

	alarmTrapPnSTDPSAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDPSAlarm
					}
		DESCRIPTION "This trap is sent
					  when POWER SUPPLY status is changed."
		::= 314

	alarmTrapPnSTDIfCableShort	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDIfCableShort
					}
		DESCRIPTION "This trap is sent
					  when IF CABLE SHORT status is changed."
		::= 315

	alarmTrapPnSTDLof	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDLof
					}
		DESCRIPTION "This trap is sent
					  when LOF status is changed."
		::= 316

	alarmTrapPnSTDCableEQLAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDCableEQLAlarm
					}
		DESCRIPTION "This trap is sent
					  when CABLE EQL status is changed."
		::= 317

	alarmTrapPnSTDXRefAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDXRefAlarm
					}
		DESCRIPTION "This trap is sent
					  when XREF status is changed."
		::= 318

	alarmTrapPnSTDIntfcMAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDIntfcMAlarm
					}
		DESCRIPTION "This trap is sent
					  when INTFC(1) MODULE status is changed."
		::= 319

	alarmTrapPnSTDIntfcMUneq	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDIntfcMUneq
					}
		DESCRIPTION "This trap is sent
					  when INTFC(1) UNEQUIPPED status is changed."
		::= 320

	alarmTrapPnSTDInputLos	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDInputLos
					}
		DESCRIPTION "This trap is sent
					  when INPUT LOS CHxx(xx : 1-48) status is changed."
		::= 321

	alarmTrapPnSTDLosMUXWork	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDLosMUXWork
					}
		DESCRIPTION "This trap is sent
					  when STM-1(1) LOS(MUX) status is changed."
		::= 323

	alarmTrapPnSTDLosDMRWork	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDLosDMRWork
					}
		DESCRIPTION "This trap is sent
					  when STM-1(1) LOS(DMR) status is changed."
		::= 324

	alarmTrapPnSTDUsageError	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDUsageError
					}
		DESCRIPTION "This trap is sent
					  when USAGE ERROR CHxx(xx : 1-48) status is changed."
		::= 325

	alarmTrapPnSTDLink	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDLink
					}
		DESCRIPTION "This trap is sent
					  when LAN LINK PORTx(x : 1-4) status is changed."
		::= 326

	alarmTrapPnSTDEBERMUXWork	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDEBERMUXWork
					}
		DESCRIPTION "This trap is sent
					  when STM-1(1) E-BER(MUX) status is changed."
		::= 328

	alarmTrapPnSTDEBERDMRWork	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDEBERDMRWork
					}
		DESCRIPTION "This trap is sent
					  when STM-1(1) E-BER(DMR) status is changed."
		::= 329

	alarmTrapPnSTDSDMUXWork	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDSDMUXWork
					}
		DESCRIPTION "This trap is sent
					  when STM-1(1) SD(MUX) status is changed."
		::= 330

	alarmTrapPnSTDSDDMRWork	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDSDDMRWork
					}
		DESCRIPTION "This trap is sent
					  when STM-1(1) SD(DMR) status is changed."
		::= 331

	alarmTrapPnSTDIntfcSAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDIntfcSAlarm
					}
		DESCRIPTION "This trap is sent
					  when INTFC(2) MODULE status is changed."
		::= 332

	alarmTrapPnSTDIntfcSUneq	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDIntfcSUneq
					}
		DESCRIPTION "This trap is sent
					  when INTFC(2) UNEQUIPPED status is changed."
		::= 333

	alarmTrapPnSTDLosMUXProt	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDLosMUXProt
					}
		DESCRIPTION "This trap is sent
					  when STM-1(2) LOS(MUX) status is changed."
		::= 334

	alarmTrapPnSTDEBERMUXProt	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDEBERMUXProt
					}
		DESCRIPTION "This trap is sent
					  when STM-1(2) E-BER(MUX) status is changed."
		::= 335

	alarmTrapPnSTDEBERDMRProt	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDEBERDMRProt
					}
		DESCRIPTION "This trap is sent
					  when STM-1(2) E-BER(DMR) status is changed."
		::= 336

	alarmTrapPnSTDSDMUXProt	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDSDMUXProt
					}
		DESCRIPTION "This trap is sent
					  when STM-1(2) SD(MUX) status is changed."
		::= 337

	alarmTrapPnSTDSDDMRProt	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDSDDMRProt
					}
		DESCRIPTION "This trap is sent
					  when STM-1(2) SD(DMR) status is changed."
		::= 338

	alarmTrapPnSTDWSLos	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDWSLos
					}
		DESCRIPTION "This trap is sent
					  when WS INPUT LOS status is changed."
		::= 339

	alarmTrapPnSTDSCLanLink	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDSCLanLink
					}
		DESCRIPTION "This trap is sent
					  when INTFC(2) LAN LINK PORTx(x : 1-2) status is changed."
		::= 340

	alarmTrapPnSTDCTRLAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDCTRLAlarm
					}
		DESCRIPTION "This trap is sent
					  when CTRL MODULE status is changed."
		::= 342

	alarmTrapPnSTDAPSSWFail	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDAPSSWFail
					}
		DESCRIPTION "This trap is sent
					  when APS SW FAIL status is changed."
		::= 344

	alarmTrapPnSTDTcn15minTotalOFS	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn15minTotalOFS
					}
		DESCRIPTION "This trap is sent
					  when TCN-OFS-15min TOTAL status is changed."
		::= 346

	alarmTrapPnSTDTcn15minTotalUAS	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn15minTotalUAS
					}
		DESCRIPTION "This trap is sent
					  when TCN-UAS-15min TOTAL status is changed."
		::= 347

	alarmTrapPnSTDTcn15minTotalES	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn15minTotalES
					}
		DESCRIPTION "This trap is sent
					  when TCN-ES-15min TOTAL status is changed."
		::= 348

	alarmTrapPnSTDTcn15minTotalSES	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn15minTotalSES
					}
		DESCRIPTION "This trap is sent
					  when TCN-SES-15min TOTAL status is changed."
		::= 349

	alarmTrapPnSTDTcn15minTotalBBE	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn15minTotalBBE
					}
		DESCRIPTION "This trap is sent
					  when TCN-BBE-15min TOTAL status is changed."
		::= 350

	alarmTrapPnSTDTcn15minTotalSEP	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn15minTotalSEP
					}
		DESCRIPTION "This trap is sent
					  when TCN-SEP-15min TOTAL status is changed."
		::= 351

	alarmTrapPnSTDTcn15minCHUAS	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn15minCHUAS
					}
		DESCRIPTION "This item is not used.
					 This trap is sent
					  when TCN-UAS-15min CHxx(xx : 1-48 only selected 4ch.)
					  status is changed."
		::= 353

	alarmTrapPnSTDTcn15minCHES	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn15minCHES
					}
		DESCRIPTION "This item is not used. 
					 This trap is sent
					  when TCN-ES-15min CHxx(xx : 1-48 only selected 4ch.)
					  status is changed."
		::= 354

	alarmTrapPnSTDTcn15minCHSES	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn15minCHSES
					}
		DESCRIPTION "This item is not used. 
					 This trap is sent
					  when TCN-SES-15min CHxx(xx : 1-48 only selected 4ch.)
					  status is changed."
		::= 355

	alarmTrapPnSTDTcn15minCHBBE	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn15minCHBBE
					}
		DESCRIPTION "This item is not used. 
					 This trap is sent
					  when TCN-BBE-15min CHxx(xx : 1-48 only selected 4ch.)
					  status is changed."
		::= 356

	alarmTrapPnSTDTcn15minCHSEP	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn15minCHSEP
					}
		DESCRIPTION "This item is not used. 
					 This trap is sent
					  when TCN-SEP-15min CHxx(xx : 1-48 only selected 4ch.)
					  status is changed."
		::= 357

	alarmTrapPnSTDTcn1dayTotalOFS	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn1dayTotalOFS
					}
		DESCRIPTION "This trap is sent
					  when TCN-OFS-1day TOTAL status is changed."
		::= 358

	alarmTrapPnSTDTcn1dayTotalUAS	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn1dayTotalUAS
					}
		DESCRIPTION "This trap is sent
					  when TCN-UAS-1day TOTAL status is changed."
		::= 359

	alarmTrapPnSTDTcn1dayTotalES	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn1dayTotalES
					}
		DESCRIPTION "This trap is sent
					  when TCN-ES-1day TOTAL status is changed."
		::= 360

	alarmTrapPnSTDTcn1dayTotalSES	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn1dayTotalSES
					}
		DESCRIPTION "This trap is sent
					  when TCN-SES-1day TOTAL status is changed."
		::= 361

	alarmTrapPnSTDTcn1dayTotalBBE	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn1dayTotalBBE
					}
		DESCRIPTION "This trap is sent
					  when TCN-BBE-1day TOTAL status is changed."
		::= 362

	alarmTrapPnSTDTcn1dayTotalSEP	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn1dayTotalSEP
					}
		DESCRIPTION "This trap is sent
					  when TCN-SEP-1day TOTAL status is changed."
		::= 363

	alarmTrapPnSTDTcn1dayCHUAS	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn1dayCHUAS
					}
		DESCRIPTION "This item is not used. 
					 This trap is sent
					  when TCN-UAS-1day CHxx(xx : 1-48 only selected 4ch.)
					  status is changed."
		::= 365

	alarmTrapPnSTDTcn1dayCHES	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn1dayCHES
					}
		DESCRIPTION "This item is not used. 
					 This trap is sent
					  when TCN-ES-1day CHxx(xx : 1-48 only selected 4ch.)
					  status is changed."
		::= 366

	alarmTrapPnSTDTcn1dayCHSES	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn1dayCHSES
					}
		DESCRIPTION "This item is not used.
					 This trap is sent
					  when TCN-SES-1day CHxx(xx : 1-48 only selected 4ch.)
					  status is changed."
		::= 367

	alarmTrapPnSTDTcn1dayCHBBE	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn1dayCHBBE
					}
		DESCRIPTION "This item is not used. 
					 This trap is sent
					  when TCN-BBE-1day CHxx(xx : 1-48 only selected 4ch.)
					  status is changed."
		::= 368

	alarmTrapPnSTDTcn1dayCHSEP	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcn1dayCHSEP
					}
		DESCRIPTION "This item is not used. 
					 This trap is sent
					  when TCN-SEP-1day CHxx(xx : 1-48 only selected 4ch.)
					  status is changed."
		::= 369

	alarmTrapPnSTDTcnUAEDMRWork	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcnUAEDMRWork
					}
		DESCRIPTION "This trap is sent
					  when Unavailable Event(TOTAL)
					  (DIR-A side for PDH, INTFC(1) for STM-1)
					  status is changed."
		::= 370

	alarmTrapPnSTDTcnUAEDMRProt	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcnUAEDMRProt
					}
		DESCRIPTION "This trap is sent
					  when Unavailable Event(TOTAL)
					  (DIR-A side for PDH, INTFC(1) for STM-1)
					  status is changed."
		::= 371

	alarmTrapPnSTDTcnTCS15minRxLev	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcnTCS15minRxLev
					}
		DESCRIPTION "This trap is sent
					  when TCN-RX LEV-15min status is changed."
		::= 372

	alarmTrapPnSTDTcnTCS1dayRxLev	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcnTCS1dayRxLev
					}
		DESCRIPTION "This trap is sent
					  when TCN-RX LEV-1day status is changed."
		::= 373

	alarmTrapPnSTDTRULORefAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTRULORefAlarm
					}
		DESCRIPTION "This trap is sent
					  when LO REF status is changed."
		::= 374

	alarmTrapPnSTDLofMUXWork	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDLofMUXWork
					}
		DESCRIPTION "This trap is sent
					  when STM-1(1) LOF(MUX) status is changed."
		::= 375

	alarmTrapPnSTDLofDMRWork	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDLofDMRWork
					}
		DESCRIPTION "This trap is sent
					  when STM-1(1) LOF(DMR) status is changed."
		::= 376

	alarmTrapPnSTDLosDMRProt	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDLosDMRProt
					}
		DESCRIPTION "This trap is sent
					  when STM-1(2) LOS(DMR) status is changed."
		::= 377

	alarmTrapPnSTDLofMUXProt	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDLofMUXProt
					}
		DESCRIPTION "This trap is sent
					  when STM-1(2) LOF(MUX) status is changed."
		::= 378

	alarmTrapPnSTDLofDMRProt	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDLofDMRProt
					}
		DESCRIPTION "This trap is sent
					  when STM-1(2) LOF(DMR) status is changed."
		::= 379

	alarmTrapPnSTDStm1TFWorkAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDStm1TFWorkAlarm
					}
		DESCRIPTION "This trap is sent
					  when STM-1(1) TF status is changed."
		::= 380

	alarmTrapPnSTDStm1TFProtAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDStm1TFProtAlarm
					}
		DESCRIPTION "This trap is sent
					  when STM-1(2) TF status is changed."
		::= 381

	alarmTrapPnSTDTcnUAEMUXWork	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcnUAEMUXWork
					}
		DESCRIPTION "This trap is sent
					  when STM-1(1) Unavailable Event(MUX) status is changed."
		::= 382

	alarmTrapPnSTDTcnUAEMUXProt	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTcnUAEMUXProt
					}
		DESCRIPTION "This trap is sent
					  when STM-1(2) Unavailable Event(MUX) status is changed."
		::= 383

	alarmTrapPnSTDAuxClusterAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDAuxClusterAlarm
					}
		DESCRIPTION "This trap is sent
					  when AUX Cluster Alarm Index status is changed.

					 This is not used. 
					 This trap is sent
					  when CLUSTERx ALARM(x : 1-4) status is changed."
		::= 384

	alarmTrapPnSTDLinearizerFail	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDLinearizerFail
					}
		DESCRIPTION "This trap is sent
					  when LINEARIZER status is changed."
		::= 385

	alarmTrapPnSTDRouteID	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDRouteID
					}
		DESCRIPTION "This trap is sent
					  when FRAME ID status is changed."
		::= 386

	alarmTrapPnSTDEarlyWarning	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDEarlyWarning
					}
		DESCRIPTION "This trap is sent
					  when EARLY WARNING status is changed."
		::= 387

	alarmTrapPnSTDInputVoltage	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDInputVoltage
					}
		DESCRIPTION "This trap is sent
					  when INPUT VOLTAGE status is changed."
		::= 388

	alarmTrapPnSTDIntfcMTypeMismatch	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDIntfcMTypeMismatch
					}
		DESCRIPTION "This trap is sent
					  when INTFC(1) TYPE MISMATCH status is changed."
		::= 389

	alarmTrapPnSTDIntfcSTypeMismatch	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDIntfcSTypeMismatch
					}
		DESCRIPTION "This trap is sent
					  when INTFC(2) TYPE MISMATCH status is changed."
		::= 390

	alarmTrapPnSTDXpicModeMismatch	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDXpicModeMismatch
					}
		DESCRIPTION "This trap is sent
					  when XPIC MODE MISMATCH status is changed."
		::= 391

	alarmTrapPnSTDXControlAlarm	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDXControlAlarm
					}
		DESCRIPTION "This trap is sent
					  when XCTRL status is changed."
		::= 392

	alarmTrapPnSTDGbELink	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDGbELink
					}
		DESCRIPTION "This trap is sent
					  when GbE LAN Link Port status is changed."
		::= 393

	alarmTrapPnSTDModemTypeMismatch	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDModemTypeMismatch
					}
		::= 394

	alarmTrapPnSTDTRUTypeMismatch	TRAP-TYPE
		ENTERPRISE	pasolinkNeoStd
		VARIABLES	{
					  pnTrapSequenceNumber,
					  pnTrapDate,
					  pnTrapTime,
					  pnSeverity,
					  pnAlarmType,
					  pnProbableCause,
					  pnTrapSource,
					  alarmItemPnSTDTRUTypeMismatch
					}
		::= 395

	eventTrapPnSTDTxMuteStatus	TRAP-TYPE
		ENTERPRISE	pasolinkNeoStd
		VARIABLES	{
					  pnTrapSequenceNumber,
					  pnTrapDate,
					  pnTrapTime,
					  pnTrapSource,
					  eventItemPnSTDTxMuteStatus
					}
		DESCRIPTION "This trap is sent
					  when MUTE STATUS status is changed."
		::= 403

	eventTrapPnSTDTxSWStatus	TRAP-TYPE
		ENTERPRISE	pasolinkNeoStd
		VARIABLES	{
					  pnTrapSequenceNumber,
					  pnTrapDate,
					  pnTrapTime,
					  pnTrapSource,
					  eventItemPnSTDTxSWStatus
					}
		DESCRIPTION "This trap is sent
					  when TX SW STATUS status is changed."
		::= 404

	eventTrapPnSTDSCLanLinkLossForward	TRAP-TYPE
		ENTERPRISE	pasolinkNeoStd
		VARIABLES	{
					  pnTrapSequenceNumber,
					  pnTrapDate,
					  pnTrapTime,
					  pnTrapSource,
					  eventItemPnSTDSCLanLinkLossForward
					}
		DESCRIPTION "This trap is sent
					  when INTFC(2) LLF PORTx status is changed."
		::= 405

	eventTrapPnSTDRxSWStatus	TRAP-TYPE
		ENTERPRISE	pasolinkNeoStd
		VARIABLES	{
					  pnTrapSequenceNumber,
					  pnTrapDate,
					  pnTrapTime,
					  pnTrapSource,
					  eventItemPnSTDRxSWStatus
					}
		DESCRIPTION "This trap is sent
					  when RX SW STATUS status is changed."
		::= 406

	eventTrapPnSTDXPICFuncStatus	TRAP-TYPE
		ENTERPRISE	pasolinkNeoStd
		VARIABLES	{
					  pnTrapSequenceNumber,
					  pnTrapDate,
					  pnTrapTime,
					  pnTrapSource,
					  eventItemPnSTDXPICFuncStatus
					}
		DESCRIPTION "This trap is sent
					  when XPIC STATUS status is changed."
		::= 407

	eventTrapPnSTDLinearizerFunc	TRAP-TYPE
		ENTERPRISE	pasolinkNeoStd
		VARIABLES	{
					  pnTrapSequenceNumber,
					  pnTrapDate,
					  pnTrapTime,
					  pnTrapSource,
					  eventItemPnSTDLinearizerFunc
					}
		DESCRIPTION "This trap is sent
					  when LINEARIZER FUNCTION status is changed."
		::= 408

	eventTrapPnSTDFadeDepthStatus	TRAP-TYPE
		ENTERPRISE	pasolinkNeoStd
		VARIABLES	{
					  pnTrapSequenceNumber,
					  pnTrapDate,
					  pnTrapTime,
					  pnTrapSource,
					  eventItemPnSTDFadeDepthStatus
					}
		DESCRIPTION "This trap is sent
					  when FADING STATUS status is changed."
		::= 409

	eventTrapPnSTDSTM1OutContWork	TRAP-TYPE
		ENTERPRISE	pasolinkNeoStd
		VARIABLES	{
					  pnTrapSequenceNumber,
					  pnTrapDate,
					  pnTrapTime,
					  pnTrapSource,
					  eventItemPnSTDSTM1OutContWork
					}
		DESCRIPTION "This trap is sent
					  when STM-1(1) OUTPUT CONTROL status is changed."
		::= 410

	eventTrapPnSTDAisGeneratedCH	TRAP-TYPE
		ENTERPRISE	pasolinkNeoStd
		VARIABLES	{
					  pnTrapSequenceNumber,
					  pnTrapDate,
					  pnTrapTime,
					  pnTrapSource,
					  eventItemPnSTDAisGeneratedCH
					}
		DESCRIPTION "This trap is sent
					  when AIS GENERATED CHxx(xx : 1-48) status is changed."
		::= 411

	eventTrapPnSTDAisReceivedCH	TRAP-TYPE
		ENTERPRISE	pasolinkNeoStd
		VARIABLES	{
					  pnTrapSequenceNumber,
					  pnTrapDate,
					  pnTrapTime,
					  pnTrapSource,
					  eventItemPnSTDAisReceivedCH
					}
		DESCRIPTION "This trap is sent
					  when AIS RECEIVED CHxx(xx : 1-48) status is changed."
		::= 412

	eventTrapPnSTDLinkLossForward	TRAP-TYPE
		ENTERPRISE	pasolinkNeoStd
		VARIABLES	{
					  pnTrapSequenceNumber,
					  pnTrapDate,
					  pnTrapTime,
					  pnTrapSource,
					  eventItemPnSTDLinkLossForward
					}
		DESCRIPTION "This trap is sent
					  when LLF PORTx(x : 1-4) status is changed."
		::= 413

	eventTrapPnSTDSpeedDuplex	TRAP-TYPE
		ENTERPRISE	pasolinkNeoStd
		VARIABLES	{
					  pnTrapSequenceNumber,
					  pnTrapDate,
					  pnTrapTime,
					  pnTrapSource,
					  eventItemPnSTDSpeedDuplex
					}
		DESCRIPTION "This trap is sent
					  when LAN MODE PORTx(x : 1-4) status is changed."
		::= 414

	eventTrapPnSTDInphaseWork	TRAP-TYPE
		ENTERPRISE	pasolinkNeoStd
		VARIABLES	{
					  pnTrapSequenceNumber,
					  pnTrapDate,
					  pnTrapTime,
					  pnTrapSource,
					  eventItemPnSTDInphaseWork
					}
		DESCRIPTION "This trap is sent
					  when INTFC(1) INPHASE status is changed."
		::= 415

	eventTrapPnSTDSTM1OutContProt	TRAP-TYPE
		ENTERPRISE	pasolinkNeoStd
		VARIABLES	{
					  pnTrapSequenceNumber,
					  pnTrapDate,
					  pnTrapTime,
					  pnTrapSource,
					  eventItemPnSTDSTM1OutContProt
					}
		DESCRIPTION "This trap is sent
					  when STM-1(2) OUTPUT CONTROL status is changed."
		::= 416

	eventTrapPnSTDInphaseProt	TRAP-TYPE
		ENTERPRISE	pasolinkNeoStd
		VARIABLES	{
					  pnTrapSequenceNumber,
					  pnTrapDate,
					  pnTrapTime,
					  pnTrapSource,
					  eventItemPnSTDInphaseProt
					}
		DESCRIPTION "This trap is sent
					  when INTFC(2) INPHASE status is changed."
		::= 417

	eventTrapPnSTDWSAisGeneratedCH	TRAP-TYPE
		ENTERPRISE	pasolinkNeoStd
		VARIABLES	{
					  pnTrapSequenceNumber,
					  pnTrapDate,
					  pnTrapTime,
					  pnTrapSource,
					  eventItemPnSTDWSAisGeneratedCH
					}
		DESCRIPTION "This trap is sent
					  when WS AIS GENERATED status is changed."
		::= 418

	eventTrapPnSTDWSAisReceivedCH	TRAP-TYPE
		ENTERPRISE	pasolinkNeoStd
		VARIABLES	{
					  pnTrapSequenceNumber,
					  pnTrapDate,
					  pnTrapTime,
					  pnTrapSource,
					  eventItemPnSTDWSAisReceivedCH
					}
		DESCRIPTION "This trap is sent
					  when WS AIS RECEIVED status is changed."
		::= 419

	eventTrapPnSTDCHUsage	TRAP-TYPE
		ENTERPRISE	pasolinkNeoStd
		VARIABLES	{
					  pnTrapSequenceNumber,
					  pnTrapDate,
					  pnTrapTime,
					  pnTrapSource,
					  eventItemPnSTDCHUsage
					}
		DESCRIPTION "This trap is sent
					  when CH USAGE(CHxx)(xx : 1-48) status is changed."
		::= 420

	eventTrapPnSTDCHCondition	TRAP-TYPE
		ENTERPRISE	pasolinkNeoStd
		VARIABLES	{
					  pnTrapSequenceNumber,
					  pnTrapDate,
					  pnTrapTime,
					  pnTrapSource,
					  eventItemPnSTDCHCondition
					}
		DESCRIPTION "This trap is sent
					  when CH CONDITION status is changed."
		::= 421

	eventTrapPnSTDCHImpedance	TRAP-TYPE
		ENTERPRISE	pasolinkNeoStd
		VARIABLES	{
					  pnTrapSequenceNumber,
					  pnTrapDate,
					  pnTrapTime,
					  pnTrapSource,
					  eventItemPnSTDCHImpedance
					}
		DESCRIPTION "This trap is sent
					  when E1 PORT IMPEDANCE status is changed."
		::= 422

	eventTrapPnSTDMSAisGeneration	TRAP-TYPE
		ENTERPRISE	pasolinkNeoStd
		VARIABLES	{
					  pnTrapSequenceNumber,
					  pnTrapDate,
					  pnTrapTime,
					  pnTrapSource,
					  eventItemPnSTDMSAisGeneration
					}
		DESCRIPTION "This trap is sent
					  when MS-AIS GENERATION status is changed."
		::= 423

	eventTrapPnSTDDxcFunction	TRAP-TYPE
		ENTERPRISE	pasolinkNeoStd
		VARIABLES	{
					  pnTrapSequenceNumber,
					  pnTrapDate,
					  pnTrapTime,
					  pnTrapSource,
					  eventItemPnSTDDxcFunction
					}
		DESCRIPTION "This trap is sent
					  when DXC FUNCTION status is changed."
		::= 424

	eventTrapPnSTDDxcCHSetting	TRAP-TYPE
		ENTERPRISE	pasolinkNeoStd
		VARIABLES	{
					  pnTrapSequenceNumber,
					  pnTrapDate,
					  pnTrapTime,
					  pnTrapSource,
					  eventItemPnSTDDxcCHSetting
					}
		DESCRIPTION "This trap is sent
					  when DXC CH Setting status is changed."
		::= 425

	eventTrapPnSTDDxcAssign	TRAP-TYPE
		ENTERPRISE	pasolinkNeoStd
		VARIABLES	{
					  pnTrapSequenceNumber,
					  pnTrapDate,
					  pnTrapTime,
					  pnTrapSource,
					  eventItemPnSTDDxcAssign
					}
		DESCRIPTION "This item is not used.
			     This trap is sent
					  when DXC ASSIGNMENT CHANGED status is changed."
		::= 426

	eventTrapPnSTDBERThreshold	TRAP-TYPE
		ENTERPRISE	pasolinkNeoStd
		VARIABLES	{
					  pnTrapSequenceNumber,
					  pnTrapDate,
					  pnTrapTime,
					  pnTrapSource,
					  eventItemPnSTDBERThreshold
					}
		DESCRIPTION "This trap is sent
					  when BER THRESHOLD SETTING status is changed."
		::= 427

	eventTrapPnSTDSubIntfc	TRAP-TYPE
		ENTERPRISE	pasolinkNeoStd
		VARIABLES	{
					  pnTrapSequenceNumber,
					  pnTrapDate,
					  pnTrapTime,
					  pnTrapSource,
					  eventItemPnSTDSubIntfc
					}
		DESCRIPTION "This trap is sent
					  when SUB INTERFACE status is changed."
		::= 428

	eventTrapPnSTDSCAssign	TRAP-TYPE
		ENTERPRISE	pasolinkNeoStd
		VARIABLES	{
					  pnTrapSequenceNumber,
					  pnTrapDate,
					  pnTrapTime,
					  pnTrapSource,
					  eventItemPnSTDSCAssign
					}
		DESCRIPTION "This trap is sent
					  when SC ASSIGNMENT status is changed."
		::= 429

	eventTrapPnSTDLanPortSetting	TRAP-TYPE
		ENTERPRISE	pasolinkNeoStd
		VARIABLES	{
					  pnTrapSequenceNumber,
					  pnTrapDate,
					  pnTrapTime,
					  pnTrapSource,
					  eventItemPnSTDLanPortSetting
					}
		DESCRIPTION "This trap is sent
					  when LAN PORT SETTING status is changed."
		::= 430

	eventTrapPnSTDAlsFunction	TRAP-TYPE
		ENTERPRISE	pasolinkNeoStd
		VARIABLES	{
					  pnTrapSequenceNumber,
					  pnTrapDate,
					  pnTrapTime,
					  pnTrapSource,
					  eventItemPnSTDAlsFunction
					}
		DESCRIPTION "This trap is sent
					  when ALS FUNCTION status is changed."
		::= 431

	eventTrapPnSTDTxPowerContValue	TRAP-TYPE
		ENTERPRISE	pasolinkNeoStd
		VARIABLES	{
					  pnTrapSequenceNumber,
					  pnTrapDate,
					  pnTrapTime,
					  pnTrapSource,
					  eventItemPnSTDTxPowerContValue
					}
		DESCRIPTION "This trap is sent
					  when TX POWER CTRL status is changed."
		::= 432

	eventTrapPnSTDSCLanSpeedDuplex	TRAP-TYPE
		ENTERPRISE	pasolinkNeoStd
		VARIABLES	{
					  pnTrapSequenceNumber,
					  pnTrapDate,
					  pnTrapTime,
					  pnTrapSource,
					  eventItemPnSTDSCLanSpeedDuplex
					}
		DESCRIPTION "This trap is sent
					  when INTFC(2) LAN MODE PORTx(x : 1-4) status is changed."
		::= 435

	eventTrapPnSTDSWCondTxRx	TRAP-TYPE
		ENTERPRISE	pasolinkNeoStd
		VARIABLES	{
					  pnTrapSequenceNumber,
					  pnTrapDate,
					  pnTrapTime,
					  pnTrapSource,
					  eventItemPnSTDSWCondTxRx
					}
		DESCRIPTION "This trap is sent
					  when CONDITION for TX/RX SW status is changed."
		::= 436

	eventTrapPnSTDSWCondAPS	TRAP-TYPE
		ENTERPRISE	pasolinkNeoStd
		VARIABLES	{
					  pnTrapSequenceNumber,
					  pnTrapDate,
					  pnTrapTime,
					  pnTrapSource,
					  eventItemPnSTDSWCondAPS
					}
		DESCRIPTION "This trap is sent
					  when CONDITION for APS status is changed."
		::= 437

	eventTrapPnSTDRelayConfigData	TRAP-TYPE
		ENTERPRISE	pasolinkNeoStd
		VARIABLES	{
					  pnTrapSequenceNumber,
					  pnTrapDate,
					  pnTrapTime,
					  pnTrapSource,
					  eventItemPnSTDRelayConfigData
					}
		DESCRIPTION "This trap is sent
					  when RELAY CONFIGURATION CHANGED status is changed."
		::= 438

	eventTrapPnSTDRelayClusterAssign	TRAP-TYPE
		ENTERPRISE	pasolinkNeoStd
		VARIABLES	{
					  pnTrapSequenceNumber,
					  pnTrapDate,
					  pnTrapTime,
					  pnTrapSource,
					  eventItemPnSTDRelayClusterAssign
					}
		DESCRIPTION "This trap is sent
					  when CLUSTER INPUT status is changed."
		::= 439

	eventTrapPnSTDTCNTreshold15minTotal	TRAP-TYPE
		ENTERPRISE	pasolinkNeoStd
		VARIABLES	{
					  pnTrapSequenceNumber,
					  pnTrapDate,
					  pnTrapTime,
					  pnTrapSource,
					  eventItemPnSTDTCNTreshold15minTotal
					}
		DESCRIPTION "This trap is sent
					  when TCN THRESHOLD 15MIN TOTAL status is changed."
		::= 440

	eventTrapPnSTDTCNTreshold15minCH	TRAP-TYPE
		ENTERPRISE	pasolinkNeoStd
		VARIABLES	{
					  pnTrapSequenceNumber,
					  pnTrapDate,
					  pnTrapTime,
					  pnTrapSource,
					  eventItemPnSTDTCNTreshold15minCH
					}
		DESCRIPTION "This item is not used. 
					 This trap is sent
					  when TCN THRESHOLD 15MIN CH status is changed."
		::= 441

	eventTrapPnSTDTCNTreshold1dayTotal	TRAP-TYPE
		ENTERPRISE	pasolinkNeoStd
		VARIABLES	{
					  pnTrapSequenceNumber,
					  pnTrapDate,
					  pnTrapTime,
					  pnTrapSource,
					  eventItemPnSTDTCNTreshold1dayTotal
					}
		DESCRIPTION "This trap is sent
					  when TCN THRESHOLD 1DAY TOTAL status is changed."
		::= 442

	eventTrapPnSTDTCNTreshold1dayCH	TRAP-TYPE
		ENTERPRISE	pasolinkNeoStd
		VARIABLES	{
					  pnTrapSequenceNumber,
					  pnTrapDate,
					  pnTrapTime,
					  pnTrapSource,
					  eventItemPnSTDTCNTreshold1dayCH
					}
		DESCRIPTION "This item is not used. 
					 This trap is sent
					  when TCN THRESHOLD 1day CH status is changed."
		::= 443

	eventTrapPnSTDFadingDepthThreshold	TRAP-TYPE
		ENTERPRISE	pasolinkNeoStd
		VARIABLES	{
					  pnTrapSequenceNumber,
					  pnTrapDate,
					  pnTrapTime,
					  pnTrapSource,
					  eventItemPnSTDFadingDepthThreshold
					}
		DESCRIPTION "This item is not used. 
					 This trap is sent
					  when FADING STATUS THRESHOLD status is changed."
		::= 444

	eventTrapPnSTDXpicCondLOSignalFail	TRAP-TYPE
		ENTERPRISE	pasolinkNeoStd
		VARIABLES	{
					  pnTrapSequenceNumber,
					  pnTrapDate,
					  pnTrapTime,
					  pnTrapSource,
					  eventItemPnSTDXpicCondLOSignalFail
					}
		DESCRIPTION "This trap is sent
					  when XPIC CONDITION-LOCAL FAIL status is changed."
		::= 445

	eventTrapPnSTDEOWIntfcType	TRAP-TYPE
		ENTERPRISE	pasolinkNeoStd
		VARIABLES	{
					  pnTrapSequenceNumber,
					  pnTrapDate,
					  pnTrapTime,
					  pnTrapSource,
					  eventItemPnSTDEOWIntfcType
					}
		DESCRIPTION "This trap is sent
					  when EOW2 EXTERNAL SETTING status is changed."
		::= 446

	eventTrapPnSTDAlarmCorrelation	TRAP-TYPE
		ENTERPRISE	pasolinkNeoStd
		VARIABLES	{
					  pnTrapSequenceNumber,
					  pnTrapDate,
					  pnTrapTime,
					  pnTrapSource,
					  eventItemPnSTDAlarmCorrelation
					}
		DESCRIPTION "This trap is sent
					  when ALARM CORRELATION CAPABILITY status is changed."
		::= 447

	eventTrapPnSTDPmonSelect	TRAP-TYPE
		ENTERPRISE	pasolinkNeoStd
		VARIABLES	{
					  pnTrapSequenceNumber,
					  pnTrapDate,
					  pnTrapTime,
					  pnTrapSource,
					  eventItemPnSTDPmonSelect
					}
		DESCRIPTION "This trap is sent
					  when PMON SELECT status is changed."
		::= 448

	eventTrapPnSTDMaintMode	TRAP-TYPE
		ENTERPRISE	pasolinkNeoStd
		VARIABLES	{
					  pnTrapSequenceNumber,
					  pnTrapDate,
					  pnTrapTime,
					  pnTrapSource,
					  eventItemPnSTDMaintMode
					}
		DESCRIPTION "This trap is sent
					  when MAINTENANCE status is changed."
		::= 449

	eventTrapPnSTDMaintLoopback1CH	TRAP-TYPE
		ENTERPRISE	pasolinkNeoStd
		VARIABLES	{
					  pnTrapSequenceNumber,
					  pnTrapDate,
					  pnTrapTime,
					  pnTrapSource,
					  eventItemPnSTDMaintLoopback1CH
					}
		DESCRIPTION "This trap is sent
					  when MAIN CH LOOPBACK-1(CHxx)(xx:01-48) status is changed."
		::= 453

	eventTrapPnSTDMaintLoopback2CH	TRAP-TYPE
		ENTERPRISE	pasolinkNeoStd
		VARIABLES	{
					  pnTrapSequenceNumber,
					  pnTrapDate,
					  pnTrapTime,
					  pnTrapSource,
					  eventItemPnSTDMaintLoopback2CH
					}
		DESCRIPTION "This trap is sent
					  when MAIN CH LOOPBACK-2(CHxx)(xx:01-48)
					  status is changed."
		::= 454

	eventTrapPnSTDMaintLoopback1Work	TRAP-TYPE
		ENTERPRISE	pasolinkNeoStd
		VARIABLES	{
					  pnTrapSequenceNumber,
					  pnTrapDate,
					  pnTrapTime,
					  pnTrapSource,
					  eventItemPnSTDMaintLoopback1Work
					}
		DESCRIPTION "This trap is sent
					  when MAIN LOOPBACK-1 INTFC(1) status is changed."
		::= 455

	eventTrapPnSTDMaintLoopback2	TRAP-TYPE
		ENTERPRISE	pasolinkNeoStd
		VARIABLES	{
					  pnTrapSequenceNumber,
					  pnTrapDate,
					  pnTrapTime,
					  pnTrapSource,
					  eventItemPnSTDMaintLoopback2
					}
		DESCRIPTION "This trap is sent
					  when MAIN LOOPBACK-2 status is changed."
		::= 456

	eventTrapPnSTDMaintDADEAdjust	TRAP-TYPE
		ENTERPRISE	pasolinkNeoStd
		VARIABLES	{
					  pnTrapSequenceNumber,
					  pnTrapDate,
					  pnTrapTime,
					  pnTrapSource,
					  eventItemPnSTDMaintDADEAdjust
					}
		DESCRIPTION "This item is not used. 
					 This trap is sent
					  when DADE ADJUST status is changed."
		::= 457

	eventTrapPnSTDMaintDADEAdjustEn	TRAP-TYPE
		ENTERPRISE	pasolinkNeoStd
		VARIABLES	{
					  pnTrapSequenceNumber,
					  pnTrapDate,
					  pnTrapTime,
					  pnTrapSource,
					  eventItemPnSTDMaintDADEAdjustEn
					}
		DESCRIPTION "This item is not used. 
					 This trap is sent
					  when DADE ADJUST ENABLE status is changed."
		::= 458

	eventTrapPnSTDMaintLanDeviceReset	TRAP-TYPE
		ENTERPRISE	pasolinkNeoStd
		VARIABLES	{
					  pnTrapSequenceNumber,
					  pnTrapDate,
					  pnTrapTime,
					  pnTrapSource,
					  eventItemPnSTDMaintLanDeviceReset
					}
		DESCRIPTION "This item is not used. 
					 This trap is sent
					  when LAN DEVICE RESET status is changed."
		::= 459

	eventTrapPnSTDMaintAlsRestart	TRAP-TYPE
		ENTERPRISE	pasolinkNeoStd
		VARIABLES	{
					  pnTrapSequenceNumber,
					  pnTrapDate,
					  pnTrapTime,
					  pnTrapSource,
					  eventItemPnSTDMaintAlsRestart
					}
		DESCRIPTION "This item is not used. 
					 This trap is sent
					  when ALS RESTART status is changed."
		::= 460

	eventTrapPnSTDMaintAlsManualRestart	TRAP-TYPE
		ENTERPRISE	pasolinkNeoStd
		VARIABLES	{
					  pnTrapSequenceNumber,
					  pnTrapDate,
					  pnTrapTime,
					  pnTrapSource,
					  eventItemPnSTDMaintAlsManualRestart
					}
		DESCRIPTION "This item is not used. 
					 This trap is sent
					  when MANUAL RESTART status is changed."
		::= 461

	eventTrapPnSTDMaintATPCManualControl	TRAP-TYPE
		ENTERPRISE	pasolinkNeoStd
		VARIABLES	{
					  pnTrapSequenceNumber,
					  pnTrapDate,
					  pnTrapTime,
					  pnTrapSource,
					  eventItemPnSTDMaintATPCManualControl
					}
		DESCRIPTION "This trap is sent
					  when ATPC MANUAL CONTROL status is changed."
		::= 462

	eventTrapPnSTDMaintATPCManualContPower	TRAP-TYPE
		ENTERPRISE	pasolinkNeoStd
		VARIABLES	{
					  pnTrapSequenceNumber,
					  pnTrapDate,
					  pnTrapTime,
					  pnTrapSource,
					  eventItemPnSTDMaintATPCManualContPower
					}
		DESCRIPTION "This trap is sent
					  when ATPC MANUAL POWER[dB] status is changed."
		::= 463

	eventTrapPnSTDMaintTxMuteControl	TRAP-TYPE
		ENTERPRISE	pasolinkNeoStd
		VARIABLES	{
					  pnTrapSequenceNumber,
					  pnTrapDate,
					  pnTrapTime,
					  pnTrapSource,
					  eventItemPnSTDMaintTxMuteControl
					}
		DESCRIPTION "This trap is sent
					  when TX MUTE CONTROL status is changed."
		::= 464

	eventTrapPnSTDMaintTxMuteContReleaseTime	TRAP-TYPE
		ENTERPRISE	pasolinkNeoStd
		VARIABLES	{
					  pnTrapSequenceNumber,
					  pnTrapDate,
					  pnTrapTime,
					  pnTrapSource,
					  eventItemPnSTDMaintTxMuteContReleaseTime
					}
		DESCRIPTION "This trap is sent
					  when TX MUTE OFF TIMER[sec] status is changed."
		::= 465

	eventTrapPnSTDMaintCW	TRAP-TYPE
		ENTERPRISE	pasolinkNeoStd
		VARIABLES	{
					  pnTrapSequenceNumber,
					  pnTrapDate,
					  pnTrapTime,
					  pnTrapSource,
					  eventItemPnSTDMaintCW
					}
		DESCRIPTION "This trap is sent
					  when CW CONTROL status is changed."
		::= 466

	eventTrapPnSTDMaintIfLoopback	TRAP-TYPE
		ENTERPRISE	pasolinkNeoStd
		VARIABLES	{
					  pnTrapSequenceNumber,
					  pnTrapDate,
					  pnTrapTime,
					  pnTrapSource,
					  eventItemPnSTDMaintIfLoopback
					}
		DESCRIPTION "This trap is sent
					  when IF LOOPBACK status is changed."
		::= 467

	eventTrapPnSTDMaintForcedXPICCont	TRAP-TYPE
		ENTERPRISE	pasolinkNeoStd
		VARIABLES	{
					  pnTrapSequenceNumber,
					  pnTrapDate,
					  pnTrapTime,
					  pnTrapSource,
					  eventItemPnSTDMaintForcedXPICCont
					}
		DESCRIPTION "This trap is sent
					  when XPIC CONTROL status is changed."
		::= 468

	eventTrapPnSTDMaintForcedLinearizerCont	TRAP-TYPE
		ENTERPRISE	pasolinkNeoStd
		VARIABLES	{
					  pnTrapSequenceNumber,
					  pnTrapDate,
					  pnTrapTime,
					  pnTrapSource,
					  eventItemPnSTDMaintForcedLinearizerCont
					}
		DESCRIPTION "This trap is sent
					  when LINEARIZER CONTROL status is changed."
		::= 469

	eventTrapPnSTDMaintRFShiftFreqSet	TRAP-TYPE
		ENTERPRISE	pasolinkNeoStd
		VARIABLES	{
					  pnTrapSequenceNumber,
					  pnTrapDate,
					  pnTrapTime,
					  pnTrapSource,
					  eventItemPnSTDMaintRFShiftFreqSet
					}
		DESCRIPTION "This item is not used.
			     This trap is sent
					  when RF SHIFT FREQUENCY[MHz] status is changed."
		::= 471

	eventTrapPnSTDMaintAntennaAlignMode	TRAP-TYPE
		ENTERPRISE	pasolinkNeoStd
		VARIABLES	{
					  pnTrapSequenceNumber,
					  pnTrapDate,
					  pnTrapTime,
					  pnTrapSource,
					  eventItemPnSTDMaintAntennaAlignMode
					}
		DESCRIPTION "This trap is sent
					  when ANTENNA ALIGNMENT MODE status is changed."
		::= 472

	eventTrapPnSTDinvUpdateMainWorkModule	TRAP-TYPE
		ENTERPRISE	pasolinkNeoStd
		VARIABLES	{
					  pnTrapSequenceNumber,
					  pnTrapDate,
					  pnTrapTime,
					  pnTrapSource,
					  eventItemPnSTDinvUpdateMainWorkModule
					}
		DESCRIPTION "This trap is sent
					  when INTFC(1) PKG CHANGED status is changed."
		::= 473

	eventTrapPnSTDinvUpdateSubProtModule	TRAP-TYPE
		ENTERPRISE	pasolinkNeoStd
		VARIABLES	{
					  pnTrapSequenceNumber,
					  pnTrapDate,
					  pnTrapTime,
					  pnTrapSource,
					  eventItemPnSTDinvUpdateSubProtModule
					}
		DESCRIPTION "This trap is sent
					  when INTFC(2) PKG CHANGED status is changed."
		::= 474

	eventTrapPnSTDinvUpdateSummary	TRAP-TYPE
		ENTERPRISE	pasolinkNeoStd
		VARIABLES	{
					  pnTrapSequenceNumber,
					  pnTrapDate,
					  pnTrapTime,
					  pnTrapSource,
					  eventItemPnSTDinvUpdateSummary
					}
		DESCRIPTION "This trap is sent
					  when INVENTORY UPDATE INFO SUMMARY status is changed."
		::= 475

	eventTrapPnSTDLanCollision	TRAP-TYPE
		ENTERPRISE	pasolinkNeoStd
		VARIABLES	{
					  pnTrapSequenceNumber,
					  pnTrapDate,
					  pnTrapTime,
					  pnTrapSource,
					  eventItemPnSTDLanCollision
					}
		DESCRIPTION "This trap is sent
					  when LAN COLLISION PORTx(x : 1-4) status is changed."
		::= 476

	eventTrapPnSTDSCLanCollision	TRAP-TYPE
		ENTERPRISE	pasolinkNeoStd
		VARIABLES	{
					  pnTrapSequenceNumber,
					  pnTrapDate,
					  pnTrapTime,
					  pnTrapSource,
					  eventItemPnSTDSCLanCollision
					}
		DESCRIPTION "This trap is sent
					  when INTFC(2) LAN COLLISION PORTx(x : 1-2) status is changed."
		::= 477

	eventTrapPnSTDAPSStatus	TRAP-TYPE
		ENTERPRISE	pasolinkNeoStd
		VARIABLES	{
					  pnTrapSequenceNumber,
					  pnTrapDate,
					  pnTrapTime,
					  pnTrapSource,
					  eventItemPnSTDAPSStatus
					}
		DESCRIPTION "This trap is sent
					  when APS ONLINE STATUS status is changed."
		::= 478

	eventTrapPnSTDAtpcPowerModeStatus	TRAP-TYPE
		ENTERPRISE	pasolinkNeoStd
		VARIABLES	{
					  pnTrapSequenceNumber,
					  pnTrapDate,
					  pnTrapTime,
					  pnTrapSource,
					  eventItemPnSTDAtpcPowerModeStatus
					}
		DESCRIPTION "This trap is sent
					  when ATPC POWER MODE status is changed."
		::= 480

	eventTrapPnSTDAuxOutput	TRAP-TYPE
		ENTERPRISE	pasolinkNeoStd
		VARIABLES	{
					  pnTrapSequenceNumber,
					  pnTrapDate,
					  pnTrapTime,
					  pnTrapSource,
					  eventItemPnSTDAuxOutput
					}
		DESCRIPTION "This trap is sent
					  when ITEM NAME(OUTPUT-x)(x : 1-4) status is changed."
		::= 481

	eventTrapPnSTDMMCMount	TRAP-TYPE
		ENTERPRISE	pasolinkNeoStd
		VARIABLES	{
					  pnTrapSequenceNumber,
					  pnTrapDate,
					  pnTrapTime,
					  pnTrapSource,
					  eventItemPnSTDMMCMount
					}
		DESCRIPTION "This trap is sent
					  when MMC MOUNT status is changed."
		::= 482

	eventTrapPnSTDAPSLockinStatus	TRAP-TYPE
		ENTERPRISE	pasolinkNeoStd
		VARIABLES	{
					  pnTrapSequenceNumber,
					  pnTrapDate,
					  pnTrapTime,
					  pnTrapSource,
					  eventItemPnSTDAPSLockinStatus
					}
		DESCRIPTION "This trap is sent
					  when APS LOCK IN STATUS status is changed."
		::= 483

	eventTrapPnSTDMaintLoopback1Prot	TRAP-TYPE
		ENTERPRISE	pasolinkNeoStd
		VARIABLES	{
					  pnTrapSequenceNumber,
					  pnTrapDate,
					  pnTrapTime,
					  pnTrapSource,
					  eventItemPnSTDMaintLoopback1Prot
					}
		DESCRIPTION "This trap is sent
					  when MAIN LOOPBACK-1 INTFC(2) status is changed."
		::= 484

	eventTrapPnSTDMaintTxSWMode	TRAP-TYPE
		ENTERPRISE	pasolinkNeoStd
		VARIABLES	{
					  pnTrapSequenceNumber,
					  pnTrapDate,
					  pnTrapTime,
					  pnTrapSource,
					  eventItemPnSTDMaintTxSWMode
					}
		DESCRIPTION "This trap is sent
					  when TX SW MODE status is changed."
		::= 485

	eventTrapPnSTDMaintRxSWMode	TRAP-TYPE
		ENTERPRISE	pasolinkNeoStd
		VARIABLES	{
					  pnTrapSequenceNumber,
					  pnTrapDate,
					  pnTrapTime,
					  pnTrapSource,
					  eventItemPnSTDMaintRxSWMode
					}
		DESCRIPTION "This trap is sent
					  when RX SW MODE status is changed."
		::= 486

	eventTrapPnSTDMaintAPSSWMode	TRAP-TYPE
		ENTERPRISE	pasolinkNeoStd
		VARIABLES	{
					  pnTrapSequenceNumber,
					  pnTrapDate,
					  pnTrapTime,
					  pnTrapSource,
					  eventItemPnSTDMaintAPSSWMode
					}
		DESCRIPTION "This trap is sent
					  when APS SW MODE status is changed."
		::= 487

	eventTrapPnSTDGbELinkLossForward	TRAP-TYPE
		ENTERPRISE	pasolinkNeoStd
		VARIABLES	{
					  pnTrapSequenceNumber,
					  pnTrapDate,
					  pnTrapTime,
					  pnTrapSource,
					  eventItemPnSTDGbELinkLossForward
					}
		DESCRIPTION "This trap is sent
					  when GbE Link Loss Forwarding Port status is changed."
		::= 488

	eventTrapPnSTDGbESpeedDuplex	TRAP-TYPE
		ENTERPRISE	pasolinkNeoStd
		VARIABLES	{
					  pnTrapSequenceNumber,
					  pnTrapDate,
					  pnTrapTime,
					  pnTrapSource,
					  eventItemPnSTDGbESpeedDuplex
					}
		DESCRIPTION "This trap is sent
					  when GbE Speed & Duplex status is changed."
		::= 489

	eventTrapPnSTDMaintLoopback3CH	TRAP-TYPE
		ENTERPRISE	pasolinkNeoStd
		VARIABLES	{
					  pnTrapSequenceNumber,
					  pnTrapDate,
					  pnTrapTime,
					  pnTrapSource,
					  eventItemPnSTDMaintLoopback3CH
					}
		DESCRIPTION "This trap is sent
					  when Main CH Loopback-2(DIR-B)(CHxx)(xx:01-48) status is changed."
		::= 490

	statusTrapPnSTDAuxInput	TRAP-TYPE
		ENTERPRISE	pasolinkNeoStd
		VARIABLES	{
					  pnTrapSequenceNumber,
					  pnTrapDate,
					  pnTrapTime,
					  pnTrapSource,
					  pnSeverity,
					  pnAlarmType,
					  pnProbableCause,
					  pnStatusTypeAux,
					  statusItemPnSTDAuxInput
					}
		DESCRIPTION "This trap is sent
					  when ITEM NAME(INPUT-x)(x : 1-6) status is changed."
		::= 501

	systemTrapPnSTDGetResult TRAP-TYPE
		ENTERPRISE  pasolinkNeoStd
		VARIABLES   {
					  pnTrapSequenceNumber,
					  pnTrapDate,
					  pnTrapTime,
					  pngmiRequestID,
					  pngmiTargetPasolink,
					  pngmiDataStatus
					}
		::= 601


-----------------------------------------------
-- pnAlarmStatusGroup Group Definitions
-----------------------------------------------

	pnAsTrGroup OBJECT IDENTIFIER
		::= { pnAlarmStatusGroup 1 }

	pnTrSysGroupTable OBJECT-TYPE
		SYNTAX		SEQUENCE OF PnTrSysGroupEntry
		ACCESS		not-accessible
		STATUS		mandatory
		DESCRIPTION	"TR SYS Group Table"
		::= { pnAsTrGroup 1 }

	pnTrSysGroupEntry OBJECT-TYPE
		SYNTAX		PnTrSysGroupEntry
		ACCESS		not-accessible
		STATUS		mandatory
		INDEX		{
		                                pnTrGroupPasoIndex,
						pnTrGroupIndex
					}
		::= { pnTrSysGroupTable 1 }

	PnTrSysGroupEntry ::= SEQUENCE {
	                                  pnTrGroupPasoIndex IpAddress,
					  pnTrGroupIndex     INTEGER,
					  pnTxPowerAlarm     NormalAlarmValue,
					  pnTxInputAlarm     NormalAlarmValue,
					  pnRxLevelAlarm     NormalAlarmValue,
					  pnApcAlarm         NormalAlarmValue,
					  pnTruCpuAlarm      NormalAlarmValue,
					  pnTruLORefAlarm    NormalAlarmValue,
					  pnMuteStatus       OffOnValue,
					  pnTruTypeMismatch  NormalAlarmValue
					}

	pnTrGroupPasoIndex OBJECT-TYPE
		SYNTAX		IpAddress 
		ACCESS		read-only
		STATUS		mandatory
		DESCRIPTION	"Pasolink IP Address Index"
		::= { pnTrSysGroupEntry 1 }

	pnTrGroupIndex OBJECT-TYPE
		SYNTAX		INTEGER{
					  no1-dirA(1),
					  no2-dirB(2)
					}
		ACCESS		read-only
		STATUS		mandatory
		DESCRIPTION	"TR Group Index
					  1:No.1/DIR-A
					  2:No.2/DIR-B
				 No.2 is available for 1+1 system.
				 DIR-B is available 2-WAY system."
		::= { pnTrSysGroupEntry 2 }

	pnTxPowerAlarm OBJECT-TYPE
		SYNTAX		NormalAlarmValue
		ACCESS		read-only
		STATUS		mandatory
		DESCRIPTION	"TX POWER
				 Refer to NormalAlarmValue of TEXTUAL-CONVENTION
					TRAP=alarmTrapPnSTDTxPowerAlarm"
		::= { pnTrSysGroupEntry 3 }

	pnTxInputAlarm OBJECT-TYPE
		SYNTAX		NormalAlarmValue
		ACCESS		read-only
		STATUS		mandatory
		DESCRIPTION	"TX INPUT
				 Refer to NormalAlarmValue of TEXTUAL-CONVENTION
					TRAP=alarmTrapPnSTDTxInputAlarm"
		::= { pnTrSysGroupEntry 4 }

	pnRxLevelAlarm OBJECT-TYPE
		SYNTAX		NormalAlarmValue
		ACCESS		read-only
		STATUS		mandatory
		DESCRIPTION	"RX LEVEL
				  Refer to NormalAlarmValue of TEXTUAL-CONVENTION
					TRAP=alarmTrapPnSTDRxLevelAlarm"
		::= { pnTrSysGroupEntry 5 }

	pnApcAlarm OBJECT-TYPE
		SYNTAX		NormalAlarmValue
		ACCESS		read-only
		STATUS		mandatory
		DESCRIPTION	"APC
				  Refer to NormalAlarmValue of TEXTUAL-CONVENTION
					TRAP=alarmTrapPnSTDApcAlarm"
		::= { pnTrSysGroupEntry 6 }

	pnTruCpuAlarm OBJECT-TYPE
		SYNTAX		NormalAlarmValue
		ACCESS		read-only
		STATUS		mandatory
		DESCRIPTION	"ODU CPU/CABLE OPEN
				 Refer to NormalAlarmValue of TEXTUAL-CONVENTION
					TRAP=alarmTrapPnSTDTRUCPUAlarm"
		::= { pnTrSysGroupEntry 7 }

	pnTruLORefAlarm OBJECT-TYPE
		SYNTAX		NormalAlarmValue
		ACCESS		read-only
		STATUS		mandatory
		DESCRIPTION	"LO REF
				  Refer to NormalAlarmValue of TEXTUAL-CONVENTION
					TRAP=alarmTrapPnSTDTRULORefAlarm"
		::= { pnTrSysGroupEntry 8 }

	pnMuteStatus OBJECT-TYPE
		SYNTAX		OffOnValue
		ACCESS		read-only
		STATUS		mandatory
		DESCRIPTION	"MUTE STATUS
				 Refer to OffOnValue of TEXTUAL-CONVENTION
					TRAP=eventTrapPnSTDTxMuteStatus"
		::= { pnTrSysGroupEntry 9 }

	pnTruTypeMismatch OBJECT-TYPE
		SYNTAX		NormalAlarmValue
		ACCESS		read-only
		STATUS		mandatory
		DESCRIPTION	"ODU Type Mismatch
				  Refer to NormalAlarmValue of TEXTUAL-CONVENTION
					TRAP=alarmTrapPnSTDTRUTypeMismatch"
		::= { pnTrSysGroupEntry 10 }

	pnTrSysGroupComTable OBJECT-TYPE
		SYNTAX		SEQUENCE OF PnTrSysGroupComEntry
		ACCESS		not-accessible
		STATUS		mandatory
		DESCRIPTION	"TR SYS Group Table"
		::= { pnAsTrGroup 2 }

	pnTrSysGroupComEntry OBJECT-TYPE
		SYNTAX		PnTrSysGroupComEntry
		ACCESS		not-accessible
		STATUS		mandatory
		INDEX		{
		                                pnTrGroupComPasoIndex
					}
		::= { pnTrSysGroupComTable 1 }

	PnTrSysGroupComEntry ::= SEQUENCE {
	                                  pnTrGroupComPasoIndex	IpAddress,
                                          pnTxSWStatus 	INTEGER,
                                          pnRxSWStatus 	INTEGER
					}

	pnTrGroupComPasoIndex OBJECT-TYPE
		SYNTAX		IpAddress 
		ACCESS		read-only
		STATUS		mandatory
		DESCRIPTION	"Pasolink IP Address Index"
		::= { pnTrSysGroupComEntry 1 }

	pnTxSWStatus OBJECT-TYPE
		SYNTAX		INTEGER (0..2)
		ACCESS		read-only
		STATUS		mandatory
		DESCRIPTION	"TX SW STATUS
					  0:Invalid,
					  1:No.1
					  2:No.2
				 This item is available for Hot stand-by system.
					TRAP=eventTrapPnSTDTxSWStatus"
		::= { pnTrSysGroupComEntry 2 }

	pnRxSWStatus OBJECT-TYPE
		SYNTAX		INTEGER (0..2)
		ACCESS		read-only
		STATUS		mandatory
		DESCRIPTION	"RX SW STATUS
					  0:Invalid,
					  1:No.1
					  2:No.2
				 This item is available for 1+1 system.
					TRAP=eventTrapPnSTDRxSWStatus"
		::= { pnTrSysGroupComEntry 3 }

	pnAsModemGroup OBJECT IDENTIFIER
		::= { pnAlarmStatusGroup 2 }

	pnModemSysGroupTable OBJECT-TYPE
		SYNTAX		SEQUENCE OF PnModemSysGroupEntry
		ACCESS		not-accessible
		STATUS		mandatory
		DESCRIPTION	"Modem Sys Group Table"
		::= { pnAsModemGroup 1 }

	pnModemSysGroupEntry OBJECT-TYPE
		SYNTAX		PnModemSysGroupEntry
		ACCESS		not-accessible
		STATUS		mandatory
		INDEX		{
                                                pnTrGroupComPasoIndex,
						pnModemSyGroupIndex
					}
		::= { pnModemSysGroupTable 1 }

	PnModemSysGroupEntry ::= SEQUENCE {
	                                  pnModemSysGroupPasoIndex	IpAddress,
					  pnModemSyGroupIndex    INTEGER,
					  pnModemAlarm           NormalAlarmValue,
					  pnModemUnequipped      NormalAlarmValue,
					  pnHighBERAlarm         NormalAlarmValue,
					  pnLowBERAlarm          NormalAlarmValue,
					  pnModAlarm             NormalAlarmValue,
					  pnDemAlarm             NormalAlarmValue,
					  pnXIFLevelAlarm        NormalAlarmValue,
					  pnXControlAlarm        NormalAlarmValue,
					  pnXpicFuncStatus       OffOnValue,
					  pnPowerSupplyAlarm     NormalAlarmValue,
					  pnIfCableShortAlarm    NormalAlarmValue,
					  pnLof                  NormalAlarmValue,
					  pnLinearizerFunc       INTEGER,
					  pnCableEQLAlarm        NormalAlarmValue,
					  pnFadingDepthStatus    INTEGER,
					  pnXRefAlarm            NormalAlarmValue,
					  pnLinearizerFail       NormalAlarmValue,
					  pnRouteId              NormalAlarmValue,
					  pnEarlyWarning         NormalAlarmValue,
					  pnAtpcPowerModeStatus  INTEGER,
					  pnInputVoltageAlarm	 INTEGER,
					  pnModemTypeMismatch	 NormalAlarmValue
					}

	pnModemSysGroupPasoIndex OBJECT-TYPE
		SYNTAX		IpAddress 
		ACCESS		read-only
		STATUS		mandatory
		DESCRIPTION	"Pasolink IP Address Index"
		::= { pnModemSysGroupEntry 1 }

	pnModemSyGroupIndex OBJECT-TYPE
		SYNTAX		INTEGER{
					  no1-dirA(1),
					  no2-dirB(2)
					}
		ACCESS		not-accessible
		STATUS		mandatory
		DESCRIPTION	"Modem Group Index
					  1:No.1/DIR-A
					  2:No.2/DIR-B
				 No.2 is available for 1+1 system.
				 DIR-B is available 2-WAY system."
		::= { pnModemSysGroupEntry 2 }

	pnModemAlarm OBJECT-TYPE
		SYNTAX		NormalAlarmValue
		ACCESS		read-only
		STATUS		mandatory
		DESCRIPTION	"MODEM MODULE
				 Refer to NormalAlarmValue of TEXTUAL-CONVENTION
					TRAP=alarmTrapPnSTDModemAlarm"
		::= { pnModemSysGroupEntry 3 }

	pnModemUnequipped OBJECT-TYPE
		SYNTAX		NormalAlarmValue
		ACCESS		read-only
		STATUS		mandatory
		DESCRIPTION	"MODEM UNEQUIPPED
				 Refer to NormalAlarmValue of TEXTUAL-CONVENTION
					TRAP=alarmTrapPnSTDModemUneq"
		::= { pnModemSysGroupEntry 4 }

	pnHighBERAlarm OBJECT-TYPE
		SYNTAX		NormalAlarmValue
		ACCESS		read-only
		STATUS		mandatory
		DESCRIPTION	"HIGH BER
				 Refer to NormalAlarmValue of TEXTUAL-CONVENTION
					TRAP=alarmTrapPnSTDHighBERAlarm"
		::= { pnModemSysGroupEntry 5 }

	pnLowBERAlarm OBJECT-TYPE
		SYNTAX		NormalAlarmValue
		ACCESS		read-only
		STATUS		mandatory
		DESCRIPTION	"LOW BER
				 Refer to NormalAlarmValue of TEXTUAL-CONVENTION
					TRAP=alarmTrapPnSTDLowBERAlarm"
		::= { pnModemSysGroupEntry 6 }

	pnModAlarm OBJECT-TYPE
		SYNTAX		NormalAlarmValue
		ACCESS		read-only
		STATUS		mandatory
		DESCRIPTION	"MOD
				 Refer to NormalAlarmValue of TEXTUAL-CONVENTION
					TRAP=alarmTrapPnSTDModAlarm"
		::= { pnModemSysGroupEntry 7 }

	pnDemAlarm OBJECT-TYPE
		SYNTAX		NormalAlarmValue
		ACCESS		read-only
		STATUS		mandatory
		DESCRIPTION	"DEM
				 Refer to NormalAlarmValue of TEXTUAL-CONVENTION
					TRAP=alarmTrapPnSTDDemAlarm"
		::= { pnModemSysGroupEntry 8 }

	pnXIFLevelAlarm OBJECT-TYPE
		SYNTAX		NormalAlarmValue
		ACCESS		read-only
		STATUS		mandatory
		DESCRIPTION	"XIF
				 Refer to NormalAlarmValue of TEXTUAL-CONVENTION
				 This item is available for XPIC system.
					TRAP=alarmTrapPnSTDXIfLevelAlarm"
		::= { pnModemSysGroupEntry 9 }

	pnXControlAlarm OBJECT-TYPE
		SYNTAX		NormalAlarmValue
		ACCESS		read-only
		STATUS		mandatory
		DESCRIPTION	"This item is not used.
		 			TRAP=alarmTrapPnSTDXContAlarm
					*)This value is fixed to 0."
		::= { pnModemSysGroupEntry 10 }

	pnXpicFuncStatus OBJECT-TYPE
		SYNTAX		INTEGER (0..2)
		ACCESS		read-only
		STATUS		mandatory
		DESCRIPTION	"XPIC STATUS
					  0:Invalid,
					  1:Normal,
					  2:Reset
				 This item is available for XPIC system.
					TRAP=eventTrapPnSTDXPICFuncStatus"
		::= { pnModemSysGroupEntry 11 }

	pnPowerSupplyAlarm OBJECT-TYPE
		SYNTAX		NormalAlarmValue
		ACCESS		read-only
		STATUS		mandatory
		DESCRIPTION	"POWER SUPPLY
				 Refer to NormalAlarmValue of TEXTUAL-CONVENTION
					TRAP=alarmTrapPnSTDPSAlarm"
		::= { pnModemSysGroupEntry 12 }

	pnIfCableShortAlarm OBJECT-TYPE
		SYNTAX		NormalAlarmValue
		ACCESS		read-only
		STATUS		mandatory
		DESCRIPTION	"IF CABLE SHORT
				 Refer to NormalAlarmValue of TEXTUAL-CONVENTION
					TRAP=alarmTrapPnSTDIfCableShort"
		::= { pnModemSysGroupEntry 13 }

	pnLof OBJECT-TYPE
		SYNTAX		NormalAlarmValue
		ACCESS		read-only
		STATUS		mandatory
		DESCRIPTION	"LOF
				 Refer to NormalAlarmValue of TEXTUAL-CONVENTION
					TRAP=alarmTrapPnSTDLof"
		::= { pnModemSysGroupEntry 14 }

	pnLinearizerFunc OBJECT-TYPE
		SYNTAX		INTEGER (0..3)
		ACCESS		read-only
		STATUS		mandatory
		DESCRIPTION	"LINEARIZER FUNCTION
					  0:Invalid,
					  1:N/A,
					  2:NON Operation,
					  3:Operation
					TRAP=eventTrapPnSTDLinearizerFunc"
		::= { pnModemSysGroupEntry 15 }

	pnCableEQLAlarm OBJECT-TYPE
		SYNTAX		NormalAlarmValue
		ACCESS		read-only
		STATUS		mandatory
		DESCRIPTION	"CABLE EQL
				 Refer to NormalAlarmValue of TEXTUAL-CONVENTION
					TRAP=alarmTrapPnSTDCableEQLAlarm"
		::= { pnModemSysGroupEntry 16 }

	pnFadingDepthStatus OBJECT-TYPE
		SYNTAX		INTEGER(0..2)
		ACCESS		read-only
		STATUS		mandatory
		DESCRIPTION	"FADING STATUS
					  0:Invalid,
					  1:Normal,
					  2:Occured
					TRAP=eventTrapPnSTDFadeDepthStatus"
		::= { pnModemSysGroupEntry 17 }

	pnXRefAlarm OBJECT-TYPE
		SYNTAX		NormalAlarmValue
		ACCESS		read-only
		STATUS		mandatory
		DESCRIPTION	"XREF
				 Refer to NormalAlarmValue of TEXTUAL-CONVENTION
				 This item is available for XPIC system.
					TRAP=alarmTrapPnSTDXRefAlarm"
		::= { pnModemSysGroupEntry 18 }

	pnLinearizerFail OBJECT-TYPE
		SYNTAX		NormalAlarmValue
		ACCESS		read-only
		STATUS		mandatory
		DESCRIPTION	"LINEARIZER
				 Refer to NormalAlarmValue of TEXTUAL-CONVENTION
					TRAP=alarmTrapPnSTDLinearizerFail"
		::= { pnModemSysGroupEntry 19 }

	pnRouteId OBJECT-TYPE
		SYNTAX		NormalAlarmValue
		ACCESS		read-only
		STATUS		mandatory
		DESCRIPTION	"FRAME ID
				 Refer to NormalAlarmValue of TEXTUAL-CONVENTION
					TRAP=alarmTrapPnSTDRouteID"
		::= { pnModemSysGroupEntry 20 }

	pnEarlyWarning OBJECT-TYPE
		SYNTAX		NormalAlarmValue
		ACCESS		read-only
		STATUS		mandatory
		DESCRIPTION	"EARLY WARNING
				 Refer to NormalAlarmValue of TEXTUAL-CONVENTION
					TRAP=alarmTrapPnSTDEarlyWarning"
		::= { pnModemSysGroupEntry 21 }

	pnAtpcPowerModeStatus OBJECT-TYPE
		SYNTAX		INTEGER(0..2)
		ACCESS		read-only
		STATUS		mandatory
		DESCRIPTION	"ATPC POWER MODE
					  0:Invalid,
					  1:Active,
					  2:Stop
					TRAP=eventTrapPnSTDAtpcPowerModeStatus"
		::= { pnModemSysGroupEntry 22 }

	pnInputVoltageAlarm OBJECT-TYPE
		SYNTAX		NormalAlarmValue
		ACCESS		read-only
		STATUS		mandatory
		DESCRIPTION	"INPUT VOLTAGE
				 Refer to NormalAlarmValue of TEXTUAL-CONVENTION
					TRAP=alarmTrapPnSTDInputVoltage"
		::= { pnModemSysGroupEntry 23 }

	pnModemTypeMismatch OBJECT-TYPE
		SYNTAX		NormalAlarmValue
		ACCESS		read-only
		STATUS		mandatory
		DESCRIPTION	"MODEM TYPE MISMATCH
				 Refer to NormalAlarmValue of TEXTUAL-CONVENTION
					TRAP=alarmTrapPnSTDModemTypeMismatch"
		::= { pnModemSysGroupEntry 24 }

	pnAsIntfcMainWorkGroup OBJECT IDENTIFIER
		::= { pnAlarmStatusGroup 3 }

	pnAsIntfcMainWorkGroupTable OBJECT-TYPE
		SYNTAX		SEQUENCE OF PnAsIntfcMainWorkGroupEntry
		ACCESS		not-accessible
		STATUS		mandatory
		DESCRIPTION	"INTFC Main Work Group"
		::= { pnAsIntfcMainWorkGroup 1 }

	pnAsIntfcMainWorkGroupEntry OBJECT-TYPE
		SYNTAX		PnAsIntfcMainWorkGroupEntry
		ACCESS		not-accessible
		STATUS		mandatory
		INDEX		{
                                                pnAsIntfcMainWorkPasoIndex
					}
		::= { pnAsIntfcMainWorkGroupTable 1 }

	PnAsIntfcMainWorkGroupEntry ::= SEQUENCE {
	                                  pnAsIntfcMainWorkPasoIndex	IpAddress,
					  pnIntfcMAlarm	NormalAlarmValue,
					  pnIntfcMUnequipped	NormalAlarmValue,
					  pnInputLoss	OCTET STRING,
					  pnLosMUXWork	NormalAlarmValue,
					  pnLosDMRWork	NormalAlarmValue,	
					  pnLofMUXWork	NormalAlarmValue,
					  pnLofDMRWork	NormalAlarmValue,
					  pnStm1OutContWork	INTEGER,
					  pnUsageError	OCTET STRING,
					  pnAisGeneratedCH	OCTET STRING,
					  pnAisReceivedCH	OCTET STRING,
					  pnEBERMUXWork	NormalAlarmValue,
					  pnEBERDMRWork	NormalAlarmValue,
					  pnSignalDegradeMUXWork	NormalAlarmValue,
					  pnSignalDegradeDMRWork	NormalAlarmValue,
					  pnInPhaseWork	NormalAlarmValue,
					  pnStm1TFWorkAlarm	NormalAlarmValue,
					  pnIntfcMTypeMismatch NormalAlarmValue,
					  pnGbELink NormalAlarmValue,
					  pnGbELinkLossForwarding	INTEGER,
					  pnGbESpeedDuplex OCTET STRING
					}

	pnAsIntfcMainWorkPasoIndex OBJECT-TYPE
		SYNTAX		IpAddress 
		ACCESS		read-only
		STATUS		mandatory
		DESCRIPTION	"Pasolink IP Address Index"
		::= { pnAsIntfcMainWorkGroupEntry 1 }

	pnIntfcMAlarm OBJECT-TYPE
		SYNTAX		NormalAlarmValue
		ACCESS		read-only
		STATUS		mandatory
		DESCRIPTION	"INTFC(1) MODULE
				 Refer to NormalAlarmValue of TEXTUAL-CONVENTION
					TRAP=alarmTrapPnSTDIntfcMAlarm"
		::= { pnAsIntfcMainWorkGroupEntry 2 }

	pnIntfcMUnequipped OBJECT-TYPE
		SYNTAX		NormalAlarmValue
		ACCESS		read-only
		STATUS		mandatory
		DESCRIPTION	"INTFC(1) UNEQUIPPED
				 Refer to NormalAlarmValue of TEXTUAL-CONVENTION
					TRAP=alarmTrapPnSTDIntfcMUneq"
		::= { pnAsIntfcMainWorkGroupEntry 3 }

	pnInputLoss OBJECT-TYPE
		SYNTAX		OCTET STRING (SIZE (6))
		ACCESS		read-only
		STATUS		mandatory
		DESCRIPTION	"INPUT LOS CHxx
					(xx : 1-48)
					  0:Normal,
					  1:Alarm
					
					 [Bit Description]
					  Bit0 = CH01 (0: Normal,1: Alarm)
					  Bit1 = CH02
					  Bit2 = CH02
					  ...
					  Bit46 = CH47
					  Bit47 = CH48
					TRAP=alarmTrapPnSTDInputLos"
		::= { pnAsIntfcMainWorkGroupEntry 4 }

	pnLosMUXWork OBJECT-TYPE
		SYNTAX		NormalAlarmValue
		ACCESS		read-only
		STATUS		mandatory
		DESCRIPTION	"STM-1(1) LOS(MUX)
				 Refer to NormalAlarmValue of TEXTUAL-CONVENTION
					TRAP=alarmTrapPnSTDLosMUXWork"
		::= { pnAsIntfcMainWorkGroupEntry 5 }

	pnLosDMRWork OBJECT-TYPE
		SYNTAX		NormalAlarmValue
		ACCESS		read-only
		STATUS		mandatory
		DESCRIPTION	"STM-1(1) LOS(DMR)
				 Refer to NormalAlarmValue of TEXTUAL-CONVENTION
					TRAP=alarmTrapPnSTDLosDMRWork"
		::= { pnAsIntfcMainWorkGroupEntry 6 }

	pnLofMUXWork OBJECT-TYPE
		SYNTAX		NormalAlarmValue
		ACCESS		read-only
		STATUS		mandatory
		DESCRIPTION	"STM-1(1) LOF(MUX)
				 Refer to NormalAlarmValue of TEXTUAL-CONVENTION
					TRAP=alarmTrapPnSTDLofMUXWork"
		::= { pnAsIntfcMainWorkGroupEntry 7 }

	pnLofDMRWork OBJECT-TYPE
		SYNTAX		NormalAlarmValue
		ACCESS		read-only
		STATUS		mandatory
		DESCRIPTION	"STM-1(1) LOF(DMR)
				 Refer to NormalAlarmValue of TEXTUAL-CONVENTION
					TRAP=alarmTrapPnSTDLofDMRWork"
		::= { pnAsIntfcMainWorkGroupEntry 8 }

	pnStm1OutContWork OBJECT-TYPE
		SYNTAX		INTEGER(0..2)
		ACCESS		read-only
		STATUS		mandatory
		DESCRIPTION	"STM-1(1) OUTPUT CONTROL
					  0:Invalid,
					  1:Normal,
					  2:Under Execution
					TRAP=eventTrapPnSTDSTM1OutContWork"
		::= { pnAsIntfcMainWorkGroupEntry 9 }

	pnUsageError OBJECT-TYPE
		SYNTAX		OCTET STRING (SIZE (6))
		ACCESS		read-only
		STATUS		mandatory
		DESCRIPTION	"USAGE ERROR CHxx
					(xx : 1-48)
					  0:Normal,
					  1:Alarm
					
					 [Bit Description]
					  Bit0 = CH01 (0: Normal,1: Alarm)
					  Bit1 = CH02
					  Bit2 = CH02
					  ...
					  Bit46 = CH47
					  Bit47 = CH48
					TRAP=alarmTrapPnSTDUsageError"
		::= { pnAsIntfcMainWorkGroupEntry 10 }

	pnAisGeneratedCH OBJECT-TYPE
		SYNTAX		OCTET STRING (SIZE (6))
		ACCESS		read-only
		STATUS		mandatory
		DESCRIPTION	"AIS GENERATED CHxx
					(xx : 1-48)
					  0:Normal,
					  1:Generated
					
					 [Bit Description]
					  Bit0 = CH01 (0: Normal,1: Generated)
					  Bit1 = CH02
					  Bit2 = CH02
					  ...
					  Bit46 = CH47
					  Bit47 = CH48
					TRAP=eventTrapPnSTDAisGeneratedCH"
		::= { pnAsIntfcMainWorkGroupEntry 11 }

	pnAisReceivedCH OBJECT-TYPE
		SYNTAX		OCTET STRING (SIZE (6))
		ACCESS		read-only
		STATUS		mandatory
		DESCRIPTION	"AIS RECEIVED CHxx
					(xx : 1-48)
					  0:Normal,
					  1:Received
					
					 [Bit Description]
					  Bit0 = CH01 (0: Normal,1: Received)
					  Bit1 = CH02
					  Bit2 = CH02
					  ...
					  Bit46 = CH47
					  Bit47 = CH48
					TRAP=eventTrapPnSTDAisReceivedCH"
		::= { pnAsIntfcMainWorkGroupEntry 12 }

	pnEBERMUXWork OBJECT-TYPE
		SYNTAX		NormalAlarmValue
		ACCESS		read-only
		STATUS		mandatory
		DESCRIPTION	"STM-1(1) E-BER(MUX)
				 Refer to NormalAlarmValue of TEXTUAL-CONVENTION
					TRAP=alarmTrapPnSTDEBERMUXWork"
		::= { pnAsIntfcMainWorkGroupEntry 13 }

	pnEBERDMRWork OBJECT-TYPE
		SYNTAX		NormalAlarmValue
		ACCESS		read-only
		STATUS		mandatory
		DESCRIPTION	"STM-1(1) E-BER(DMR)
				 Refer to NormalAlarmValue of TEXTUAL-CONVENTION
					TRAP=alarmTrapPnSTDEBERDMRWork"
		::= { pnAsIntfcMainWorkGroupEntry 14 }

	pnSignalDegradeMUXWork OBJECT-TYPE
		SYNTAX		NormalAlarmValue
		ACCESS		read-only
		STATUS		mandatory
		DESCRIPTION	"STM-1(1) SD(MUX)
				 Refer to NormalAlarmValue of TEXTUAL-CONVENTION
					TRAP=alarmTrapPnSTDSDMUXWork"
		::= { pnAsIntfcMainWorkGroupEntry 15 }

	pnSignalDegradeDMRWork OBJECT-TYPE
		SYNTAX		NormalAlarmValue
		ACCESS		read-only
		STATUS		mandatory
		DESCRIPTION	"STM-1(1) SD(DMR)
				 Refer to NormalAlarmValue of TEXTUAL-CONVENTION
					TRAP=alarmTrapPnSTDSDDMRWork"
		::= { pnAsIntfcMainWorkGroupEntry 16 }

	pnInPhaseWork OBJECT-TYPE
		SYNTAX		INTEGER(0..1)
		ACCESS		read-only
		STATUS		mandatory
		DESCRIPTION	"INTFC(1) INPHASE
					  0:Invalid,
					  1:OUTPHASE,
					  2:INPHASE
					TRAP=eventTrapPnSTDInphaseWork"
		::= { pnAsIntfcMainWorkGroupEntry 17 }

	pnStm1TFWorkAlarm OBJECT-TYPE
		SYNTAX		NormalAlarmValue
		ACCESS		read-only
		STATUS		mandatory
		DESCRIPTION	"STM-1(1) TF
				 Refer to NormalAlarmValue of TEXTUAL-CONVENTION
					TRAP=alarmTrapPnSTDStm1TFWorkAlarm"
		::= { pnAsIntfcMainWorkGroupEntry 18 }

	pnIntfcMTypeMismatch OBJECT-TYPE
		SYNTAX		NormalAlarmValue
		ACCESS		read-only
		STATUS		mandatory
		DESCRIPTION	"INTFC(1) TYPE MISMATCH
				 Refer to NormalAlarmValue of TEXTUAL-CONVENTION
					TRAP=alarmTrapPnSTDIntfcMTypeMismatch"
		::= { pnAsIntfcMainWorkGroupEntry 19 }

	pnGbELink OBJECT-TYPE
		SYNTAX		NormalAlarmValue
		ACCESS		read-only
		STATUS		mandatory
		DESCRIPTION	"GbE LAN Link Port
				 Refer to NormalAlarmValue of TEXTUAL-CONVENTION
					TRAP=alarmTrapPnSTDGbELink"
		::= { pnAsIntfcMainWorkGroupEntry 20 }

	pnGbELinkLossForwarding OBJECT-TYPE
		SYNTAX		INTEGER (0..2)
		ACCESS		read-only
		STATUS		mandatory
		DESCRIPTION	"GbE Link Loss Forwarding Port
					  0:Invalid,
					  1:Normal,
					  2:Under Execution
					TRAP=eventTrapPnSTDGbELinkLossForward"
		::= { pnAsIntfcMainWorkGroupEntry 21 }

	pnGbESpeedDuplex OBJECT-TYPE
		SYNTAX		OCTET STRING (SIZE (1))
		ACCESS		read-only
		STATUS		mandatory
		DESCRIPTION	"GbE Speed & Duplex

					 [Description]
					 Bit 0 = MASTER/SLAVE (0:SLAVE, 1:MASTER)
					 Bit 1 = FULL DUPLEX (0:HALF, 1:FULL)
					 Bit 2 = FORCED SETTING MODE (0:AUTONEGO, 1:FORCED)
					 Bit 3 = MDIX (0:MDI, 1:MDIX)
					 Bit 4, 5 = SPEED (00:10M, 01:100M, 10:1000M, 11:1000M-INI)
					TRAP=eventTrapPnSTDGbESpeedDuplex"
		::= { pnAsIntfcMainWorkGroupEntry 22 }

	pnLanStatusTable OBJECT-TYPE
		SYNTAX		SEQUENCE OF PnLanStatusEntry
		ACCESS		not-accessible
		STATUS		mandatory
		DESCRIPTION	"LAN Status Table"
		::= { pnAsIntfcMainWorkGroup 2 }

	pnLanStatusEntry OBJECT-TYPE
		SYNTAX		PnLanStatusEntry
		ACCESS		not-accessible
		STATUS		mandatory
		INDEX		{
		                pnLanstatusPasoIndex,                 
						pnLanStatusIndex
					}
		::= { pnLanStatusTable 1 }

	PnLanStatusEntry ::= SEQUENCE {
	                  pnLanstatusPasoIndex	IpAddress,
					  pnLanStatusIndex      INTEGER,
					  pnLink                INTEGER,
					  pnCollision           INTEGER,
					  pnLinkLossForwarding  INTEGER,
					  pnSpeedDuplex         INTEGER
					}

	pnLanstatusPasoIndex OBJECT-TYPE
		SYNTAX		IpAddress 
		ACCESS		read-only
		STATUS		mandatory
		DESCRIPTION	"Pasolink IP Address Index"
		::= { pnLanStatusEntry 1 }

	pnLanStatusIndex OBJECT-TYPE
		SYNTAX		INTEGER{
					  port1(1),
					  port2(2),
					  port3(3),
					  port4(4)
					}
		ACCESS		read-only
		STATUS		mandatory
		DESCRIPTION	"PORTx(x:1-4) Index
					  1: Port 1
					  2: Port 2
					  3: Port 3
					  4: Port 4"
		::= { pnLanStatusEntry 2 }

	pnLink OBJECT-TYPE
		SYNTAX		INTEGER(0..2)
		ACCESS		read-only
		STATUS		mandatory
		DESCRIPTION	"LAN LINK PORTx
					(x : 1-4)
					  0:Invalid,
					  1:Normal,
					  2:Alarm
					TRAP=alarmTrapPnSTDLink"
		::= { pnLanStatusEntry 3 }

	pnCollision OBJECT-TYPE
		SYNTAX		INTEGER(0..2)
		ACCESS		read-only
		STATUS		mandatory
		DESCRIPTION	"LAN COLLISION PORTx
					(x : 1-4)
					  0:Invalid,
					  1:Normal,
					  2:Collision
					TRAP=eventTrapPnSTDLanCollision"
		::= { pnLanStatusEntry 4 }

	pnLinkLossForwarding OBJECT-TYPE
		SYNTAX		INTEGER(0..2)
		ACCESS		read-only
		STATUS		mandatory
		DESCRIPTION	"LLF PORTx
					(x : 1-4)
					  0:Invalid,
					  1:Normal,
					  2:Under Execution
					TRAP=eventTrapPnSTDLinkLossForward"
		::= { pnLanStatusEntry 5 }

	pnSpeedDuplex OBJECT-TYPE
		SYNTAX		INTEGER(0..8)
		ACCESS		read-only
		STATUS		mandatory
		DESCRIPTION	"LAN MODE PORTx
					(x : 1-4)
				 Speed & Duplex
					  0:INVALID,
					  1:10M-HALF(MDI),
					  2:10M-FULL(MDI),
					  3:100M-HALF(MDI),
					  4:100M-FULL(MDI),
					  5:10M-HALF(MDIX),
					  6:10M-FULL(MDIX),
					  7:100M-HALF(MDIX),
					  8:100M-FULL(MDIX)
					TRAP=eventTrapPnSTDSpeedDuplex"
		::= { pnLanStatusEntry 6 }

	pnAsIntfcSubProtGroup OBJECT IDENTIFIER
		::= { pnAlarmStatusGroup 4 }

	pnAsIntfcSubProtTable OBJECT-TYPE
		SYNTAX		SEQUENCE OF PnAsIntfcSubProtEntry
		ACCESS		not-accessible
		STATUS		mandatory
		DESCRIPTION	"Intfc Sub Prot Table"
		::= { pnAsIntfcSubProtGroup 1 }

	pnAsIntfcSubProtEntry OBJECT-TYPE
		SYNTAX		PnAsIntfcSubProtEntry
		ACCESS		not-accessible
		STATUS		mandatory
		INDEX		{
		                                pnAsIntfcSubProtPasoIndex 
					}
		::= { pnAsIntfcSubProtTable 1 }

	PnAsIntfcSubProtEntry ::= SEQUENCE {
					  pnAsIntfcSubProtPasoIndex	IpAddress,
					  pnIntfcSAlarm	NormalAlarmValue,
					  pnIntfcSUnequipped	NormalAlarmValue,
					  pnLosMUXProt	NormalAlarmValue,
					  pnLosDMRProt	NormalAlarmValue,
					  pnEBERMUXProt	NormalAlarmValue,
					  pnEBERDMRProt	NormalAlarmValue,
					  pnSignalDegradeMUXProt	NormalAlarmValue,
					  pnSignalDegradeDMRProt	NormalAlarmValue,
					  pnStm1OutContProt	INTEGER,
					  pnInPhaseProt	INTEGER,
					  pnWsLos	NormalAlarmValue,
					  pnWsAisReceived	INTEGER,
					  pnWsAisGenerated	INTEGER,
					  pnLofMUXProt	NormalAlarmValue,
					  pnLofDMRProt	NormalAlarmValue,
					  pnStm1TFProtAlarm	NormalAlarmValue,
					  pnIntfcSTypeMismatch	NormalAlarmValue
					}

	pnAsIntfcSubProtPasoIndex OBJECT-TYPE
		SYNTAX		IpAddress 
		ACCESS		read-only
		STATUS		mandatory
		DESCRIPTION	"Pasolink IP Address Index"
		::= { pnAsIntfcSubProtEntry 1 }

	pnIntfcSAlarm OBJECT-TYPE
		SYNTAX		NormalAlarmValue
		ACCESS		read-only
		STATUS		mandatory
		DESCRIPTION	"INTFC(2) MODULE
				 Refer to NormalAlarmValue of TEXTUAL-CONVENTION
					TRAP=alarmTrapPnSTDIntfcSAlarm"
		::= { pnAsIntfcSubProtEntry 2 }

	pnIntfcSUnequipped OBJECT-TYPE
		SYNTAX		NormalAlarmValue
		ACCESS		read-only
		STATUS		mandatory
		DESCRIPTION	"INTFC(2) UNEQUIPPED
				 Refer to NormalAlarmValue of TEXTUAL-CONVENTION
					TRAP=alarmTrapPnSTDIntfcSUneq"
		::= { pnAsIntfcSubProtEntry 3 }

	pnLosMUXProt OBJECT-TYPE
		SYNTAX		NormalAlarmValue
		ACCESS		read-only
		STATUS		mandatory
		DESCRIPTION	"STM-1(2) LOS(MUX)
				 Refer to NormalAlarmValue of TEXTUAL-CONVENTION
					TRAP=alarmTrapPnSTDLosMUXProt"
		::= { pnAsIntfcSubProtEntry 4 }

	pnLosDMRProt OBJECT-TYPE
		SYNTAX		NormalAlarmValue
		ACCESS		read-only
		STATUS		mandatory
		DESCRIPTION	"STM-1(2) LOS(DMR)
				 Refer to NormalAlarmValue of TEXTUAL-CONVENTION
					TRAP=alarmTrapPnSTDLosDMRProt"
		::= { pnAsIntfcSubProtEntry 5 }

	pnEBERMUXProt OBJECT-TYPE
		SYNTAX		NormalAlarmValue
		ACCESS		read-only
		STATUS		mandatory
		DESCRIPTION	"STM-1(2) E-BER(MUX)
				 Refer to NormalAlarmValue of TEXTUAL-CONVENTION
					TRAP=alarmTrapPnSTDEBERMUXProt"
		::= { pnAsIntfcSubProtEntry 6 }

	pnEBERDMRProt OBJECT-TYPE
		SYNTAX		NormalAlarmValue
		ACCESS		read-only
		STATUS		mandatory
		DESCRIPTION	"STM-1(2) E-BER(DMR)
				 Refer to NormalAlarmValue of TEXTUAL-CONVENTION
					TRAP=alarmTrapPnSTDEBERDMRProt"
		::= { pnAsIntfcSubProtEntry 7 }

	pnSignalDegradeMUXProt OBJECT-TYPE
		SYNTAX		NormalAlarmValue
		ACCESS		read-only
		STATUS		mandatory
		DESCRIPTION	"STM-1(2) SD(MUX)
				 Refer to NormalAlarmValue of TEXTUAL-CONVENTION
					TRAP=alarmTrapPnSTDSDMUXProt"
		::= { pnAsIntfcSubProtEntry 8 }

	pnSignalDegradeDMRProt OBJECT-TYPE
		SYNTAX		NormalAlarmValue
		ACCESS		read-only
		STATUS		mandatory
		DESCRIPTION	"STM-1(2) SD(DMR)
				 Refer to NormalAlarmValue of TEXTUAL-CONVENTION
					TRAP=alarmTrapPnSTDSDDMRProt"
		::= { pnAsIntfcSubProtEntry 9 }

	pnStm1OutContProt OBJECT-TYPE
		SYNTAX		INTEGER(0..2)
		ACCESS		read-only
		STATUS		mandatory
		DESCRIPTION	"STM-1(2) OUTPUT CONTROL
					  0:Invalid,
					  1:Normal,
					  2:Under Execution
					TRAP=eventTrapPnSTDSTM1OutContProt"
		::= { pnAsIntfcSubProtEntry 10 }

	pnInPhaseProt OBJECT-TYPE
		SYNTAX		INTEGER(0..2)
		ACCESS		read-only
		STATUS		mandatory
		DESCRIPTION	"INTFC(2) INPHASE
					  0:Invalid,
					  1:OUTPHASE,
					  2:INPHASE
					TRAP=eventTrapPnSTDInphaseProt"
		::= { pnAsIntfcSubProtEntry 11 }

	pnWsLos OBJECT-TYPE
		SYNTAX		NormalAlarmValue
		ACCESS		read-only
		STATUS		mandatory
		DESCRIPTION	"WS INPUT LOS
				 Refer to NormalAlarmValue of TEXTUAL-CONVENTION
					TRAP=alarmTrapPnSTDWSLos"
		::= { pnAsIntfcSubProtEntry 12 }

	pnWsAisReceived OBJECT-TYPE
		SYNTAX		INTEGER(0..2)
		ACCESS		read-only
		STATUS		mandatory
		DESCRIPTION	"WS AIS RECEIVED
					  0:Invalid,
					  1:Normal,
					  2:Recieved
					TRAP=eventTrapPnSTDWSAisReceivedCH"
		::= { pnAsIntfcSubProtEntry 13 }

	pnWsAisGenerated OBJECT-TYPE
		SYNTAX		INTEGER(0..2)
		ACCESS		read-only
		STATUS		mandatory
		DESCRIPTION	"WS AIS GENERATED
					  0:Invalid,
					  1:Normal,
					  2:Generated
					TRAP=eventTrapPnSTDWSAisGeneratedCH"
		::= { pnAsIntfcSubProtEntry 14 }

	pnLofMUXProt OBJECT-TYPE
		SYNTAX		NormalAlarmValue
		ACCESS		read-only
		STATUS		mandatory
		DESCRIPTION	"STM-1(2) LOF(MUX)
				 Refer to NormalAlarmValue of TEXTUAL-CONVENTION
					TRAP=alarmTrapPnSTDLofMUXProt"
		::= { pnAsIntfcSubProtEntry 15 }

	pnLofDMRProt OBJECT-TYPE
		SYNTAX		NormalAlarmValue
		ACCESS		read-only
		STATUS		mandatory
		DESCRIPTION	"STM-1(2) LOF(DMR)
					TRAP=alarmTrapPnSTDLofDMRProt"
		::= { pnAsIntfcSubProtEntry 16 }

	pnStm1TFProtAlarm OBJECT-TYPE
		SYNTAX		NormalAlarmValue
		ACCESS		read-only
		STATUS		mandatory
		DESCRIPTION	"STM-1(2) TF
				 Refer to NormalAlarmValue of TEXTUAL-CONVENTION
					TRAP=alarmTrapPnSTDStm1TFProtAlarm"
		::= { pnAsIntfcSubProtEntry 17 }

	pnIntfcSTypeMismatch OBJECT-TYPE
		SYNTAX		NormalAlarmValue
		ACCESS		read-only
		STATUS		mandatory
		DESCRIPTION	"INTFC(2) TYPE MISMATCH
				 Refer to NormalAlarmValue of TEXTUAL-CONVENTION
					TRAP=alarmTrapPnSTDIntfcSTypeMismatch"
		::= { pnAsIntfcSubProtEntry 18 }

	pnScLanStatusTable OBJECT-TYPE
		SYNTAX		SEQUENCE OF PnScLanStatusEntry
		ACCESS		not-accessible
		STATUS		mandatory
		DESCRIPTION	"SC LAN STATUS TABLE"
		::= { pnAsIntfcSubProtGroup 2 }

	pnScLanStatusEntry OBJECT-TYPE
		SYNTAX		PnScLanStatusEntry
		ACCESS		not-accessible
		STATUS		mandatory
		INDEX		{
		                                pnScLanStatusPasoIndex,
						pnScLanStatusIndex
					}
		::= { pnScLanStatusTable 1 }

	PnScLanStatusEntry ::= SEQUENCE {
	                  pnScLanStatusPasoIndex   IpAddress,      
					  pnScLanStatusIndex         INTEGER,
					  pnScLanLink                INTEGER,
					  pnScLanCollision           INTEGER,
					  pnScLanLinkLossForwarding  INTEGER,
					  pnScLanSpeedDuplex         INTEGER
					}

	pnScLanStatusPasoIndex OBJECT-TYPE
		SYNTAX		IpAddress 
		ACCESS		read-only
		STATUS		mandatory
		DESCRIPTION	"Pasolink IP Address Index"
		::= { pnScLanStatusEntry 1 }

	pnScLanStatusIndex OBJECT-TYPE
		SYNTAX		INTEGER{
					  port1(1),
					  port2(2)
					}
		ACCESS		read-only
		STATUS		mandatory
		DESCRIPTION	"PORTx(x:1-2) Index
					  1: Port 1
					  2: Port 2"
		::= { pnScLanStatusEntry 2 }

	pnScLanLink OBJECT-TYPE
		SYNTAX		INTEGER(0..2)
		ACCESS		read-only
		STATUS		mandatory
		DESCRIPTION	"INTFC(2) LAN LINK PORTx
					(x : 1-2)
					  0:Invalid,
					  1:Normal,
					  2:Alarm
					TRAP=alarmTrapPnSTDSCLanLink"
		::= { pnScLanStatusEntry 3 }

	pnScLanCollision OBJECT-TYPE
		SYNTAX		INTEGER(0..2)
		ACCESS		read-only
		STATUS		mandatory
		DESCRIPTION	"INTFC(2) LAN COLLISION PORTx
					(x : 1-2)
					  0:Invalid,
					  1:Normal,
					  2:Collision
					TRAP=eventTrapPnSTDSCLanCollision"
		::= { pnScLanStatusEntry 4 }

	pnScLanLinkLossForwarding OBJECT-TYPE
		SYNTAX		INTEGER(0..2)
		ACCESS		read-only
		STATUS		mandatory
		DESCRIPTION	"INTFC(2) LLF PORTx
					(x : 1-2)
					  0:Invalid,
					  1:Normal,
					  2:Under Execution
					TRAP=eventTrapPnSTDSCLanLinkLossForward"
		::= { pnScLanStatusEntry 5 }

	pnScLanSpeedDuplex OBJECT-TYPE
		SYNTAX		INTEGER(0..8)
		ACCESS		read-only
		STATUS		mandatory
		DESCRIPTION	"INTFC(2) LAN MODE PORTx
					(x : 1-4)
				 Speed & Duplex
					  0:INVALID,
					  1:10M-HALF(MDI),
					  2:10M-FULL(MDI),
					  3:100M-HALF(MDI),
					  4:100M-FULL(MDI),
					  5:10M-HALF(MDIX),
					  6:10M-FULL(MDIX),
					  7:100M-HALF(MDIX),
					  8:100M-FULL(MDIX)
					TRAP=eventTrapPnSTDSCLanSpeedDuplex"
		::= { pnScLanStatusEntry 6 }

	pnAsCtrlGroup OBJECT IDENTIFIER
		::= { pnAlarmStatusGroup 5 }

	pnAsCtrlGroupTable OBJECT-TYPE
		SYNTAX		SEQUENCE OF PnAsCtrlGroupEntry
		ACCESS		not-accessible
		STATUS		mandatory
		DESCRIPTION	"CTRL Group Table"
		::= { pnAsCtrlGroup 1 }

	pnAsCtrlGroupEntry OBJECT-TYPE
		SYNTAX		PnAsCtrlGroupEntry
		ACCESS		not-accessible
		STATUS		mandatory
		INDEX		{
		                                pnAsCtrlGroupPasoIndex
					}
		::= { pnAsCtrlGroupTable 1 }

	PnAsCtrlGroupEntry ::= SEQUENCE {
					  pnAsCtrlGroupPasoIndex	IpAddress,
					  pnCtrlAlarm	NormalAlarmValue,
					  pnMultiMediaCardMount	OffOnValue,
					  pnApsSWFail	NormalAlarmValue,
					  pnSvLineAlarm	NormalAlarmValue,
					  pnApsStatus	INTEGER,
					  pnApsLockinStatus INTEGER,
					  pnXCtrlAlarm	INTEGER,
					  pnXpicModeMismatch	INTEGER
					}

	pnAsCtrlGroupPasoIndex OBJECT-TYPE
		SYNTAX		IpAddress 
		ACCESS		read-only
		STATUS		mandatory
		DESCRIPTION	"Pasolink IP Address Index"
		::= { pnAsCtrlGroupEntry 1 }

	pnCtrlAlarm OBJECT-TYPE
		SYNTAX		NormalAlarmValue
		ACCESS		read-only
		STATUS		mandatory
		DESCRIPTION	"CTRL MODULE
				 Refer to NormalAlarmValue of TEXTUAL-CONVENTION
					TRAP=alarmTrapPnSTDCTRLAlarm"
		::= { pnAsCtrlGroupEntry 2 }

	pnMultiMediaCardMount OBJECT-TYPE
		SYNTAX		OffOnValue
		ACCESS		read-only
		STATUS		mandatory
		DESCRIPTION	"MMC MOUNT
				 Refer to OffOnValue of TEXTUAL-CONVENTION
					TRAP=eventTrapPnSTDMMCMount"
		::= { pnAsCtrlGroupEntry 3 }

	pnApsSWFail OBJECT-TYPE
		SYNTAX		NormalAlarmValue
		ACCESS		read-only
		STATUS		mandatory
		DESCRIPTION	"APS SW FAIL
				 Refer to NormalAlarmValue of TEXTUAL-CONVENTION
					TRAP=alarmTrapPnSTDAPSSWFail"
		::= { pnAsCtrlGroupEntry 4 }

	pnSvLineAlarm OBJECT-TYPE
		SYNTAX		NormalAlarmValue
		ACCESS		read-only
		STATUS		mandatory
		DESCRIPTION	"This item is not used.
				 SV LINE
				 Refer to NormalAlarmValue of TEXTUAL-CONVENTION"
		::= { pnAsCtrlGroupEntry 5 }

	pnApsStatus OBJECT-TYPE
		SYNTAX		INTEGER(0..2)
		ACCESS		read-only
		STATUS		mandatory
		DESCRIPTION	"APS ONLINE STATUS
					  0:Invalid,
					  1:Working,
					  2:Protection
					TRAP=eventTrapPnSTDAPSStatus"
		::= { pnAsCtrlGroupEntry 6 }

	pnApsLockinStatus OBJECT-TYPE
		SYNTAX		INTEGER (0..2)
		ACCESS		read-only
		STATUS		mandatory
		DESCRIPTION	"APS LOCK IN STATUS
					  0:Invalid,
					  1:NORMAL,
					  2:LOCK IN
					TRAP=eventTrapPnSTDAPSLockinStatus"
		::= { pnAsCtrlGroupEntry 7 }

	pnXCtrlAlarm OBJECT-TYPE
		SYNTAX		INTEGER
		ACCESS		read-only
		STATUS		mandatory
		DESCRIPTION	"XCTRL
					 Refer to NormalAlarmValue of TEXTUAL-CONVENTION
					 This item is available for XPIC system.
					  0:Invalid,
					  1:NORMAL,
					  2:ALARM
					TRAP=alarmTrapPnSTDXControlAlarm"
		::= { pnAsCtrlGroupEntry 8 }

	pnXpicModeMismatch OBJECT-TYPE
		SYNTAX		INTEGER
		ACCESS		read-only
		STATUS		mandatory
		DESCRIPTION	"XPIC MODE MISMATCH
					 Refer to NormalAlarmValue of TEXTUAL-CONVENTION
					 This item is available for XPIC system.
					  0:Invalid,
					  1:NORMAL,
					  2:ALARM
					TRAP=alarmTrapPnSTDXpicModeMismatch"
		::= { pnAsCtrlGroupEntry 9 }

	pnAsTcnGroup OBJECT IDENTIFIER
		::= { pnAlarmStatusGroup 6 }

	pnTcn15minCurrentTotalTable OBJECT-TYPE
		SYNTAX		SEQUENCE OF PnTcn15minCurrentTotalEntry
		ACCESS		not-accessible
		STATUS		mandatory
		DESCRIPTION	"TCN 15min Current Total Table"
		::= { pnAsTcnGroup 1 }

	pnTcn15minCurrentTotalEntry OBJECT-TYPE
		SYNTAX		PnTcn15minCurrentTotalEntry
		ACCESS		not-accessible
		STATUS		mandatory
		INDEX		{
		                                pnTcn15minCurrentTotalPasoIndex,
						pnTcn15minCurrentTotalWPIndex
					}
		::= { pnTcn15minCurrentTotalTable 1 }

	PnTcn15minCurrentTotalEntry ::= SEQUENCE {
					  pnTcn15minCurrentTotalPasoIndex IpAddress,
					  pnTcn15minCurrentTotalWPIndex  INTEGER,
					  pnTcn15minCurrentTotalOFS      NormalAlarmValue,
					  pnTcn15minCurrentTotalUAS      NormalAlarmValue,
					  pnTcn15minCurrentTotalES       NormalAlarmValue,
					  pnTcn15minCurrentTotalSES      NormalAlarmValue,
					  pnTcn15minCurrentTotalBBE      NormalAlarmValue,
					  pnTcn15minCurrentTotalSEP      NormalAlarmValue
					}

	pnTcn15minCurrentTotalPasoIndex OBJECT-TYPE
		SYNTAX		IpAddress 
		ACCESS		read-only
		STATUS		mandatory
		DESCRIPTION	"Pasolink IP Address Index"
		::= { pnTcn15minCurrentTotalEntry 1 }

	pnTcn15minCurrentTotalWPIndex OBJECT-TYPE
		SYNTAX		INTEGER{
					  working-MUX(1),
					  protection-MUX(2),
					  working-DMR-dirA(3),
					  protection-DMR-dirB(4)
					}
		ACCESS		read-only
		STATUS		mandatory
		DESCRIPTION	"TCN 15min Current Total Index
					  1:Working - MUX,
					  2:Protection - MUX
					  3:Working - DMR - DIR-A
					  4:Protection - DMR - DIR-B
					
					  *)DIR-A/DIR-B is available for 2-WAY.
					  *)Protection is available for APS."
		::= { pnTcn15minCurrentTotalEntry 2 }

	pnTcn15minCurrentTotalOFS OBJECT-TYPE
		SYNTAX		NormalAlarmValue
		ACCESS		read-only
		STATUS		mandatory
		DESCRIPTION	"TCN-OFS-15min TOTAL
				 Refer to NormalAlarmValue of TEXTUAL-CONVENTION
					TRAP=alarmTrapPnSTDTcn15minTotalOFS"
		::= { pnTcn15minCurrentTotalEntry 3 }

	pnTcn15minCurrentTotalUAS OBJECT-TYPE
		SYNTAX		NormalAlarmValue
		ACCESS		read-only
		STATUS		mandatory
		DESCRIPTION	"TCN-UAS-15min TOTAL
				 Refer to NormalAlarmValue of TEXTUAL-CONVENTION
					TRAP=alarmTrapPnSTDTcn15minTotalUAS"
		::= { pnTcn15minCurrentTotalEntry 4 }

	pnTcn15minCurrentTotalES OBJECT-TYPE
		SYNTAX		NormalAlarmValue
		ACCESS		read-only
		STATUS		mandatory
		DESCRIPTION	"TCN-ES-15min TOTAL
				 Refer to NormalAlarmValue of TEXTUAL-CONVENTION
					TRAP=alarmTrapPnSTDTcn15minTotalES"
		::= { pnTcn15minCurrentTotalEntry 5 }

	pnTcn15minCurrentTotalSES OBJECT-TYPE
		SYNTAX		NormalAlarmValue
		ACCESS		read-only
		STATUS		mandatory
		DESCRIPTION	"TCN-SES-15min TOTAL
				 Refer to NormalAlarmValue of TEXTUAL-CONVENTION
					TRAP=alarmTrapPnSTDTcn15minTotalSES"
		::= { pnTcn15minCurrentTotalEntry 6 }

	pnTcn15minCurrentTotalBBE OBJECT-TYPE
		SYNTAX		NormalAlarmValue
		ACCESS		read-only
		STATUS		mandatory
		DESCRIPTION	"TCN-BBE-15min TOTAL
				 Refer to NormalAlarmValue of TEXTUAL-CONVENTION
					TRAP=alarmTrapPnSTDTcn15minTotalBBE"
		::= { pnTcn15minCurrentTotalEntry 7 }

	pnTcn15minCurrentTotalSEP OBJECT-TYPE
		SYNTAX		NormalAlarmValue
		ACCESS		read-only
		STATUS		mandatory
		DESCRIPTION	"TCN-SEP-15min TOTAL
				 Refer to NormalAlarmValue of TEXTUAL-CONVENTION
					TRAP=alarmTrapPnSTDTcn15minTotalSEP"
		::= { pnTcn15minCurrentTotalEntry 8 }

	pnTcn15minCurrentCHTable OBJECT-TYPE
		SYNTAX		SEQUENCE OF PnTcn15minCurrentCHEntry
		ACCESS		not-accessible
		STATUS		mandatory
		DESCRIPTION	"TCN 15min Current CH Table"
		::= { pnAsTcnGroup 2 }

	pnTcn15minCurrentCHEntry OBJECT-TYPE
		SYNTAX		PnTcn15minCurrentCHEntry
		ACCESS		not-accessible
		STATUS		mandatory
		INDEX		{
		                                pnTcn15minCurrentCHPasoIndex
					}
		::= { pnTcn15minCurrentCHTable 1 }

	PnTcn15minCurrentCHEntry ::= SEQUENCE {
					  pnTcn15minCurrentCHPasoIndex	IpAddress,
					  pnTcn15minCurrentCHUAS      OCTET STRING,
					  pnTcn15minCurrentCHES       OCTET STRING,
					  pnTcn15minCurrentCHSES      OCTET STRING,
					  pnTcn15minCurrentCHBBE      OCTET STRING,
					  pnTcn15minCurrentCHSEP      OCTET STRING
					}

	pnTcn15minCurrentCHPasoIndex OBJECT-TYPE
		SYNTAX		IpAddress 
		ACCESS		read-only
		STATUS		mandatory
		DESCRIPTION	"Pasolink IP Address Index"
		::= { pnTcn15minCurrentCHEntry 1 }

	pnTcn15minCurrentCHUAS OBJECT-TYPE
		SYNTAX		OCTET STRING (SIZE (1))
		ACCESS		read-only
		STATUS		mandatory
		DESCRIPTION	"This item is not used.
				 TCN-UAS-15min CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnSTDTcn15minCHUAS"
		::= { pnTcn15minCurrentCHEntry  2 }

	pnTcn15minCurrentCHES OBJECT-TYPE
		SYNTAX		OCTET STRING (SIZE (1))
		ACCESS		read-only
		STATUS		mandatory
		DESCRIPTION	"This item is not used.
				 TCN-ES-15min CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnSTDTcn15minCHES"
		::= { pnTcn15minCurrentCHEntry  3 }

	pnTcn15minCurrentCHSES OBJECT-TYPE
		SYNTAX		OCTET STRING (SIZE (1))
		ACCESS		read-only
		STATUS		mandatory
		DESCRIPTION	"This item is not used.
				 TCN-SES-15min CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnSTDTcn15minCHSES"
		::= { pnTcn15minCurrentCHEntry  4 }

	pnTcn15minCurrentCHBBE OBJECT-TYPE
		SYNTAX		OCTET STRING (SIZE (1))
		ACCESS		read-only
		STATUS		mandatory
		DESCRIPTION	"This item is not used.
				 TCN-BBE-15min CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnSTDTcn15minCHBBE"
		::= { pnTcn15minCurrentCHEntry  5 }

	pnTcn15minCurrentCHSEP OBJECT-TYPE
		SYNTAX		OCTET STRING (SIZE (1))
		ACCESS		read-only
		STATUS		mandatory
		DESCRIPTION	"This item is not used.
				 TCN-SEP-15min CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnSTDTcn15minCHSEP"
		::= { pnTcn15minCurrentCHEntry  6 }

	pnTcn1dayCurrentTotalTable OBJECT-TYPE
		SYNTAX		SEQUENCE OF PnTcn1dayCurrentTotalEntry
		ACCESS		not-accessible
		STATUS		mandatory
		DESCRIPTION	"1day Current Total Table"
		::= { pnAsTcnGroup 3 }

	pnTcn1dayCurrentTotalEntry OBJECT-TYPE
		SYNTAX		PnTcn1dayCurrentTotalEntry
		ACCESS		not-accessible
		STATUS		mandatory
		INDEX		{
						pnTcn1dayCurrentTotalPasoIndex,
						pnTcn1dayCurrentTotalWPIndex
					}
		::= { pnTcn1dayCurrentTotalTable 1 }

	PnTcn1dayCurrentTotalEntry ::= SEQUENCE {
					  pnTcn1dayCurrentTotalPasoIndex IpAddress,
					  pnTcn1dayCurrentTotalWPIndex  INTEGER,
					  pnTcn1dayCurrentTotalOFS      NormalAlarmValue,
					  pnTcn1dayCurrentTotalUAS      NormalAlarmValue,
					  pnTcn1dayCurrentTotalES       NormalAlarmValue,
					  pnTcn1dayCurrentTotalSES      NormalAlarmValue,
					  pnTcn1dayCurrentTotalBBE      NormalAlarmValue,
					  pnTcn1dayCurrentTotalSEP      NormalAlarmValue
					}

	pnTcn1dayCurrentTotalPasoIndex OBJECT-TYPE
		SYNTAX		IpAddress 
		ACCESS		read-only
		STATUS		mandatory
		DESCRIPTION	"Pasolink IP Address Index"
		::= { pnTcn1dayCurrentTotalEntry 1 }

	pnTcn1dayCurrentTotalWPIndex OBJECT-TYPE
		SYNTAX		INTEGER{
					  working-MUX(1),
					  protection-MUX(2),
					  working-DMR-dirA(3),
					  protection-DMR-dirB(4)
					}
		ACCESS		read-only
		STATUS		mandatory
		DESCRIPTION	"TCN 1day Current Total Index
					  1:Working(MUX),
					  2:Protection(MUX),
					  3:Working(DMR)/Working(DIR-A)
					  4:Protection(DMR)/Working(DIR-B)

					  *)DIR-A/DIR-B is available for 2-WAY.
					  *)Protection is available for APS.
					  *)MUX is unavailable for LAN interface."
		::= { pnTcn1dayCurrentTotalEntry 2 }

	pnTcn1dayCurrentTotalOFS OBJECT-TYPE
		SYNTAX		NormalAlarmValue
		ACCESS		read-only
		STATUS		mandatory
		DESCRIPTION	"TCN-OFS-1day TOTAL
				 Refer to NormalAlarmValue of TEXTUAL-CONVENTION
					TRAP=alarmTrapPnSTDTcn1dayTotalOFS"
		::= { pnTcn1dayCurrentTotalEntry 3 }

	pnTcn1dayCurrentTotalUAS OBJECT-TYPE
		SYNTAX		NormalAlarmValue
		ACCESS		read-only
		STATUS		mandatory
		DESCRIPTION	"TCN-UAS-1day TOTAL
				 Refer to NormalAlarmValue of TEXTUAL-CONVENTION
					TRAP=alarmTrapPnSTDTcn1dayTotalUAS"
		::= { pnTcn1dayCurrentTotalEntry 4 }

	pnTcn1dayCurrentTotalES OBJECT-TYPE
		SYNTAX		NormalAlarmValue
		ACCESS		read-only
		STATUS		mandatory
		DESCRIPTION	"TCN-ES-1day TOTAL
				 Refer to NormalAlarmValue of TEXTUAL-CONVENTION
					TRAP=alarmTrapPnSTDTcn1dayTotalES"
		::= { pnTcn1dayCurrentTotalEntry 5 }

	pnTcn1dayCurrentTotalSES OBJECT-TYPE
		SYNTAX		NormalAlarmValue
		ACCESS		read-only
		STATUS		mandatory
		DESCRIPTION	"TCN-SES-1day TOTAL
				 Refer to NormalAlarmValue of TEXTUAL-CONVENTION
					TRAP=alarmTrapPnSTDTcn1dayTotalSES"
		::= { pnTcn1dayCurrentTotalEntry 6 }

	pnTcn1dayCurrentTotalBBE OBJECT-TYPE
		SYNTAX		NormalAlarmValue
		ACCESS		read-only
		STATUS		mandatory
		DESCRIPTION	"TCN-BBE-1day TOTAL
				 Refer to NormalAlarmValue of TEXTUAL-CONVENTION
					TRAP=alarmTrapPnSTDTcn1dayTotalBBE"
		::= { pnTcn1dayCurrentTotalEntry 7 }

	pnTcn1dayCurrentTotalSEP OBJECT-TYPE
		SYNTAX		NormalAlarmValue
		ACCESS		read-only
		STATUS		mandatory
		DESCRIPTION	"TCN-SEP-1day TOTAL
				 Refer to NormalAlarmValue of TEXTUAL-CONVENTION
					TRAP=alarmTrapPnSTDTcn1dayTotalSEP"
		::= { pnTcn1dayCurrentTotalEntry 8 }

	pnTcn1dayCurrentCHTable OBJECT-TYPE
		SYNTAX		SEQUENCE OF PnTcn1dayCurrentCHEntry
		ACCESS		not-accessible
		STATUS		mandatory
		DESCRIPTION	"TCN 1day Current CH Table"
		::= { pnAsTcnGroup 4 }

	pnTcn1dayCurrentCHEntry OBJECT-TYPE
		SYNTAX		PnTcn1dayCurrentCHEntry
		ACCESS		not-accessible
		STATUS		mandatory
		INDEX		{
		                                pnTcn1dayCurrentCHPasoIndex
					}
		::= { pnTcn1dayCurrentCHTable 1 }

	PnTcn1dayCurrentCHEntry ::= SEQUENCE {
					  pnTcn1dayCurrentCHPasoIndex IpAddress,
					  pnTcn1dayCurrentCHUAS      OCTET STRING,
					  pnTcn1dayCurrentCHES       OCTET STRING,
					  pnTcn1dayCurrentCHSES      OCTET STRING,
					  pnTcn1dayCurrentCHBBE      OCTET STRING,
					  pnTcn1dayCurrentCHSEP      OCTET STRING
					}

	pnTcn1dayCurrentCHPasoIndex OBJECT-TYPE
		SYNTAX		IpAddress 
		ACCESS		read-only
		STATUS		mandatory
		DESCRIPTION	"Pasolink IP Address Index"
		::= { pnTcn1dayCurrentCHEntry 1 }

	pnTcn1dayCurrentCHUAS OBJECT-TYPE
		SYNTAX		OCTET STRING (SIZE (1))
		ACCESS		read-only
		STATUS		mandatory
		DESCRIPTION	"This item is not used.
				 TCN-UAS-1day CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnSTDTcn1dayCHUAS"
		::= { pnTcn1dayCurrentCHEntry  2 }

	pnTcn1dayCurrentCHES OBJECT-TYPE
		SYNTAX		OCTET STRING (SIZE (1))
		ACCESS		read-only
		STATUS		mandatory
		DESCRIPTION	"This item is not used.
				 TCN-ES-1day CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnSTDTcn1dayCHES"
		::= { pnTcn1dayCurrentCHEntry  3 }

	pnTcn1dayCurrentCHSES OBJECT-TYPE
		SYNTAX		OCTET STRING (SIZE (1))
		ACCESS		read-only
		STATUS		mandatory
		DESCRIPTION	"This item is not used.
				 TCN-SES-1day CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnSTDTcn1dayCHSES"
		::= { pnTcn1dayCurrentCHEntry  4 }

	pnTcn1dayCurrentCHBBE OBJECT-TYPE
		SYNTAX		OCTET STRING (SIZE (1))
		ACCESS		read-only
		STATUS		mandatory
		DESCRIPTION	"This item is not used.
				 TCN-BBE-1day CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnSTDTcn1dayCHBBE"
		::= { pnTcn1dayCurrentCHEntry  5 }

	pnTcn1dayCurrentCHSEP OBJECT-TYPE
		SYNTAX		OCTET STRING (SIZE (1))
		ACCESS		read-only
		STATUS		mandatory
		DESCRIPTION	"This item is not used.
				 TCN-SEP-1day CHxx
					(xx : 1-48 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnSTDTcn1dayCHSEP"
		::= { pnTcn1dayCurrentCHEntry  6 }

	pnTcnCurrentUAETable OBJECT-TYPE
		SYNTAX		SEQUENCE OF PnTcnCurrentUAEEntry
		ACCESS		not-accessible
		STATUS		mandatory
		DESCRIPTION	"TCN Current UAE"
		::= { pnAsTcnGroup 5 }

	pnTcnCurrentUAEEntry OBJECT-TYPE
		SYNTAX		PnTcnCurrentUAEEntry
		ACCESS		not-accessible
		STATUS		mandatory
		INDEX		{
		                                pnTcnCurrentUAEPasoIndex
					}
		::= { pnTcnCurrentUAETable 1 }

	PnTcnCurrentUAEEntry ::= SEQUENCE {
					  pnTcnCurrentUAEPasoIndex	IpAddress,
					  pnTcnUAEDMRWork	NormalAlarmValue,
					  pnTcnUAEDMRProt	NormalAlarmValue,
					  pnTcnUAEMUXWork	NormalAlarmValue,
					  pnTcnUAEMUXProt	NormalAlarmValue,
					}

	pnTcnCurrentUAEPasoIndex OBJECT-TYPE
		SYNTAX		IpAddress 
		ACCESS		read-only
		STATUS		mandatory
		DESCRIPTION	"Pasolink IP Address Index"
		::= { pnTcnCurrentUAEEntry 1 }

	pnTcnUAEDMRWork OBJECT-TYPE
		SYNTAX		NormalAlarmValue
		ACCESS		read-only
		STATUS		mandatory
		DESCRIPTION	"Unavailable Event(TOTAL)
				 Refer to NormalAlarmValue of TEXTUAL-CONVENTION
					  This shows the value of DIR-A side  for PDH.
					  This shows the value of INTFC(1) for STM-1.
					TRAP=alarmTrapPnSTDTcnUAEDMRWork"
		::= { pnTcnCurrentUAEEntry 2 }

	pnTcnUAEDMRProt OBJECT-TYPE
		SYNTAX		NormalAlarmValue
		ACCESS		read-only
		STATUS		mandatory
		DESCRIPTION	"Unavailable Event(TOTAL)
					  This shows the value of DIR-B side  for PDH.
					  This shows the value of INTFC(2) for STM-1.
					TRAP=alarmTrapPnSTDTcnUAEDMRProt"
		::= { pnTcnCurrentUAEEntry 3 }

	pnTcnUAEMUXWork OBJECT-TYPE
		SYNTAX		NormalAlarmValue
		ACCESS		read-only
		STATUS		mandatory
		DESCRIPTION	"STM-1(1) Unavailable Event(MUX)
				 This item is available for STM-1 interface.
					TRAP=alarmTrapPnSTDTcnUAEMUXWork"
		::= { pnTcnCurrentUAEEntry 4 }

	pnTcnUAEMUXProt OBJECT-TYPE
		SYNTAX		NormalAlarmValue
		ACCESS		read-only
		STATUS		mandatory
		DESCRIPTION	"STM-1(2) Unavailable Event(MUX)
				 This item is available for APS.
					TRAP=alarmTrapPnSTDTcnUAEMUXProt"
		::= { pnTcnCurrentUAEEntry 5 }

	pnTcnTCSTable OBJECT-TYPE
		SYNTAX		SEQUENCE OF PnTcnTCSEntry
		ACCESS		not-accessible
		STATUS		mandatory
		DESCRIPTION	"TCN TCS Table"
		::= { pnAsTcnGroup 6 }

	pnTcnTCSEntry OBJECT-TYPE
		SYNTAX		PnTcnTCSEntry
		ACCESS		not-accessible
		STATUS		mandatory
		INDEX		{
						pnTcnTCSPasoIndex,
						pnTcnTCSSysIndex
					}
		::= { pnTcnTCSTable 1 }

	PnTcnTCSEntry ::= SEQUENCE {
	                                  pnTcnTCSPasoIndex IpAddress,
					  pnTcnTCSSysIndex    INTEGER,
					  pnTcnTCS15minRxLev  NormalAlarmValue,
					  pnTcnTCS1dayRxLev   NormalAlarmValue
					}

	pnTcnTCSPasoIndex OBJECT-TYPE
		SYNTAX		IpAddress 
		ACCESS		read-only
		STATUS		mandatory
		DESCRIPTION	"Pasolink IP Address Index"
		::= { pnTcnTCSEntry 1 }

	pnTcnTCSSysIndex OBJECT-TYPE
		SYNTAX		INTEGER{
					  no1-dirA(1),
					  no2-dirB(2)
					}
		ACCESS		read-only
		STATUS		mandatory
		DESCRIPTION	"TCN TCS System Index
					  1:No.1/DIR-A
					  2:No.2/DIR-B
				 *)No.2 is available for 1+1 system.
				 *)DIR-A/B is available for 2-WAY."
		::= { pnTcnTCSEntry 2 }

	pnTcnTCS15minRxLev OBJECT-TYPE
		SYNTAX		NormalAlarmValue
		ACCESS		read-only
		STATUS		mandatory
		DESCRIPTION	"TCN-RX LEV-15min
				 Refer to NormalAlarmValue of TEXTUAL-CONVENTION
					TRAP=alarmTrapPnSTDTcnTCS15minRxLev"
		::= { pnTcnTCSEntry 3 }

	pnTcnTCS1dayRxLev OBJECT-TYPE
		SYNTAX		NormalAlarmValue
		ACCESS		read-only
		STATUS		mandatory
		DESCRIPTION	"TCN-RX LEV-1day
				 Refer to NormalAlarmValue of TEXTUAL-CONVENTION
					TRAP=alarmTrapPnSTDTcnTCS1dayRxLev"
		::= { pnTcnTCSEntry 4 }

	pnAsAuxIOGroup OBJECT IDENTIFIER
		::= { pnAlarmStatusGroup 7 }

	pnAuxInputStatusTable OBJECT-TYPE
		SYNTAX		SEQUENCE OF PnAuxInputStatusEntry
		ACCESS		not-accessible
		STATUS		mandatory
		DESCRIPTION	"AUX Input Status Table"
		::= { pnAsAuxIOGroup 1 }

	pnAuxInputStatusEntry OBJECT-TYPE
		SYNTAX		PnAuxInputStatusEntry
		ACCESS		not-accessible
		STATUS		mandatory
		INDEX		{
						pnAuxInputStatusPasoIndex,
						pnAuxInputStatusIndex
					}
		::= { pnAuxInputStatusTable 1 }

	PnAuxInputStatusEntry ::= SEQUENCE {
                                          pnAuxInputStatusPasoIndex IpAddress,
					  pnAuxInputStatusIndex  INTEGER,
					  pnAuxInputStatusValue  INTEGER
					}

	pnAuxInputStatusPasoIndex OBJECT-TYPE
		SYNTAX		IpAddress 
		ACCESS		read-only
		STATUS		mandatory
		DESCRIPTION	"Pasolink IP Address Index"
		::= { pnAuxInputStatusEntry 1 }

	pnAuxInputStatusIndex OBJECT-TYPE
		SYNTAX		INTEGER{
					  auxInput1(1),
					  auxInput2(2),
					  auxInput3(3),
					  auxInput4(4),
					  auxInput5(5),
					  auxInput6(6)
					}
		ACCESS		read-only
		STATUS		mandatory
		DESCRIPTION	"AUX Input Status Index
					  1:Input 1
					  2:Input 2
					  3:Input 3
					  4:Input 4
					  5:Input 5
					  6:Input 6"
		::= { pnAuxInputStatusEntry 2 }

	pnAuxInputStatusValue OBJECT-TYPE
		SYNTAX		INTEGER(0..2)
		ACCESS		read-only
		STATUS		mandatory
		DESCRIPTION	"ITEM NAME(INPUT-x)
					(x : 1-6)
					  0:Invalid,
					  1:Open State,
					  2:Close State
					TRAP=statusTrapPnSTDAuxInput"
		::= { pnAuxInputStatusEntry 3 }

	pnAuxOutputStatusTable OBJECT-TYPE
		SYNTAX		SEQUENCE OF PnAuxOutputStatusEntry
		ACCESS		not-accessible
		STATUS		mandatory
		DESCRIPTION	"AUX Output Status Table"
		::= { pnAsAuxIOGroup 2 }

	pnAuxOutputStatusEntry OBJECT-TYPE
		SYNTAX		PnAuxOutputStatusEntry
		ACCESS		not-accessible
		STATUS		mandatory
		INDEX		{
					        pnAuxOutputStatusPasoIndex,
						pnAuxOutputStatusIndex
					}
		::= { pnAuxOutputStatusTable 1 }

	PnAuxOutputStatusEntry ::= SEQUENCE {
					  pnAuxOutputStatusPasoIndex IpAddress,
					  pnAuxOutputStatusIndex  INTEGER,
					  pnAuxOutputStatusValue  INTEGER
					}

	pnAuxOutputStatusPasoIndex OBJECT-TYPE
		SYNTAX		IpAddress 
		ACCESS		read-only
		STATUS		mandatory
		DESCRIPTION	"Pasolink IP Address Index"
		::= { pnAuxOutputStatusEntry 1 }

	pnAuxOutputStatusIndex OBJECT-TYPE
		SYNTAX		INTEGER{
					  auxOutput1(1),
					  auxOutput2(2),
					  auxOutput3(3),
					  auxOutput4(4)
					}
		ACCESS		read-only
		STATUS		mandatory
		DESCRIPTION	"AUX Output Status Index
					  1:Output 1
					  2:Output 2
					  3:Output 3
					  4:Output 4"
		::= { pnAuxOutputStatusEntry 2 }

	pnAuxOutputStatusValue OBJECT-TYPE
		SYNTAX		INTEGER(0..2)
		ACCESS		read-only
		STATUS		mandatory
		DESCRIPTION	"ITEM NAME(OUTPUT-x)
					(x : 1-4)
					  0:Invalid,
					  1:Open state,
					  2:Close state

					*) This value is for control house keeping
					TRAP=eventTrapPnSTDAuxOutput"
		::= { pnAuxOutputStatusEntry 3 }

	pnAuxClusterAlarmTable OBJECT-TYPE
		SYNTAX		SEQUENCE OF PnAuxClusterAlarmEntry
		ACCESS		not-accessible
		STATUS		mandatory
		DESCRIPTION	"AUX Cluster Alarm Table"
		::= { pnAsAuxIOGroup 3 }

	pnAuxClusterAlarmEntry OBJECT-TYPE
		SYNTAX		PnAuxClusterAlarmEntry
		ACCESS		not-accessible
		STATUS		mandatory
		INDEX		{
						pnAuxClusterAlarmPasoIndex,
						pnAuxClusterAlarmIndex
					}
		::= { pnAuxClusterAlarmTable 1 }

	PnAuxClusterAlarmEntry ::= SEQUENCE {
					  pnAuxClusterAlarmPasoIndex  IpAddress,
					  pnAuxClusterAlarmIndex  INTEGER,
					  pnAuxClusterAlarmValue  NormalAlarmValue
					}

	pnAuxClusterAlarmPasoIndex OBJECT-TYPE
		SYNTAX		IpAddress 
		ACCESS		read-only
		STATUS		mandatory
		DESCRIPTION	"Pasolink IP Address Index"
		::= { pnAuxClusterAlarmEntry 1 }

	pnAuxClusterAlarmIndex OBJECT-TYPE
		SYNTAX		INTEGER{
					  clusterAlarm1(1),
					  clusterAlarm2(2),
					  clusterAlarm3(3),
					  clusterAlarm4(4)
					}
		ACCESS		read-only
		STATUS		mandatory
		DESCRIPTION	"
					AUX Cluster Alarm Index
					  1:Cluster Alarm 1
					  2:Cluster Alarm 2
					  3:Cluster Alarm 3
					  4:Cluster Alarm 4
					
					TRAP=alarmTrapPnSTDAuxClusterAlarm"
		::= { pnAuxClusterAlarmEntry 2 }

	pnAuxClusterAlarmValue OBJECT-TYPE
		SYNTAX		NormalAlarmValue
		ACCESS		read-only
		STATUS		mandatory
		DESCRIPTION	"This is not used.
				 CLUSTERx ALARM
					(x : 1-4)
					TRAP=alarmTrapPnSTDAuxClusterAlarm"
		::= { pnAuxClusterAlarmEntry 3 }

-----------------------------------------------
-- pnEquipmentSetUpGroup Group Definitions
-----------------------------------------------

	pnEsCommonTable OBJECT-TYPE
		SYNTAX		SEQUENCE OF PnEsCommonEntry
		ACCESS		not-accessible
		STATUS		mandatory
		DESCRIPTION	"Es Common Table"
		::= { pnEquipmentSetUpGroup 1 }

	pnEsCommonEntry OBJECT-TYPE
		SYNTAX		PnEsCommonEntry
		ACCESS		not-accessible
		STATUS		mandatory
		INDEX		{
		                          pnEsCommonPasoIndex
					}
		::= { pnEsCommonTable 1 }

	PnEsCommonEntry ::= SEQUENCE {
		                          pnEsCommonPasoIndex IpAddress,
					  pnEsSystemArchitecture	INTEGER,
					  pnEsRedundancy	INTEGER,
					  pnEsXPICTypeSelect	INTEGER,
					  pnEsAPSFunction	INTEGER,
					  pnEsIntfcMainWorkSelect	INTEGER,
					  pnEsIntfcSubProtSelect	INTEGER,
					  pnEsModulationScheme	INTEGER,
					  pnEsTransmissionCapacity	INTEGER ,
					  pnEsLANPortUsage	INTEGER,
					  pnEsTxSWType	INTEGER,
					  pnEsModulationSchemeDirB	INTEGER,
					  pnEsTransmissionCapacityDirB	INTEGER,
					  pnEsLan2mCapacityDirA	INTEGER,
					  pnEsLanScAssignmentDirA	INTEGER,
					  pnEsLan2mCapacityDirB	INTEGER,
					  pnEsLanScAssignmentDirB	INTEGER,
					  pnEsDiNumber	INTEGER
					}

	pnEsCommonPasoIndex OBJECT-TYPE
		SYNTAX		IpAddress 
		ACCESS		read-only
		STATUS		mandatory
		DESCRIPTION	"Pasolink IP Address Index"
		::= { pnEsCommonEntry 1 }

	pnEsSystemArchitecture OBJECT-TYPE
		SYNTAX		INTEGER (0..255)
		ACCESS		read-only
		STATUS		mandatory
		DESCRIPTION	"USER INTERFACE
					  0:Invalid,
					  1:PDH E1,
					  2:PDH E1 with LAN,
					  3:4PORT LAN with E1,
					  4:PDH E3,
					  5:PDH E3 with LAN,
					  6:SDH STM-1,
					  7:2PORT LAN over STM-1,
					  8:GbE over STM-1"
		::= { pnEsCommonEntry 2 }

	pnEsRedundancy OBJECT-TYPE
		SYNTAX		INTEGER (0..7)
		ACCESS		read-only
		STATUS		mandatory
		DESCRIPTION	"REDUNDANCY SETTING
					  0:Invalid,
					  1:1+0(TERM),
					  2:1+1(HOT STANDBY TERM),
					  3:1+1(TWINPATH TERM),
					  4:2-WAY PDH(STAR),
					  5:2-WAY PDH(TREE),
					  6:2-WAY PDH(REP),
					  7:2-WAY PDH(RING),
					  8:2-WAY PDH

					  *)2-WAY is available, when System Architecture is PDH."
		::= { pnEsCommonEntry 3 }

	pnEsXPICTypeSelect OBJECT-TYPE
		SYNTAX		INTEGER (0..3)
		ACCESS		read-only
		STATUS		mandatory
		DESCRIPTION	"XPIC USAGE
					  0:INVALID,
					  1:NOT USED,
					  2:USED(MAIN MASTER),
					  3:USED(SUB MASTER)
					
					  *)This item is used for XPIC system.
					     This value is fixed to 0 when System Architecture is PDH."
		::= { pnEsCommonEntry 4 }

	pnEsAPSFunction OBJECT-TYPE
		SYNTAX		INTEGER (0..3)
		ACCESS		read-only
		STATUS		mandatory
		DESCRIPTION	"APS FUNCTION
					  0:Invalid,
					  1:Unavailable,
					  2:Available
					
					  *) This value is fixed to 2 when INTFC(2) is OPT INTFC."
		::= { pnEsCommonEntry 5 }

	pnEsIntfcMainWorkSelect OBJECT-TYPE
		SYNTAX		INTEGER (0..255)
		ACCESS		read-only
		STATUS		mandatory
		DESCRIPTION	"MAIN(WORK)
					  0:BLANK,
					  1:16xE1 BASIC PKG,
					  2:16xE1 STANDARD PKG(E/W LAN),
					  3:32xE1 PKG(E/W LAN),
					  4:48xE1 PKG,
					  5:4PORT LAN WITH E1,
					  6:STM-1(OPTICAL),
					  7:STM-1(ELECTRICAL),
					  8:2PORT LAN OVER STM-1,
					  9:GbE OVER STM-1,
					  10:E3 PKG(E/W LAN),
					  11:16E1 2-WAY/XC PKG(E/W LAN),
					  13:GbE(10/100/1000B) OVER STM-1"
		::= { pnEsCommonEntry 6 }

	pnEsIntfcSubProtSelect OBJECT-TYPE
		SYNTAX		INTEGER (0..255)
		ACCESS		read-only
		STATUS		mandatory
		DESCRIPTION	"SUB(PROT)
					  0:INVALID,
					  1:NOT USED,
					  2:STM-1(OPTICAL),
					  3:WS/LAN
					  4:WS

					  *) This value is fixed to 0 when System Architecture is PDH."
		::= { pnEsCommonEntry 7 }

	pnEsModulationScheme OBJECT-TYPE
		SYNTAX		INTEGER (0..6)
		ACCESS		read-only
		STATUS		mandatory
		DESCRIPTION	"MODULATION SCHEME
					  0:Invalid,
					  1:QPSK,
					  2:16QAM,
					  3:32QAM,
					  4:64QAM,
					  5:128QAM,
					  6:256QAM   -- Not Used
					
					  *)This Value shows for DIR-A when Redundancy is 2-WAY."
		::= { pnEsCommonEntry 8 }

	pnEsTransmissionCapacity OBJECT-TYPE
		SYNTAX		INTEGER  (0..8)
		ACCESS		read-only
		STATUS		mandatory
		DESCRIPTION	"TRANSMISSION CAPACITY
					  0:Invalid,
					  1:5MB   -- Not Used
					  2:10MB
					  3:20MB
					  4:40MB
					  5:80MB
					  6:100MB
					  7:156MB(STM-1/2P LAN)
					  8:311MB(2xSTM-1)   -- Not Used
					
					  *)This Value shows for DIR-A when Redundancy is 2-WAY."
		::= { pnEsCommonEntry 9 }

	pnEsLANPortUsage OBJECT-TYPE
		SYNTAX		INTEGER (0..14)
		ACCESS		read-only
		STATUS		mandatory
		DESCRIPTION	"LAN PORT USAGE
					  0:INVALID,
					  1:NOT USED ,
					  2:P1-2 SHARED/1PORT ONLY(MAIN),
					  3:P1-2 SEPARATED(MAIN),
					  4:P1-2 SHARED/1PORT ONLY(SC),
					  5:P1-2 SEPARATED(SC),
					  6:P1-4 SHARED(MAIN),
					  7:P1-2 SHARED/P3-4 SHARED(MAIN),
					  8:P1-4 SEPARATED(MAIN),
					  9:P1-4 SHARED(SC),
					  10:P1-2 SHARED/P3-4 SHARED(SC)
					  11:P1=75MB/P2=75MB
					  12:P1=100MB/P2=50MB
					  13:BEST EFFORT
					  14:P1=100MB/P2=NOT USED
					  15:P1-2 SHARED/1PORT ONLY(WS)
					  16:P1-2 SEPARATED(WS)-- Not Used
					  17-19:reserved
					  20:P1=75MB/P2=75MB+WS LAN
					  21:P1=100MB/P2=50MB+WS LAN
					  22:BEST EFFORT+WS LAN
					  23:P1=100MB/P2=NOT USED+WS LAN
					  24:P1=75MB/P2=75MB+SC LAN
					  25:P1=100MB/P2=50MB+SC LAN
					  26:BEST EFFORT+SC LAN
					  27:P1=100MB/P2=NOT USED+SC LAN
					  28-29:reserved
					  30:GbE Only
					  31:GbE+WS LAN
					  32:GbE+SC LAN
					  33-39:reserved
					  40:STM-1+WS LAN
					  41:STM-1+SC LAN
					  42-49:reserved
					  50:P1-2 SHARED/1PORT ONLY(DIR-A M)
					  51:P1-2 SHARED/1PORT ONLY(DIR-A SC)
					  52:P1-2 SHARED/1PORT ONLY(DIR-B M)
					  53:P1-2 SHARED/1PORT ONLY(DIR-B SC)
					  54:P1-2 STAR (DIR-A M, DIR-B M)
					  55:P1-2 STAR (DIR-A SC, DIR-B SC)
					  56:P1-2 STAR (DIR-A M, DIR-B SC)
					  57:P1-2 STAR (DIR-A SC, DIR-B M)
					  58:P1-2 MIXED (DIR-A M, DIR-B M)
					  59:P1-2 MIXED (DIR-A M, DIR-B SC)
					  60:P1-2 MIXED (DIR-A SC, DIR-B M)
					  61:P1-2 MIXED (DIR-A SC, DIR-B SC)
					  *) The values from 1 to 9 and 15 and 50 to 61 are only for PDH.
					      The values from 11 to 14 and 20 to 41 are only for SDH.
					      This value is fixed to 0 when LAN is not used."
		::= { pnEsCommonEntry 10 }

	pnEsTxSWType OBJECT-TYPE
		SYNTAX		INTEGER (0..2)
		ACCESS		read-only
		STATUS		mandatory
		DESCRIPTION	"TX SW TYPE
					 0:Invalid,
					 1:MUTE,
					 2:RF SW TYPE--Not used"
		::= { pnEsCommonEntry 11 }

	pnEsModulationSchemeDirB OBJECT-TYPE
		SYNTAX		INTEGER (0..6)
		ACCESS		read-only
		STATUS		mandatory
		DESCRIPTION	"MODULATION SCHEME DIR-B
					  0:Invalid,
					  1:QPSK,
					  2:16QAM,
					  3:32QAM,
					  4:64QAM,
					  5:128QAM,
					  6:256QAM  -- Not Used
					
					  *)This Value is fixed to 0 when Redundancy isn't 2-WAY."
		::= { pnEsCommonEntry 12 }

	pnEsTransmissionCapacityDirB OBJECT-TYPE
		SYNTAX		INTEGER (0..8)
		ACCESS		read-only
		STATUS		mandatory
		DESCRIPTION	"TRANSMISSION CAPACITY DIR-B
					  0:Invalid,
					  1:5MB,   -- Not Used
					  2:10MB,
					  3:20MB,
					  4:40MB,
					  5:80MB,
					  6:100MB,
					  7:156MB(STM-1/2P LAN),
					  8:311MB(2xSTM-1)   -- Not Used
					
					  *)This Value is fixed to 0 when Redundancy isn't 2-WAY."
		::= { pnEsCommonEntry 13 }

	pnEsLan2mCapacityDirA OBJECT-TYPE
		SYNTAX		INTEGER (0..100)
		ACCESS		read-only
		STATUS		mandatory
		DESCRIPTION	"LAN & 2M CAPACITY[Mbps]
					
					  *)This Value shows for DIR-A when Redundancy is 2-WAY.
					  *)This Value is fixed 0 when Main CH isn't used by LAN."
		::= { pnEsCommonEntry 14 }

	pnEsLanScAssignmentDirA OBJECT-TYPE
		SYNTAX		INTEGER (0..3)
		ACCESS		read-only
		STATUS		mandatory
		DESCRIPTION	"LAN & SC ASSIGNMENT
					  0:INVALID,
					  1:64Kbp,
					  2:128Kbps,
					  3:256Kbps
					  4:64Kbps(E1<DMR>)
					  5:64Kbps(F1<DMR>)
					  6:192Kbps(DCCr<DMR>)
					  7:64Kbps(E1<MUX>)
					  8:64Kbps(F1<MUX>)
					  9:192Kbps(DCCr<MUX>)
					 10:2Mbps (WS)
					  *)This Value shows for DIR-A when Redundancy is 2-WAY.
					  *)This Value is fixed to 0 when SC isn't used by LAN.  "
		::= { pnEsCommonEntry 15 }

	pnEsLan2mCapacityDirB OBJECT-TYPE
		SYNTAX		INTEGER (0..100)
		ACCESS		read-only
		STATUS		mandatory
		DESCRIPTION	"LAN & 2M CAPACITY(DIR-B)[Mbps]
					
					  *)This Value is fixed to 0 when Redundancy isn't 2-WAY.
					  *)This Value is fixed to 0 when Main CH isn't used for LAN."
		::= { pnEsCommonEntry 16 }

	pnEsLanScAssignmentDirB OBJECT-TYPE
		SYNTAX		INTEGER (0..3)
		ACCESS		read-only
		STATUS		mandatory
		DESCRIPTION	"LAN & SC ASSIGNMENT(DIR-B)
					  0:INVALID,
					  1:64Kbp,
					  2:128Kbps,
					  3:256Kbps
					  4:64Kbps(E1<DMR>)
					  5:64Kbps(F1<DMR>)
					  6:192Kbps(DCCr<DMR>)
					  7:64Kbps(E1<MUX>)
					  8:64Kbps(F1<MUX>)
					  9:192Kbps(DCCr<MUX>)
					 10:2Mbps (WS)
					  *)This Value is fixed to 0 when Redundancy isn't 2-WAY.
					  *)This Value is fixed 0 to when SC isn't used by LAN.  "
		::= { pnEsCommonEntry 17 }

	pnEsDiNumber OBJECT-TYPE
		SYNTAX		INTEGER (0..48)
		ACCESS		read-only
		STATUS		mandatory
		DESCRIPTION	"This item is not used.
				 DI NUMBER
					  
					  *) This Value is not used when System Architecture is SDH."
		::= { pnEsCommonEntry 18 }

	pnEsSysTable OBJECT-TYPE
		SYNTAX		SEQUENCE OF PnEsSysEntry
		ACCESS		not-accessible
		STATUS		mandatory
		DESCRIPTION	"Sys Item Table"
		::= { pnEquipmentSetUpGroup 2 }

	pnEsSysEntry OBJECT-TYPE
		SYNTAX		PnEsSysEntry
		ACCESS		not-accessible
		STATUS		mandatory
		INDEX		{
						pnEsSysPasoIndex,
						pnEsSysIndex
					}
		::= { pnEsSysTable 1 }

	PnEsSysEntry ::= SEQUENCE {
					  pnEsSysPasoIndex    IpAddress,
					  pnEsSysIndex        INTEGER,
					  pnEsSysTxFreq       DisplayString,
					  pnEsSysRxFreq       DisplayString,
					  pnEsSysTxPowerCont  INTEGER,
					  pnEsSysFrameID      INTEGER
					}

	pnEsSysPasoIndex OBJECT-TYPE
		SYNTAX		IpAddress 
		ACCESS		read-only
		STATUS		mandatory
		DESCRIPTION	"Pasolink IP Address Index"
		::= { pnEsSysEntry 1 }

	pnEsSysIndex OBJECT-TYPE
		SYNTAX		INTEGER{
					  no1-dirA(1),
					  no2-dirB(2)
					}
		ACCESS		read-only
		STATUS		mandatory
		::= { pnEsSysEntry 2 }

	pnEsSysTxFreq OBJECT-TYPE
		SYNTAX		DisplayString (SIZE (0..9))
		ACCESS		read-only
		STATUS		mandatory
		DESCRIPTION	"TX RF FREQUENCY(No.x) [MHz]  x=1 or 2
					TX RF FREQUENCY(DIR-y) [MHz] y=A or B
					  *)No.2 is available when Redundancy is 1+1(HS) or 1+1(TP).
					  *)DIR-A/DIR-B is available when Redundancy is 2-WAY."
		::= { pnEsSysEntry 3 }

	pnEsSysRxFreq OBJECT-TYPE
		SYNTAX		DisplayString (SIZE (0..9))
		ACCESS		read-only
		STATUS		mandatory
		DESCRIPTION	"RX RF FREQUENCY(No.x) [MHz]   x=1 or 2
					RX RF FREQUENCY(DIR-y) [MHz]  y=A or B
					  *)No.2 is available when Redundancy is 1+1(HS) or 1+1(TP).
					  *)DIR-A/DIR-B is available when Redundancy is 2-WAY."
		::= { pnEsSysEntry 4 }

	pnEsSysTxPowerCont OBJECT-TYPE
		SYNTAX		INTEGER (0..2)
		ACCESS		read-only
		STATUS		mandatory
		DESCRIPTION	"TX POWER CONTROL
					TX POWER CONTROL(DIR-y)   y=A or B 
					  0:Invalid,
					  1:MTPC,
					  2:ATPC
					
					  *)No.2 is not used.
					  *)DIR-A/DIR-B is available when Redundancy is 2-WAY."
		::= { pnEsSysEntry 5 }

	pnEsSysFrameID OBJECT-TYPE
		SYNTAX		INTEGER (0..32)
		ACCESS		read-only
		STATUS		mandatory
		DESCRIPTION	"FRAME ID(No.x)  x=1 or 2
					FRAME ID(DIR-y) y=A or B
					  0:Invalid,
					  Other: Frame ID Number.
					
					  *)No.2 is unavailable when Redundancy is 1+0.
					  *)No.2 is fixed to 0 when Redundancy is 1+0.
					  *)DIR-A and DIR-B is available when Redundancy is 2-WAY."
		::= { pnEsSysEntry 6 }


-----------------------------------------------
-- pnProvisioningGroup Group Definitions
-----------------------------------------------

 	pnProvCHTable OBJECT-TYPE
		SYNTAX		SEQUENCE OF PnProvCHEntry
		ACCESS		not-accessible
		STATUS		mandatory
		DESCRIPTION	"Prov Ch Table"
		::= { pnProvisioningGroup 1 }

	pnProvCHEntry OBJECT-TYPE
		SYNTAX		PnProvCHEntry
		ACCESS		not-accessible
		STATUS		mandatory
		INDEX		{
						pnProvCHPasoIndex
					}
		::= { pnProvCHTable 1 }

	PnProvCHEntry ::= SEQUENCE {
					  pnProvCHPasoIndex	IpAddress,
					  pnChUsage	OCTET STRING,
					  pnChCondition	OCTET STRING,
					  pnChImpedance	OCTET STRING,
					  pnMsAisGeneration INTEGER
 					}

	pnProvCHPasoIndex OBJECT-TYPE
		SYNTAX		IpAddress 
		ACCESS		read-only
		STATUS		mandatory
		DESCRIPTION	"Pasolink IP Address Index"
		::= { pnProvCHEntry 1 }

	pnChUsage OBJECT-TYPE
		SYNTAX		OCTET STRING (SIZE (48))
		ACCESS		read-only
		STATUS		mandatory
		DESCRIPTION	"CH USAGE(CHxx)
					xx=1-48
					  0:Invalid,
					  1:Not Used,
					  2:Used,
					  3:Used(LAN)
					
					  [Description]
					    Byte 0 = CH01(0:Invalid, 1:Not Used, 2:Used(E1), 3:Used(LAN))
					    Byte 1 = CH02
					    ...
					    Byte 46 = CH47 for E1 interface
					                   E3 CH01 for E3 interface
					    Byte 47 = CH48 for E1 interface
					                  E3 CH02 for E3 interface
					TRAP=eventTrapPnSTDCHUsage"
		::= { pnProvCHEntry  2 }

	pnChCondition OBJECT-TYPE
		SYNTAX		OCTET STRING (SIZE (6))
		ACCESS		read-only
		STATUS		mandatory
		DESCRIPTION	"CH CONDITION
					  [Description]
					    Byte 0 = CH USAGE ERROR REORT
					                  0:Invalid, 1:Not Report, 2:Report
					    Byte 1 = AIS ACTIVATION CONDITION
					                  0:Invalid, 1:LOF+HIGH BER 2:LOF
					    Byte 2 = AIS ACTIVATION DELAY
					                  0:Invalid, 1:Off, 2:On
					    Byte 3 = AIS GENERATED REPORT
					                  0:Invalid, 1:Not Report, 2:Report
					    Byte 4 = AIS RECEIVED REPORT
					                  0:Invalid, 1:Not Report, 2:Report
					    Byte 5 = AIS RECEIVED CONDITION
					                  0:Invalid, 1:Alarm, 2:Status
					TRAP=eventTrapPnSTDCHCondition"
		::= { pnProvCHEntry  3 }

	pnChImpedance OBJECT-TYPE
		SYNTAX		OCTET STRING (SIZE (10))
		ACCESS		read-only
		STATUS		mandatory
		DESCRIPTION	"E1 PORT IMPEDANCE
					  0:Invalid,
					  1:120[ohm],
					  2:75[ohm]
					
					  [Description]
					    BYTE0 = E1 PORT IMPEDANCE(CH1) (0:Invalid, 1:120[ohm], 2:75[ohm])
					    BYTE1 = E1 PORT IMPEDANCE(CH2)
					    BYTE2 = E1 PORT IMPEDANCE(CH3)
					    BYTE3 = E1 PORT IMPEDANCE(CH4)
					    BYTE4 = E1 PORT IMPEDANCE(CH5-8)
					    BYTE5 = E1 PORT IMPEDANCE(CH9-16)
					    BYTE6 = E1 PORT IMPEDANCE(CH17-24)
					    BYTE7 = E1 PORT IMPEDANCE(CH25-32)
					    BYTE8 = E1 PORT IMPEDANCE(CH33-40)
					    BYTE9 = E1 PORT IMPEDANCE(CH41-48)
					
					TRAP=eventTrapPnSTDCHImpedance"
		::= { pnProvCHEntry  4 }

	pnMsAisGeneration OBJECT-TYPE
		SYNTAX		INTEGER (0..2)
		ACCESS		read-only
		STATUS		mandatory
		DESCRIPTION	"MS-AIS GENERATION
					  0:Invalid,
					  1:Disabled,
					  2:Enabled
					TRAP=eventTrapPnSTDMSAisGeneration"
		::= { pnProvCHEntry  5 }

 	pnProvDXCTable OBJECT-TYPE
		SYNTAX		SEQUENCE OF PnProvDXCEntry
		ACCESS		not-accessible
		STATUS		mandatory
		DESCRIPTION	"Prov DXC Table"
		::= { pnProvisioningGroup 2 }

	pnProvDXCEntry OBJECT-TYPE
		SYNTAX		PnProvDXCEntry
		ACCESS		not-accessible
		STATUS		mandatory
		INDEX		{
						pnProvDXCPasoIndex
					}
		::= { pnProvDXCTable 1 }

	PnProvDXCEntry ::= SEQUENCE {
					  pnProvDXCPasoIndex	IpAddress,
					  pnDxcFunction	INTEGER,
					  pnDxcCHSetting	OCTET STRING,
					  pnDxcAssign	OCTET STRING
 					}

	pnProvDXCPasoIndex OBJECT-TYPE
		SYNTAX		IpAddress 
		ACCESS		read-only
		STATUS		mandatory
		DESCRIPTION	"Pasolink IP Address Index"
		::= { pnProvDXCEntry 1 }

        pnDxcFunction OBJECT-TYPE
		SYNTAX		INTEGER (0..2)
		ACCESS		read-only
		STATUS		mandatory
		DESCRIPTION	"DXC FUNCTION
					  0:Invalid,
					  1:Disabled,
					  2:Enabled
					TRAP=eventTrapPnSTDDxcFunction"
		::= { pnProvDXCEntry 2 }

	pnDxcCHSetting OBJECT-TYPE
		SYNTAX		OCTET STRING (SIZE (156))
		ACCESS		read-only
		STATUS		mandatory
		DESCRIPTION	"DXC CH Setting

					  [Description]
					    Byte 0 = CH01
					    ...
					    Byte 47 = CH48
					    Byte 52 = DIR-A CH01 Setting
					    ...
					    Byte 99 = DIR-A CH48 Setting
					    Byte 104 = DIR-B CH01 Setting
					    ...
					    Byte 151 = DIR-B CH48 Setting

					    Bit 0-5 (000000=Invalid, 000001=CH1,...,110000=CH48)
					    Bit 6-7 (00=LINE,01=DIR-A,10=DIR-B,11=LAN)
					TRAP=eventTrapPnSTDDxcCHSetting"
		::= { pnProvDXCEntry 3 }

	pnDxcAssign OBJECT-TYPE
		SYNTAX		OCTET STRING (SIZE (48))
		ACCESS		read-only
		STATUS		mandatory
		DESCRIPTION	"This item is not used.
				 DXC ASSIGNMENT CHANGED
					  0:INVALID,
					  1:PORT1,
					  2:PORT2,
					  ...
					  47:PORT47,
					  48:PORT48
					
					  [Description]
					    Byte 0 = CH01 (0:Invalid, X:Port X,  x=1~48)
					    Byte 1 = CH02
					    ...
					    Byte 46 = CH47
					    Byte 47 = CH48
					TRAP=eventTrapPnSTDDxcAssign"
		::= { pnProvDXCEntry 4 }

 	pnProvBERThresholdTable OBJECT-TYPE
		SYNTAX		SEQUENCE OF PnProvBERThresholdEntry
		ACCESS		not-accessible
		STATUS		mandatory
		DESCRIPTION	"Prov BER Threshold Table"
		::= { pnProvisioningGroup 3 }

	pnProvBERThresholdEntry OBJECT-TYPE
		SYNTAX		PnProvBERThresholdEntry
		ACCESS		not-accessible
		STATUS		mandatory
		INDEX		{
						pnProvBERThresholdPasoIndex
					}
		::= { pnProvBERThresholdTable 1 }

	PnProvBERThresholdEntry ::= SEQUENCE {
					  pnProvBERThresholdPasoIndex	IpAddress,
					  pnProvBERThreshold	OCTET STRING
 					}

	pnProvBERThresholdPasoIndex OBJECT-TYPE
		SYNTAX		IpAddress 
		ACCESS		read-only
		STATUS		mandatory
		DESCRIPTION	"Pasolink IP Address Index"
		::= { pnProvBERThresholdEntry 1 }

	pnProvBERThreshold OBJECT-TYPE
		SYNTAX		OCTET STRING (SIZE (8))
		ACCESS		read-only
		STATUS		mandatory
		DESCRIPTION	"BER THRESHOLD SETTING
					  
					  [Description]
					    Byte 0 = HIGH BER THRESHOLD/HIGH BER THRESHOLD(DIR-A)  
					                (0:INVALID, 1:1E-3, 2:1E-4, 3:1E-5)
					    Byte 1 = HIGH BER THRESHOLD(DIR-B) 
					                (0:INVALID, 1:1E-3, 2:1E-4, 3:1E-5)
					    Byte 2 = LOW BER THRESHOLD/LOW BER THRESHOLD(DIR-A) 
					                (0:INVALID, 1:1E-6, 2:1E-7, 3:1E-8, 4:1E-9)
					    Byte 3 = LOW BER THRESHOLD(DIR-B) 
					                (0:INVALID, 1:1E-6, 2:1E-7, 3:1E-8, 4:1E-9)
					    Byte 4 = E-BER(DMR)
					                (0:INVALID, 1:1E-3, 2:1E-4, 3:1E-5)
					    Byte 5 = SD(DMR)
					                (0:INVALID, 1:1E-6, 2:1E-7, 3:1E-8, 4:1E-9)
					    Byte 6 = E-BER(MUX)
					                 (0:INVALID, 1:1E-3, 2:1E-4, 3:1E-5)
					    Byte 7 = SD(MUX)
					                (0:INVALID, 1:1E-6, 2:1E-7, 3:1E-8, 4:1E-9)
					TRAP=eventTrapPnSTDBERThreshold"
		::= { pnProvBERThresholdEntry 2 }

 	pnProvSubIntfcTable OBJECT-TYPE
		SYNTAX		SEQUENCE OF PnProvSubIntfcEntry
		ACCESS		not-accessible
		STATUS		mandatory
		DESCRIPTION	"Prov Sub Intfc Table"
		::= { pnProvisioningGroup 4 }

	pnProvSubIntfcEntry OBJECT-TYPE
		SYNTAX		PnProvSubIntfcEntry
		ACCESS		not-accessible
		STATUS		mandatory
		INDEX		{
						pnProvSubIntfcPasoIndex
					}
		::= { pnProvSubIntfcTable 1 }

	PnProvSubIntfcEntry ::= SEQUENCE {
					  pnProvSubIntfcPasoIndex	IpAddress,
					  pnProvSubIntfc	OCTET STRING
 					}

	pnProvSubIntfcPasoIndex OBJECT-TYPE
		SYNTAX		IpAddress 
		ACCESS		read-only
		STATUS		mandatory
		DESCRIPTION	"Pasolink IP Address Index"
		::= { pnProvSubIntfcEntry 1 }

	pnProvSubIntfc OBJECT-TYPE
		SYNTAX		OCTET STRING (SIZE (4))
		ACCESS		read-only
		STATUS		mandatory
		DESCRIPTION	"SUB INTERFACE
					  0:INVALID
					  1:NOT USED
					  2:E1 WAYSIDE+SC LAN(SC)
					  3:E1 WAYSIDE
					  4:SC LAN(WAYSIDE)
					  5:SC LAN(SC)
				 *)Byte 1-3 are fixed to 0.
					TRAP=eventTrapPnSTDSubIntfc"
		::= { pnProvSubIntfcEntry 2 }

 	pnProvSCAssignmentTable OBJECT-TYPE
		SYNTAX		SEQUENCE OF PnProvSCAssignmentEntry
		ACCESS		not-accessible
		STATUS		mandatory
		DESCRIPTION	"Prov SC Assignment Table"
		::= { pnProvisioningGroup 5 }

	pnProvSCAssignmentEntry OBJECT-TYPE
		SYNTAX		PnProvSCAssignmentEntry
		ACCESS		not-accessible
		STATUS		mandatory
		INDEX		{
						pnProvSCAssignmentPasoIndex
					}
		::= { pnProvSCAssignmentTable 1 }

	PnProvSCAssignmentEntry ::= SEQUENCE {
					  pnProvSCAssignmentPasoIndex	IpAddress,
					  pnProvSCAssign	OCTET STRING
 					}

	pnProvSCAssignmentPasoIndex OBJECT-TYPE
		SYNTAX		IpAddress 
		ACCESS		read-only
		STATUS		mandatory
		DESCRIPTION	"Pasolink IP Address Index"
		::= { pnProvSCAssignmentEntry 1 }

	pnProvSCAssign OBJECT-TYPE
		SYNTAX		OCTET STRING (SIZE (8))
		ACCESS		read-only
		STATUS		mandatory
		DESCRIPTION	"SC ASSIGNMENT
					  [Description]
					    Byte 0 = RS-232C-1
					         (0:INVALID, 1:NOT USED, 2:SC1, 3:SC2,
					          4:SC3, 5:SC4, 16:E1(MUX), 17:F1(MUX),
					          19:E1(DMR), 20:F1(DMR))
					    Byte 1 = RS-232C-2
					         (0:INVALID, 1:NOT USED, 2:SC1, 3:SC2,
					          4:SC3, 5:SC4, 16:E1(MUX), 17:F1(MUX),
					          19:E1(DMR), 20:F1(DMR))
					    Byte 2 = V11-1
					         (0:INVALID, 1:NOT USED, 2:SC1, 3:SC2, 
					          4:SC3, 5:SC4, 16:E1(MUX), 17:F1(MUX), 
					          18:DCCr(MUX), 19:E1(DMR), 20:F1(DMR), 
					          21:DCCr(DMR))
					    Byte 3 = V11-2
					         (0:INVALID, 1:NOT USED, 2:SC1, 3:SC2, 
					          4:SC3, 5:SC4, 16:E1(MUX), 17:F1(MUX), 
					          18:DCCr(MUX), 19:E1(DMR), 20:F1(DMR), 
					          21:DCCr(DMR))
					    Byte 4 = SC LAN1
					         (0:INVALID, 1:NOT USED, 2:SC1, 10:SC1-2,
					          14:SC1-4, 16:E1(MUX), 17:F1(MUX), 18:DCCr(MUX),
					          19:E1(DMR), 20:F1(DMR), 21:DCCr(DMR))
					    Byte 5 = SC LAN2
					         (0:INVALID, 1:NOT USED, 2:SC1, 10:SC1-2,
					          14:SC1-4, 16:E1(MUX), 17:F1(MUX), 18:DCCr(MUX),
					          19:E1(DMR), 20:F1(DMR), 21:DCCr(DMR))
					    Byte 6 = V11-1 DIRECTION SETTING
					         (0:INVALID, 1:CO-DIRECTIONAL, 2:CONTRA-DIRECTIONAL)
					    Byte 7 = V11-2 DIRECTION SETTING
					         (0:INVALID, 1:CO-DIRECTIONAL, 2:CONTRA-DIRECTIONAL)
					
					TRAP=eventTrapPnSTDSCAssign"
		::= { pnProvSCAssignmentEntry 2 }

 	pnProvLANPortSetTable OBJECT-TYPE
		SYNTAX		SEQUENCE OF PnProvLANPortSetEntry
		ACCESS		not-accessible
		STATUS		mandatory
		DESCRIPTION	"Prov LAN Port Set Table"
		::= { pnProvisioningGroup 6 }

	pnProvLANPortSetEntry OBJECT-TYPE
		SYNTAX		PnProvLANPortSetEntry
		ACCESS		not-accessible
		STATUS		mandatory
		INDEX		{
						pnProvLANPortSetPasoIndex
					}
		::= { pnProvLANPortSetTable 1 }

	PnProvLANPortSetEntry ::= SEQUENCE {
					  pnProvLANPortSetPasoIndex	IpAddress,
					  pnProvLANPortSet	OCTET STRING
 					}

	pnProvLANPortSetPasoIndex OBJECT-TYPE
		SYNTAX		IpAddress 
		ACCESS		read-only
		STATUS		mandatory
		DESCRIPTION	"Pasolink IP Address Index"
		::= { pnProvLANPortSetEntry 1 }

	pnProvLANPortSet OBJECT-TYPE
		SYNTAX  	OCTET STRING (SIZE (41))
		ACCESS		read-only
		STATUS		mandatory
		DESCRIPTION	"LAN PORT SETTING
					  [Description]
					  Byte 0 = SWITCHING FUNCTION
					       (0:INVALID, 1:DISABLED(No Report), 2:ENABLED(Report))
					
					  Byte 1 = SPEED & DUPLEX PORT1
					  Byte 2 = SPEED & DUPLEX PORT2
					  Byte 3 = SPEED & DUPLEX PORT3
					  Byte 4 = SPEED & DUPLEX PORT4
					  Byte 5 = INTFC(2) SPEED & DUPLEX PORT1
					  Byte 6 = INTFC(2) SPEED & DUPLEX PORT2
					       (0:INVALID, 1:AUTONEG(AUTO-MDI/MDIX),
					        2:10M-HALF(MDI), 3:10M-FULL(MDI), 
					        4:100M-HALF(MDI), 5:100M-FULL(MDI), 
					        6:10M-HALF(MDIX), 7:10M-FULL(MDIX), 
					        8:100M-HALF(MDIX), 9:100M-FULL(MDIX))
					
					  Byte 7 = FLOW CONTROL PORT1
					  Byte 8 = FLOW CONTROL PORT2
					  Byte 9 = FLOW CONTROL PORT3
					  Byte 10 = FLOW CONTROL PORT4
					  Byte 11 = INTFC(2) FLOW CONTROL PORT1
					  Byte 12 = INTFC(2) FLOW CONTROL PORT2
					       (0:INVALID, 1:OFF, 2:ON)
					
					  Byte 13 = COLLISION REPORT PORT1
					  Byte 14 = COLLISION REPORT PORT2
					  Byte 15 = COLLISION REPORT PORT3
					  Byte 16 = COLLISION REPORT PORT4
					  Byte 17 = INTFC(2) COLLISION REPORT PORT1
					  Byte 18 = INTFC(2) COLLISION REPORT PORT2
					       (0:INVALID, 1:DISABLED(No Report), 2:ENABLED(Report))
					
					  Byte 19 = LINK LOSS FORWARDING PORT1
					  Byte 20 = LINK LOSS FORWARDING PORT2
					  Byte 21 = LINK LOSS FORWARDING PORT3
					  Byte 22 = LINK LOSS FORWARDING PORT4
					  Byte 23 = INTFC(2) LINK LOSS FWD PORT1
					  Byte 24 = INTFC(2) LINK LOSS FWD PORT2
					       (0:INVALID, 1:DISABLED, 2:ENABLED)
					
					  Byte 25 = LOCK SOURCE SETTING
					       (0:INVALID, 1:INTERNAL CLOCK, 
					        2:DMR -> INTERNAL CLOCK)
					
					  Byte 26 = 2M FRAMING PORT1
					  Byte 27 = 2M FRAMING PORT2
					  Byte 28 = 2M FRAMING PORT3
					  Byte 29 = 2M FRAMING PORT4
					       (0:NOT USED, 1:PCM30, 2:PCM30C, 
					        3:PCM31, 4:PCM31C)
					
					  Byte 30 = PORT1 USAGE
					  Byte 31 = PORT2 USAGE
					  Byte 32 = PORT3 USAGE
					  Byte 33 = PORT4 USAGE
					  Byte 34 = INTFC(2) PORT1 USAGE
					  Byte 35 = INTFC(2) PORT2 USAGE
					       (0:INVALID, 1:NOT USED, 2:USED)
					  Byte 36 = SUB SWITCHING FUNCTION
						(0:INVALID, 1:DISABLED, 2:ENABLED)
					  Byte 37 = MEDIA TYPE
						(0:INVALID, 1:SFP, 2:RJ-45)
					  Byte 38 = GbE SPEED & DUPLEX
						(0:INVALID, 
						 1:RESERVE1, 
						 2:AUTONEG(AUTO 1000MB FULL DUPLEX), 
						 3:AUTONEG(AUTO MDI/MDIX), 
						 4:RESERVE4, 
						 5:RESERVE5, 
						 6:100MB-FULL(MDI), 
						 7:100MB-FULL(MDIX), 
						 8:100MB-HALF(MDI), 
						 9:100MB-HALF(MDIX), 
						 10:10MB-FULL(MDI), 
						 11:10MB-FULL(MDIX), 
						 12:10MB-HALF(MDI), 
						 13:10MB-HALF(MDIX))
					  Byte 39 = GbE LINK LOSS FORWARDING
						(0:INVALID, 1:DISABLED, 2:ENABLED)
					  Byte 40 = GbE FLOW CONTROL(0:INVALID, 1:OFF, 2:ON)
					TRAP=eventTrapPnSTDLanPortSetting"
		::= { pnProvLANPortSetEntry 2 }


 	pnProvALSTable OBJECT-TYPE
		SYNTAX		SEQUENCE OF PnProvALSEntry
		ACCESS		not-accessible
		STATUS		mandatory
		DESCRIPTION	"Prov ALS Table"
		::= { pnProvisioningGroup 7 }

	pnProvALSEntry OBJECT-TYPE
		SYNTAX		PnProvALSEntry
		ACCESS		not-accessible
		STATUS		mandatory
		INDEX		{
						pnProvALSPasoIndex
					}
		::= { pnProvALSTable 1 }

	PnProvALSEntry ::= SEQUENCE {
					  pnProvALSPasoIndex	IpAddress,
					  pnAlsFunc	OCTET STRING
 					}

	pnProvALSPasoIndex OBJECT-TYPE
		SYNTAX		IpAddress 
		ACCESS		read-only
		STATUS		mandatory
		DESCRIPTION	"Pasolink IP Address Index"
		::= { pnProvALSEntry 1 }

	pnAlsFunc OBJECT-TYPE
		SYNTAX		OCTET STRING (SIZE (2))
		ACCESS		read-only
		STATUS		mandatory
		DESCRIPTION	"ALS FUNCTION
				   [Description]
					Byte0 = ALS FUNCTION
					   0:Invalid,
					   1:Disabled,
					   2:Enabled
					 Byte1 = ALS INTERVAL
					   0:Invalid,
					   1:60sec,
					   2:180sec,
					   3:300sec
					TRAP=eventTrapPnSTDAlsFunction"
		::= { pnProvALSEntry 2 }

	pnProvTxPowerContTable OBJECT-TYPE
		SYNTAX		SEQUENCE OF PnProvTxPowerContEntry
		ACCESS		not-accessible
		STATUS		mandatory
		DESCRIPTION	"PROV TX Power Cont Table"
		::= { pnProvisioningGroup 8 }

	pnProvTxPowerContEntry OBJECT-TYPE
		SYNTAX		PnProvTxPowerContEntry
		ACCESS		not-accessible
		STATUS		mandatory
		INDEX		{
						pnProvTxPowerContPasoIndex,
						pnProvTxPowerContIndex
					}
		::= { pnProvTxPowerContTable 1 }

	PnProvTxPowerContEntry ::= SEQUENCE {
	                                  pnProvTxPowerContPasoIndex IpAddress,
					  pnProvTxPowerContIndex  INTEGER,
					  pnProvTxPowerContValue  OCTET STRING
					}

	pnProvTxPowerContPasoIndex OBJECT-TYPE
		SYNTAX		IpAddress 
		ACCESS		read-only
		STATUS		mandatory
		DESCRIPTION	"Pasolink IP Address Index"
		::= { pnProvTxPowerContEntry 1 }

	pnProvTxPowerContIndex OBJECT-TYPE
		SYNTAX		INTEGER{
					  no1-dirA(1),
					  no2-dirB(2)
					}
		ACCESS		read-only
		STATUS		mandatory
		DESCRIPTION	"PROV TX Power Cont Index
					 1:No.1 when EQUIPMENT CONFIG is TERM.
					   DIR-A when EQUIPMENT CONFIG is 2-way
					 2:No.2 when EQUIPMENT CONFIG is TERM.
					   DIR-B when EQUIPMENT CONFIG is 2-way."
		::= { pnProvTxPowerContEntry 2 }

	pnProvTxPowerContValue OBJECT-TYPE
		SYNTAX		OCTET STRING (SIZE (9))
		ACCESS		read-only
		STATUS		mandatory
		DESCRIPTION	"TX POWER CTRL
					
					  [Description]
						Byte 0
						MTPC TX POWER (signed char)
						Byte 1
						 ATPC THRESHOLD LEVEL <integral number>
						(signed char)
						Byte 2
						 ATPC THRESHOLD LEVEL <a place of decimal>
						  This value is fixed to 0.
						Byte 3
						 ADDITIONAL ATT
						  (char)
						Byte 4
						 ATPC(MAX)
						  (signed char)
						Byte 5
						ATPC(MIN)
						  (signed char)
						Byte 6
						 HYSTERESIS
						  This is fixed value.
						Byte 7
						 ATPC POWER MODE
						   0:INVALID, 1:HOLD, 2:MAX, 3:MIN
						Byte 8
						  ODU COMM ALARM MODE
						  This is fixed value.

						*)In case of Byte 0 - 5, the range of each value is difined in the mib of 
						  invTRUProvRangeInfoValue.
					TRAP=eventTrapPnSTDTxPowerContValue"
		::= { pnProvTxPowerContEntry 3 }

 	pnProvSWCondTable OBJECT-TYPE
		SYNTAX		SEQUENCE OF PnProvSWCondEntry
		ACCESS		not-accessible
		STATUS		mandatory
		DESCRIPTION	"Prov SW Cond Table"
		::= { pnProvisioningGroup 9 }

	pnProvSWCondEntry OBJECT-TYPE
		SYNTAX		PnProvSWCondEntry
		ACCESS		not-accessible
		STATUS		mandatory
		INDEX		{
						pnProvSWCondPasoIndex
					}
		::= { pnProvSWCondTable 1 }

	PnProvSWCondEntry ::= SEQUENCE {
					  pnProvSWCondPasoIndex	IpAddress,
					  pnProvSWCondTxRxSW	OCTET STRING,
					  pnProvSWCondAPS	OCTET STRING
 					}

	pnProvSWCondPasoIndex OBJECT-TYPE
		SYNTAX		IpAddress 
		ACCESS		read-only
		STATUS		mandatory
		DESCRIPTION	"Pasolink IP Address Index"
		::= { pnProvSWCondEntry 1 }

	pnProvSWCondTxRxSW OBJECT-TYPE
		SYNTAX		OCTET STRING (SIZE (5))
		ACCESS		read-only
		STATUS		mandatory
		DESCRIPTION	"CONDITION for TX/RX SW
					  
					  [Description]
					  Byte 0 = TX SW PRIORITY
					      (0:INVALID, 1:NON PRIORITY, 2:PRIORITY No.1)
					  Byte 1 = RX SW PRIORITY
					      (0:INVALID, 1:NON PRIORITY, 2:PRIORITY No.1)
					  Byte 2 = RX SW MAINTENANCE MODE
					      (0:INVALID, 1:MANUAL, 2:FORCED)
					  Byte 3 = RX SW CONDITION-EARLY WARNING
					      (0:INVALID, 1:INCLUDED EW, 2:EXCLUDED EW)
					  Byte 4 = RX SW CONDITION-XPIC RESET
					      (0:INVALID, 1:INCLUDED CROSS RESET, 2:EXCLUDED CROSS RESET)
					TRAP=eventTrapPnSTDSWCondTxRx"
		::= { pnProvSWCondEntry 2 }

	pnProvSWCondAPS OBJECT-TYPE
		SYNTAX		OCTET STRING (SIZE (7))
		ACCESS		read-only
		STATUS		mandatory
		DESCRIPTION	"CONDITION for APS
					
					  [Description]
					  Byte 0 = APS ALARM PRIORITY 
					      (0:INVALID, 1:Manual, 2:FORCED)
					  Byte 1 = APS CONDITION-SF
					      (0:INVALID, 1:PRIORITY HIGH, 2:PRIORITY LOW)
					  Byte 2 = APS CONDITION-SD
					      (0:INVALID, 1:INCLUDED SD, 2:EXCLUDED SD)
					  Byte 3 = LOCK IN USAGE (0:INVALID, 1:NOT USED, 2:USED)
					  Byte 4 = LOCK IN COUNT (VALUE(INT 0-255))
					  Byte 5 = LOCK IN DETECT TIME (VALUE(INT 0-60))
					  Byte 6 = LOCK IN HOLD TIME (VALUE(INT 0-48))
					TRAP=eventTrapPnSTDSWCondAPS"
		::= { pnProvSWCondEntry 3 }


	pnProvRelayTable OBJECT-TYPE
		SYNTAX		SEQUENCE OF PnProvRelayEntry
		ACCESS		not-accessible
		STATUS		mandatory
		DESCRIPTION	"Prov Relay Table"
		::= { pnProvisioningGroup 10 }

	pnProvRelayEntry OBJECT-TYPE
		SYNTAX		PnProvRelayEntry
		ACCESS		not-accessible
		STATUS		mandatory
		INDEX		{
						pnProvRelayPasoIndex
					}
		::= { pnProvRelayTable 1 }

	PnProvRelayEntry ::= SEQUENCE {
					  pnProvRelayPasoIndex	IpAddress,
					  pnProvRelayConfigData	OCTET STRING,
					  pnProvRelayClusterAssign	OCTET STRING
 					}

	pnProvRelayPasoIndex OBJECT-TYPE
		SYNTAX		IpAddress 
		ACCESS		read-only
		STATUS		mandatory
		DESCRIPTION	"Pasolink IP Address Index"
		::= { pnProvRelayEntry 1 }

	pnProvRelayConfigData OBJECT-TYPE
		SYNTAX		OCTET STRING (SIZE (48))
		ACCESS		read-only
		STATUS		mandatory
		DESCRIPTION	"RELAY CONFIGURATION CHANGED
					
					  [Description]
					  (Relay x (x:1~6))
					   [START BIT] = 64 * (x - 1)
					
					    Bit (0 + [START BIT]) = MAINT (Remark1)
					    Bit (1 + [START BIT]) = PS ALARM1 (Remark2)
					    Bit (2 + [START BIT]) = PS ALARM2 (Remark2)
					    Bit (3 + [START BIT]) = (FIXED to 0)
					    Bit (4 + [START BIT]) = (FIXED to 0)
					    Bit (5 + [START BIT]) = (FIXED to 0)
					    Bit (6 + [START BIT]) = (FIXED to 0)
					    Bit (7 + [START BIT]) = CPU ALARM (Remark2)
					    Bit (8 + [START BIT]) = ODU ALARM1 (Remark7)
					    Bit (9 + [START BIT]) = ODU ALARM2 (Remark7)
					    Bit (10 + [START BIT]) = IDU ALARM (Remark7)
					    Bit (11 + [START BIT]) = (FIXED to 0)
					    Bit (12 + [START BIT]) = (FIXED to 0)
					    Bit (13 + [START BIT]) = (FIXED to 0)
					    Bit (14 + [START BIT]) = (FIXED to 0)
					    Bit (15 + [START BIT]) = (FIXED to 0)
					    Bit (16 + [START BIT]) = TX POWER ALARM1 (Remark7)
					    Bit (17 + [START BIT]) = TX POWER ALARM2 (Remark7)
					    Bit (18 + [START BIT]) = TX IN LEV ALARM1 (Remark7)
					    Bit (19 + [START BIT]) = TX IN LEV ALARM2 (Remark7)
					    Bit (20 + [START BIT]) = RX LEV ALARM1 (Remark7)
					    Bit (21 + [START BIT]) = RX LEV ALARM2 (Remark7)
					    Bit (22 + [START BIT]) = APC ALARM1 (Remark7)
					    Bit (23 + [START BIT]) = APC ALARM2 (Remark7)
					    Bit (24 + [START BIT]) = IF CABLE SHORT ALARM1 (Remark7)
					    Bit (25 + [START BIT]) = IF CABLE SHORT ALARM2 (Remark7)
					    Bit (26 + [START BIT]) = ODU CPU ALARM1 (Remark7)
					    Bit (27 + [START BIT]) = ODU CPU ALARM2 (Remark7)
					    Bit (28 + [START BIT]) = (FIXED to 0)
					    Bit (29 + [START BIT]) = (FIXED to 0)
					    Bit (30 + [START BIT]) = (FIXED to 0)
					    Bit (31 + [START BIT]) = (FIXED to 0)
					    Bit (32 + [START BIT]) = MOD ALARM1 (Remark7)
					    Bit (33 + [START BIT]) = MOD ALARM2 (Remark7)
					    Bit (34 + [START BIT]) = DEM ALARM1 (Remark7)
					    Bit (35 + [START BIT]) = DEM ALARM2 (Remark7)
					    Bit (36 + [START BIT]) = CH INPUT LOSS (Remark7)
					    Bit (37 + [START BIT]) = CH AIS RECEIVED (Remark7)
					    Bit (38 + [START BIT]) = CH AIS GENERATED (Remark7)
					    Bit (39 + [START BIT]) = CH USAGE ERROR (Remark7)
					    Bit (40 + [START BIT]) = LOW BER ALARM1 (Remark7)
					    Bit (41 + [START BIT]) = LOW BER ALARM2 (Remark7)
					    Bit (42 + [START BIT]) = HIGH BER ALARM1 (Remark7)
					    Bit (43 + [START BIT]) = HIGH BER ALARM2 (Remark7)
					    Bit (44 + [START BIT]) = STM-1 TF ALARM (Remark7)
					    Bit (45 + [START BIT]) = STM-1 SLOS (Remark7)
					    Bit (46 + [START BIT]) = STM-1 RLOS (Remark7)
					    Bit (47 + [START BIT]) = LAN LINK ALARM (Remark7)
					    Bit (48 + [START BIT]) = LOF1 (Remark7)
					    Bit (49 + [START BIT]) = LOF2 (Remark7)
					    Bit (50 + [START BIT]) = X REF ALARM1 (Remark7)
					    Bit (51 + [START BIT]) = X REF ALARM2 (Remark7)
					    Bit (52 + [START BIT]) = X CTRL ALARM1 (Remark7)
					    Bit (53 + [START BIT]) = X CTRL ALARM2 (Remark7)
					    Bit (54 + [START BIT]) = SC LAN LINK ALARM (Remark7)
					    Bit (55 + [START BIT]) = WS INPUT LOSS (Remark7)
					    Bit (56 + [START BIT]) = CLUSTER ALARM1 (Remark6)
					    Bit (57 + [START BIT]) = CLUSTER ALARM2 (Remark5)
					    Bit (58 + [START BIT]) = CLUSTER ALARM3 (Remark4)
					    Bit (59 + [START BIT]) = CLUSTER ALARM4 (Remark3)
					    Bit (60 + [START BIT]) = HK1 OUTPUT (Remark6)
					    Bit (61 + [START BIT]) = HK2 OUTPUT (Remark5)
					    Bit (62 + [START BIT]) = HK3 OUTPUT (Remark4)
					    Bit (63 + [START BIT]) = HK4 OUTPUT (Remark3)
					
					  Remark1 : The value of Relay 1 is fixed to  1. 
					            The value of the other Relay is fixed to 0.
					  Remark2 : The value of Relay 3 is fixed to 1. 
					            The value of the other Relay is fixed to 0.
					  Remark3 : The value of Relay 3 is fixed to 1. 
					            The value of the other Relay is fixed to 0.
					  Remark4 : The value of Relay 4 is fixed to 1. 
					            The value of the other Relay is fixed to 0.
					  Remark5 : The value of Relay 5 is fixed to 1. 
					            The value of the other Relay is fixed to 0.
					  Remark6 : The value of Relay 6 is fixed to 1. 
					            The value of the other Relay is fixed to 0.
					  Remark7 : The value of Relay 1 and Relay 2 is fixed to 0. 
					            The value of the other Relay is 0 and 1.
					
					TRAP=eventTrapPnSTDRelayConfigData"
		::= { pnProvRelayEntry 2 }

	pnProvRelayClusterAssign OBJECT-TYPE
		SYNTAX		OCTET STRING (SIZE (4))
		ACCESS		read-only
		STATUS		mandatory
		DESCRIPTION	"CLUSTER INPUT
					  0:Invalid,
					  1:Disabled,
					  2:Enabled)
					
					  [Description]
					  Byte 0 = CLUSTER1 INPUT (0:Invalid, 1:Disabled, 2:Enabled)
					  Byte 1 = CLUSTER2 INPUT
					  Byte 2 = CLUSTER3 INPUT
					  Byte 3 = CLUSTER4 INPUT
					TRAP=eventTrapPnSTDRelayClusterAssign"
		::= { pnProvRelayEntry 3 }

	pnProvTCNTresholdGroup OBJECT IDENTIFIER
		::= { pnProvisioningGroup 11 }

	pnProvTCNThreshold15minTotalTable OBJECT-TYPE
		SYNTAX		SEQUENCE OF PnProvTCNThreshold15minTotalEntry
		ACCESS		not-accessible
		STATUS		mandatory
		DESCRIPTION	"Prov TCN Threshold 15min Total Table"
		::= { pnProvTCNTresholdGroup 1 }

	pnProvTCNThreshold15minTotalEntry OBJECT-TYPE
		SYNTAX		PnProvTCNThreshold15minTotalEntry
		ACCESS		not-accessible
		STATUS		mandatory
		INDEX		{
						pnProvTCNThreshold15minTotalPasoIndex,
						pnProvTCNThreshold15minTotalWPIndex,
						pnProvTCNThreshold15minTotalORIndex
					}
		::= { pnProvTCNThreshold15minTotalTable 1 }

	PnProvTCNThreshold15minTotalEntry ::= SEQUENCE {
					  pnProvTCNThreshold15minTotalPasoIndex IpAddress,
					  pnProvTCNThreshold15minTotalWPIndex  INTEGER,
					  pnProvTCNThreshold15minTotalORIndex  INTEGER,
					  pnProvTCNThreshold15minTotalValue    OCTET STRING
					}

	pnProvTCNThreshold15minTotalPasoIndex OBJECT-TYPE
		SYNTAX		IpAddress 
		ACCESS		read-only
		STATUS		mandatory
		DESCRIPTION	"Pasolink IP Address Index"
		::= { pnProvTCNThreshold15minTotalEntry 1 }

	pnProvTCNThreshold15minTotalWPIndex OBJECT-TYPE
		SYNTAX		INTEGER{
					  working-MUX(1),
					  protection-MUX(2),
					  working-DMR-dirA(3),
					  protection-DMR-dirB(4)
					}
		ACCESS		read-only
		STATUS		mandatory
		DESCRIPTION	"TCN 15min Current Total Working/Protection Index
					  1:Working(MUX),
					  2:Protection(MUX),
					  3:Working(DMR)/Working(DIR-A)
					  4:Protection(DMR)/Working(DIR-B)
					
					  *)MUX side is not used when using LAN.
					  *)Protection is only used when APS function is used.
					  *)DIR-* is only used when Redundancy is 2-Way.
					"
		::= { pnProvTCNThreshold15minTotalEntry  2 }

	pnProvTCNThreshold15minTotalORIndex OBJECT-TYPE
		SYNTAX		INTEGER{
					  occur(1),
					  recover(2)
					}
		ACCESS		read-only
		STATUS		mandatory
		DESCRIPTION	"TCN Threshold 15min Total Occur/Recover Index
					  1:Occur,
					  2:Recover"
		::= { pnProvTCNThreshold15minTotalEntry  3 }

	pnProvTCNThreshold15minTotalValue OBJECT-TYPE
		SYNTAX		OCTET STRING (SIZE (24))
		ACCESS		read-only
		STATUS		mandatory
		DESCRIPTION	"TCN THRESHOLD 15MIN TOTAL
					
					  [Description]
					  (Byte 0 - Byte 3)   = OFS TCN THRESHOLD TOTAL-15min (0 - 900)
					  (Byte 4 - Byte 7)   = UAS TCN THRESHOLD TOTAL-15min (0 - 900)
					  (Byte 8 - Byte 11)  = ES TCN THRESHOLD TOTAL-15min  (0 - 900)
					  (Byte 12 - Byte 15) = SES TCN THRESHOLD TOTAL-15min (0 - 900)
					  (Byte 16 - Byte 19) = BBE TCN THRESHOLD TOTAL-15min 
					                       (PDH(Bit Rate = 10MB)  : 0 - 804600   
					                        PDH(Bit Rate = 20MB)  : 0 - 804600
					                        PDH(Bit Rate = 40MB)  : 0 - 804600
					                        PDH(Bit Rate = 80MB)  : 0 - 1611000
					                        PDH(Bit Rate = 100MB) : 0 - 1611000
					                        SDH(Bit Rate = 156MB) : 0 - 2159100)
					  (Byte 20 - Byte 23) = SEP TCN THRESHOLD TOTAL-15min (0 - 900)
					TRAP=eventTrapPnSTDTCNTreshold15minTotal"
		::= { pnProvTCNThreshold15minTotalEntry 4 }

	pnProvTCNThreshold15minCHTable OBJECT-TYPE
		SYNTAX		SEQUENCE OF PnProvTCNThreshold15minCHEntry
		ACCESS		not-accessible
		STATUS		mandatory
		DESCRIPTION	"PROV TCN Threshold 15min CH Table"
		::= { pnProvTCNTresholdGroup 2 }

	pnProvTCNThreshold15minCHEntry OBJECT-TYPE
		SYNTAX		PnProvTCNThreshold15minCHEntry
		ACCESS		not-accessible
		STATUS		mandatory
		INDEX		{
						pnProvTCNThreshold15minCHPasoIndex,
						pnProvTCNThreshold15minCHIndex,
						pnProvTCNThreshold15minCHORIndex
					}
		::= { pnProvTCNThreshold15minCHTable 1 }

	PnProvTCNThreshold15minCHEntry ::= SEQUENCE {
					  pnProvTCNThreshold15minCHPasoIndex    IpAddress,
					  pnProvTCNThreshold15minCHIndex    INTEGER,
					  pnProvTCNThreshold15minCHORIndex  INTEGER,
					  pnProvTCNThreshold15minCHValue    OCTET STRING
					}

	pnProvTCNThreshold15minCHPasoIndex OBJECT-TYPE
		SYNTAX		IpAddress 
		ACCESS		read-only
		STATUS		mandatory
		DESCRIPTION	"Pasolink IP Address Index"
		::= { pnProvTCNThreshold15minCHEntry 1 }

	pnProvTCNThreshold15minCHIndex OBJECT-TYPE
		SYNTAX		INTEGER{
					  ch-A(1),
					  ch-B(2),
					  ch-C(3),
					  ch-D(4)
					}
		ACCESS		read-only
		STATUS		mandatory
		DESCRIPTION	"TCN 15min Current CH Index
					  1:CH-A,
					  2:CH-B,
					  3:CH-C,
					  4:CH-D
					
					
					"
		::= { pnProvTCNThreshold15minCHEntry 2 }

	pnProvTCNThreshold15minCHORIndex OBJECT-TYPE
		SYNTAX		INTEGER{
					  occur(1),
					  recover(2)
					}
		ACCESS		read-only
		STATUS		mandatory
		DESCRIPTION	"TCN Threshold 15min CH Occur/Recover Index
					  1:Occur,
					  2:Recover"
		::= { pnProvTCNThreshold15minCHEntry 3 }

	pnProvTCNThreshold15minCHValue OBJECT-TYPE
		SYNTAX		OCTET STRING (SIZE (24))
		ACCESS		read-only
		STATUS		mandatory
		DESCRIPTION	"This item is not used.
				 TCN THRESHOLD 15MIN CH
					  This value is used by only PDH.
					
					  [Description]
					  (Byte 0 - Byte 3)   = (Fixed to 0)
					  (Byte 4 - Byte 7)   = UAS TCN THRESHOLD CH-15min (0 - 900)
					  (Byte 8 - Byte 11)  = ES TCN THRESHOLD CH-15min  (0 - 900)
					  (Byte 12 - Byte 15) = SES TCN THRESHOLD CH-15min (0 - 900)
					  (Byte 16 - Byte 19) = BBE TCN THRESHOLD CH-15min (0 - 402300)
					  (Byte 20 - Byte 23) = SEP TCN THRESHOLD CH-15min (0 - 900)
					TRAP=eventTrapPnSTDTCNTreshold15minCH"
		::= { pnProvTCNThreshold15minCHEntry 4 }

	pnProvTCNThreshold1dayTotalTable OBJECT-TYPE
		SYNTAX		SEQUENCE OF PnProvTCNThreshold1dayTotalEntry
		ACCESS		not-accessible
		STATUS		mandatory
		DESCRIPTION	"PROV TCN Threshold 1day Total Table"
		::= { pnProvTCNTresholdGroup 3 }

	pnProvTCNThreshold1dayTotalEntry OBJECT-TYPE
		SYNTAX		PnProvTCNThreshold1dayTotalEntry
		ACCESS		not-accessible
		STATUS		mandatory
		INDEX		{
						pnProvTCNThreshold1dayTotalPasoIndex,
						pnProvTCNThreshold1dayTotalWPIndex,
						pnProvTCNThreshold1dayTotalORIndex
					}
		::= { pnProvTCNThreshold1dayTotalTable 1 }

	PnProvTCNThreshold1dayTotalEntry ::= SEQUENCE {
					  pnProvTCNThreshold1dayTotalPasoIndex  IpAddress,
					  pnProvTCNThreshold1dayTotalWPIndex  INTEGER,
					  pnProvTCNThreshold1dayTotalORIndex  INTEGER,
					  pnProvTCNThreshold1dayTotalValue    OCTET STRING
					}

	pnProvTCNThreshold1dayTotalPasoIndex OBJECT-TYPE
		SYNTAX		IpAddress 
		ACCESS		read-only
		STATUS		mandatory
		DESCRIPTION	"Pasolink IP Address Index"
		::= { pnProvTCNThreshold1dayTotalEntry 1 }

	pnProvTCNThreshold1dayTotalWPIndex OBJECT-TYPE
		SYNTAX		INTEGER{
					  working-MUX(1),
					  protection-MUX(2),
					  working-DMR-dirA(3),
					  protection-DMR-dirB(4)
					}
		ACCESS		read-only
		STATUS		mandatory
		DESCRIPTION	"TCN 1day Current Total Working/Protection Index
					  1:Working(MUX),
					  2:Protection(MUX),
					  3:Working(DMR)/Working(DIR-A)
					  4:Protection(DMR)/Working(DIR-B)
					
					  *)MUX side is not used when using LAN.
					  *)Protection is only used when APS function is used.
					  *)DIR-* is only used when Redundancy is 2-Way."
		::= { pnProvTCNThreshold1dayTotalEntry 2 }

	pnProvTCNThreshold1dayTotalORIndex OBJECT-TYPE
		SYNTAX		INTEGER{
					  occur(1),
					  recover(2)
					}
		ACCESS		read-only
		STATUS		mandatory
		DESCRIPTION	"TCN Threshold 1day Total Occur/Recover Index
					  1:Occur,
					  2:Recover"
		::= { pnProvTCNThreshold1dayTotalEntry 3 }

	pnProvTCNThreshold1dayTotalValue OBJECT-TYPE
		SYNTAX		OCTET STRING (SIZE (24))
		ACCESS		read-only
		STATUS		mandatory
		DESCRIPTION	"TCN THRESHOLD 1DAY TOTAL
					
					  [Description]
					  (Byte 0 - Byte 3) = OFS TCN THRESHOLD TOTAL-1day (0 - 86400)
					  (Byte 4 - Byte 7) = UAS TCN THRESHOLD TOTAL-1day (0 - 86400)
					  (Byte 8 - Byte 11) = ES TCN THRESHOLD TOTAL-1day (0 - 86400)
					  (Byte 12 - Byte 15) = SES TCN THRESHOLD TOTAL-1day (0 - 86400)
					  (Byte 16 - Byte 19) = BBE TCN THRESHOLD TOTAL-1day
					                       (PDH(Bit Rate = 10MB)  : 0 - 77241600
					                        PDH(Bit Rate = 20MB)  : 0 - 77241600
					                        PDH(Bit Rate = 40MB)  : 0 - 77241600
					                        PDH(Bit Rate = 80MB)  : 0 - 154656000
					                        PDH(Bit Rate = 100MB) : 0 - 154656000
					                        SDH(Bit Rate = 156MB) : 0 - 207273600)
					  (Byte 20 - Byte 23) = SEP TCN THRESHOLD TOTAL-1day (0 - 86400)
					TRAP=eventTrapPnSTDTCNTreshold1dayTotal"
		::= { pnProvTCNThreshold1dayTotalEntry 4 }

	pnProvTCNThreshold1dayCHTable OBJECT-TYPE
		SYNTAX		SEQUENCE OF PnProvTCNThreshold1dayCHEntry
		ACCESS		not-accessible
		STATUS		mandatory
		DESCRIPTION	"PROV TCN Threshold 1day CH Table"
		::= { pnProvTCNTresholdGroup 4 }

	pnProvTCNThreshold1dayCHEntry OBJECT-TYPE
		SYNTAX		PnProvTCNThreshold1dayCHEntry
		ACCESS		not-accessible
		STATUS		mandatory
		INDEX		{
						pnProvTCNThreshold1dayCHPasoIndex,
						pnProvTCNThreshold1dayCHIndex,
						pnProvTCNThreshold1dayCHORIndex
					}
		::= { pnProvTCNThreshold1dayCHTable 1 }

	PnProvTCNThreshold1dayCHEntry ::= SEQUENCE {
					  pnProvTCNThreshold1dayCHPasoIndex    IpAddress,
					  pnProvTCNThreshold1dayCHIndex    INTEGER,
					  pnProvTCNThreshold1dayCHORIndex  INTEGER,
					  pnProvTCNThreshold1dayCHValue    OCTET STRING
					}

	pnProvTCNThreshold1dayCHPasoIndex OBJECT-TYPE
		SYNTAX		IpAddress 
		ACCESS		read-only
		STATUS		mandatory
		DESCRIPTION	"Pasolink IP Address Index"
		::= { pnProvTCNThreshold1dayCHEntry 1 }

	pnProvTCNThreshold1dayCHIndex OBJECT-TYPE
		SYNTAX		INTEGER{
					  ch-A(1),
					  ch-B(2),
					  ch-C(3),
					  ch-D(4)
					}
		ACCESS		read-only
		STATUS		mandatory
		DESCRIPTION	"TCN 1day Current CH Index
					  1:CH-A,
					  2:CH-B,
					  3:CH-C,
					  4:CH-D"
		::= { pnProvTCNThreshold1dayCHEntry 2 }

	pnProvTCNThreshold1dayCHORIndex OBJECT-TYPE
		SYNTAX		INTEGER{
					  occur(1),
					  recover(2)
					}
		ACCESS		read-only
		STATUS		mandatory
		DESCRIPTION	"TCN Threshold 1day CH Occur/Recover Index
					  1:Occur,
					  2:Recover"
		::= { pnProvTCNThreshold1dayCHEntry 3 }

	pnProvTCNThreshold1dayCHValue OBJECT-TYPE
		SYNTAX		OCTET STRING (SIZE (24))
		ACCESS		read-only
		STATUS		mandatory
		DESCRIPTION	"This item is not used.
				 TCN THRESHOLD 1day CH
					  This value is used by only PDH.
					
					  [Description]
					  (Byte 0 - Byte 3)   = (Fixed to 0)
					  (Byte 4 - Byte 7)   = UAS TCN THRESHOLD CH-1day (0 - 900)
					  (Byte 8 - Byte 11)  = ES TCN THRESHOLD CH-1day  (0 - 900)
					  (Byte 12 - Byte 15) = SES TCN THRESHOLD CH-1day (0 - 900)
					  (Byte 16 - Byte 19) = BBE TCN THRESHOLD CH-1day (0 - 402300)
					  (Byte 20 - Byte 23) = SEP TCN THRESHOLD CH-1day (0 - 900)
					TRAP=eventTrapPnSTDTCNTreshold1dayCH"
		::= { pnProvTCNThreshold1dayCHEntry 4 }


	pnProvMDUCondSetTable OBJECT-TYPE
		SYNTAX		SEQUENCE OF PnProvMDUCondSetEntry
		ACCESS		not-accessible
		STATUS		mandatory
		DESCRIPTION	"PROV MDU Cond Set Table"
		::= { pnProvisioningGroup 12 }

	pnProvMDUCondSetEntry OBJECT-TYPE
		SYNTAX		PnProvMDUCondSetEntry
		ACCESS		not-accessible
		STATUS		mandatory
		INDEX		{
						pnProvMDUCondSetPasoIndex
					}
		::= { pnProvMDUCondSetTable 1 }

	PnProvMDUCondSetEntry ::= SEQUENCE {
					  pnProvMDUCondSetPasoIndex  IpAddress,
					  pnFadingDepthThreshold	OCTET STRING,
					  pnXpicCondLOSignalFail	INTEGER,
					  pnEowIFType	INTEGER,
					  pnAlarmCorrelationCapability	OffOnValue
					}

	pnProvMDUCondSetPasoIndex OBJECT-TYPE
		SYNTAX		IpAddress 
		ACCESS		read-only
		STATUS		mandatory
		DESCRIPTION	"Pasolink IP Address Index"
		::= { pnProvMDUCondSetEntry 1 }

	pnFadingDepthThreshold OBJECT-TYPE
		SYNTAX		OCTET STRING (SIZE (2))
		ACCESS		read-only
		STATUS		mandatory
		DESCRIPTION	"This item is not used.
				 FADING STATUS THRESHOLD

					  [Description]
					  Byte 0 = FADING DEPTH THRESHOLD(No.1/DIR-A)
					  Byte 1 = FADING DEPTH THRESHOLD(No.2/DIR-B)
					       (0:Invalid, 1:5[dB], 2:10[dB], 3:15[dB],
					        4:20[dB], 5:25[dB], 6:30[dB])
					
					   Byte 2 is fixed to 0, when Redundancy is 1+0 TERM.
					TRAP=eventTrapPnSTDFadingDepthThreshold"
		::= { pnProvMDUCondSetEntry 2 }

	pnXpicCondLOSignalFail OBJECT-TYPE
		SYNTAX		INTEGER (0..2)
		ACCESS		read-only
		STATUS		mandatory
		DESCRIPTION	"XPIC CONDITION-LOCAL FAIL 
					  0:Invalid,
					  1:From RF to Self LO Signal,
					  2:Mute
					TRAP=eventTrapPnSTDXpicCondLOSignalFail"
		::= { pnProvMDUCondSetEntry 3 }

	pnEowIFType OBJECT-TYPE
		SYNTAX		INTEGER (0..2)
		ACCESS		read-only
		STATUS		mandatory
		DESCRIPTION	"EOW2 EXTERNAL SETTING
					  0:Invalid,
					  1:Normal,
					  2:Invert
					TRAP=eventTrapPnSTDEOWIntfcType"
		::= { pnProvMDUCondSetEntry 4 }

	pnAlarmCorrelationCapability OBJECT-TYPE
		SYNTAX		OffOnValue
		ACCESS		read-only
		STATUS		mandatory
		DESCRIPTION	"ALARM CORRELATION CAPABILITY
					 0:OFF,
					 1:ON
					TRAP=eventTrapPnSTDAlarmCorrelation"
		::= { pnProvMDUCondSetEntry 5 }

	pnProvPMONSelectTable OBJECT-TYPE
		SYNTAX		SEQUENCE OF PnProvPMONSelectEntry
		ACCESS		not-accessible
		STATUS		mandatory
		DESCRIPTION	"PROV PMON Select Table"
		::= { pnProvisioningGroup 13 }

	pnProvPMONSelectEntry OBJECT-TYPE
		SYNTAX		PnProvPMONSelectEntry
		ACCESS		not-accessible
		STATUS		mandatory
		INDEX		{
						pnProvPMONSelectPasoIndex
					}
		::= { pnProvPMONSelectTable 1 }

	PnProvPMONSelectEntry ::= SEQUENCE {
					  pnProvPMONSelectPasoIndex  IpAddress,
					  pnProvPMONSelect	OCTET STRING,
					}

	pnProvPMONSelectPasoIndex OBJECT-TYPE
		SYNTAX		IpAddress 
		ACCESS		read-only
		STATUS		mandatory
		DESCRIPTION	"Pasolink IP Address Index"
		::= { pnProvPMONSelectEntry 1 }

	pnProvPMONSelect OBJECT-TYPE
		SYNTAX		OCTET STRING (SIZE (10))
		ACCESS		read-only
		STATUS		mandatory
		DESCRIPTION	"PMON SELECT
					
					  [Description]
					  Byte 0 = SES COUNT ACTIVATION(DIR-A) (1:30[%], 2:15[%])
					  Byte 1 = SES COUNT ACTIVATION(DIR-B) (1:30[%], 2:15[%])
					  Byte 2 = PMON E1-A SELECT (0:Not Select, x: CHx(x:1-48))
					  Byte 3 = PMON E1-B SELECT (0:Not Select, x: CHx(x:1-48))
					  Byte 4 = PMON E1-C SELECT (0:Not Select, x: CHx(x:1-48))
					  Byte 5 = PMON E1-D SELECT (0:Not Select, x: CHx(x:1-48))
					  Byte 6 = RX LEVEL TCN THRESHOLD(No.1/DIR-A) integral number
					           (signed char: -99 to -7)
					  Byte 7 = RX LEVEL TCN THRESHOLD(No.1/DIR-A)a place of decimal
					           (0-9)
					  Byte 8 = RX LEVEL TCN THRESHOLD(No.2/DIR-B) integral number
					           (signed char: -99 to -7)
					  Byte 9 = RX LEVEL TCN THRESHOLD(No.2/DIR-B)a place of decimal
					           (0-9)
					
					  *) The values of No.2/DIR-B side are fixed to 0 when
					     Redundancy is 1+0 TERM.
					TRAP=eventTrapPnSTDPmonSelect"
		::= { pnProvPMONSelectEntry 2 }


-----------------------------------------------
-- pnMaintenanceGroup Group Definitions
-----------------------------------------------


	pnMaintCommonTable OBJECT-TYPE
		SYNTAX		SEQUENCE OF PnMaintCommonEntry
		ACCESS		not-accessible
		STATUS		mandatory
		DESCRIPTION	"MAINT Common Table"
		::= { pnMaintenanceGroup 1 }

	pnMaintCommonEntry OBJECT-TYPE
		SYNTAX		PnMaintCommonEntry
		ACCESS		not-accessible
		STATUS		mandatory
		INDEX		{
						pnMaintCommonPasoIndex
					}
		::= { pnMaintCommonTable 1 }

	PnMaintCommonEntry ::= SEQUENCE {
					  pnMaintCommonPasoIndex	IpAddress,
					  pnMaintMode	OffOnValue,
					  pnMaintTxSWControl	INTEGER,
					  pnMaintRxSWControl	INTEGER,
					  pnMaintAPSSWControl	INTEGER,
					  pnMaintLoopback1CH	OCTET STRING,
					  pnMaintLoopback2CH	OCTET STRING,
					  pnMaintLoopback1Work	INTEGER,
					  pnMaintLoopback2	INTEGER,
					  pnMaintDADEAdjust	INTEGER,
					  pnMaintDADEAdjustEnable	INTEGER,
					  pnMaintLANDeviceReset	INTEGER,
					  pnMaintAlsRestart	INTEGER,
					  pnMaintAlsManualRestart	INTEGER,
					  pnMaintLoopback1Prot	OffOnValue,
					  pnMaintTxSWMode	INTEGER,
					  pnMaintRxSWMode	INTEGER,
					  pnMaintAPSSWMode	INTEGER,
					  pnMaintLoopback3CH	OCTET STRING
					}

	pnMaintCommonPasoIndex OBJECT-TYPE
		SYNTAX		IpAddress 
		ACCESS		read-only
		STATUS		mandatory
		DESCRIPTION	"Pasolink IP Address Index"
		::= { pnMaintCommonEntry 1 }

	pnMaintMode OBJECT-TYPE
		SYNTAX		OffOnValue
		ACCESS		read-only
		STATUS		mandatory
		DESCRIPTION	"MAINTENANCE
					  0:Invalid,
					  1:Off,
					  2:On
					TRAP=eventTrapPnSTDMaintMode"
		::= { pnMaintCommonEntry 2 }

	pnMaintTxSWControl OBJECT-TYPE
		SYNTAX		INTEGER (0..3)
		ACCESS		read-only
		STATUS		mandatory
		DESCRIPTION	"This item is not used.
                                 TX SW MANUAL CONTROL
					  0:Invalid,
					  1:Auto,
					  2:No.1,
					  3:No.2
					TRAP=eventTrapPnSTDMaintTxSWContol"
		::= { pnMaintCommonEntry 3 }

	pnMaintRxSWControl OBJECT-TYPE
		SYNTAX		INTEGER (0..3)
		ACCESS		read-only
		STATUS		mandatory
		DESCRIPTION	"This item is not used.
                                 RX SW MANUAL CONTROL
					  0:Invalid,
					  1:Auto,
					  2:No.1,
					  3:No.2
					TRAP=eventTrapPnSTDMaintRxSWContol"
		::= { pnMaintCommonEntry 4 }

	pnMaintAPSSWControl OBJECT-TYPE
		SYNTAX		INTEGER (0..3)
		ACCESS		read-only
		STATUS		mandatory
		DESCRIPTION	"This item is not used.
                                 APS MANUAL CONTROL
					  0:Invalid,
					  1:Auto,
					  2:Working,
					  3:Protection
					TRAP=eventTrapPnSTDMaintAPSSWContol"
		::= { pnMaintCommonEntry 5 }

	pnMaintLoopback1CH OBJECT-TYPE
		SYNTAX		OCTET STRING (SIZE (6))
		ACCESS		read-only
		STATUS		mandatory
		DESCRIPTION	"MAIN CH LOOPBACK-1(CHxx)
					(xx:01-48)
					  0:Off,
					  1:On
					
					  [Description]
					  Bit 0 = MAIN CH LOOPBACK-1(CH01) (0:Off, 1:On)
					  Bit 1 = MAIN CH LOOPBACK-1(CH02)
					  ...
					  Bit 46 = MAIN CH LOOPBACK-1(CH47) for E1 interface
						    MAIN CH LOOPBACK-1(E3 CH1) for E3 interface
					  Bit 47 = MAIN CH LOOPBACK-1(CH48) for E1 interface
					              MAIN CH LOOPBACK-1(E3 CH2) for E3 interface
					
					  *) The value of CHxx is fixed to 0, when CHxx Usage is not used. (xx: 01 - 48)
					TRAP=eventTrapPnSTDMaintLoopback1CH"
		::= { pnMaintCommonEntry 6 }

	pnMaintLoopback2CH OBJECT-TYPE
		SYNTAX		OCTET STRING (SIZE (6))
		ACCESS		read-only
		STATUS		mandatory
		DESCRIPTION	"
					MAIN CH LOOPBACK-2(CHxx)
					(xx:01-48)
					  0:Off,
					  1:On
					
					  [Description]
					  Bit 0 = MAIN CH LOOPBACK-2(CH01) (0:Off, 1:On)
					  Bit 1 = MAIN CH LOOPBACK-2(CH02)
					  ...
					  Bit 46 = MAIN CH LOOPBACK-1(CH47) for E1 interface
						    MAIN CH LOOPBACK-1(E3 CH1) for E3 interface
					  Bit 47 = MAIN CH LOOPBACK-1(CH48) for E1 interface
					              MAIN CH LOOPBACK-1(E3 CH2) for E3 interface
					
					  *) The value of CHxx is fixed to 0, when CHxx Usage is not used. (xx: 01 - 48)
					TRAP=eventTrapPnSTDMaintLoopback2CH"
		::= { pnMaintCommonEntry 7 }

	pnMaintLoopback1Work OBJECT-TYPE
		SYNTAX		OffOnValue
		ACCESS		read-only
		STATUS		mandatory
		DESCRIPTION	"MAIN LOOPBACK-1 INTFC(1)
					0:OFF,
					1:ON
					TRAP=eventTrapPnSTDMaintLoopback1Work"
		::= { pnMaintCommonEntry 8 }

	pnMaintLoopback2 OBJECT-TYPE
		SYNTAX		OffOnValue
		ACCESS		read-only
		STATUS		mandatory
		DESCRIPTION	"MAIN LOOPBACK-2
					0:OFF,
					1:ON
					TRAP=eventTrapPnSTDMaintLoopback2"
		::= { pnMaintCommonEntry 9 }

	pnMaintDADEAdjust OBJECT-TYPE
		SYNTAX		INTEGER (0..3)
		ACCESS		read-only
		STATUS		mandatory
		DESCRIPTION	"This item is not used.
					DADE ADJUST
					  0:Invalid,
					  1:DADE,
					  2:Off Set DADE,
					  3:DADE OFF
					TRAP=eventTrapPnSTDMaintDADEAdjust"
		::= { pnMaintCommonEntry 10 }

	pnMaintDADEAdjustEnable OBJECT-TYPE
		SYNTAX		INTEGER (0..2)
		ACCESS		read-only
		STATUS		mandatory
		DESCRIPTION	"This item is not used.
					DADE ADJUST ENABLE
					  0:Invalid,
					  1:Off,
					  2:ON Executing
					TRAP=eventTrapPnSTDMaintDADEAdjustEn"
		::= { pnMaintCommonEntry 11 }

	pnMaintLANDeviceReset OBJECT-TYPE
		SYNTAX		INTEGER (0..7)
		ACCESS		read-only
		STATUS		mandatory
		DESCRIPTION	"This item is not used.
				LAN DEVICE RESET
					  0:Invalid,
					  1:Not Selected,
					  2:INTFC1(Port1),
					  3:INTFC1(Port2),
					  4:INTFC1(Port3),
					  5:INTFC1(Port4),
					  6:INTFC2(Port1),
					  7:INTFC2(Port2)
					TRAP=eventTrapPnSTDMaintLanDeviceReset"
		::= { pnMaintCommonEntry 12 }

	pnMaintAlsRestart OBJECT-TYPE
		SYNTAX		INTEGER (0..5)
		ACCESS		read-only
		STATUS		mandatory
		DESCRIPTION	"This item is not used.
				ALS RESTART
					  0:Invalid,
					  1:Not Selected,
					  2:2sec(INTFC1),
					  3:90sec(INTFC1),
					  4:2sec(INTFC2),
					  5:90sec(INTFC2)
					TRAP=eventTrapPnSTDMaintAlsRestart"
		::= { pnMaintCommonEntry 13 }

	pnMaintAlsManualRestart OBJECT-TYPE
		SYNTAX		INTEGER (0..3)
		ACCESS		read-only
		STATUS		mandatory
		DESCRIPTION	"This item is not used.
				MANUAL RESTART
					  0:Invalid,
					  1:Off,
					  2:ON(INTFC1),
					  3:ON(INTFC2)
					TRAP=eventTrapPnSTDMaintAlsManualRestart"
		::= { pnMaintCommonEntry 14 }

	pnMaintLoopback1Prot OBJECT-TYPE
		SYNTAX		OffOnValue
		ACCESS		read-write
		STATUS		mandatory
		DESCRIPTION	"MAIN LOOPBACK-1 INTFC(2)
					0:OFF,
					1:ON
					TRAP=eventTrapPnSTDMaintLoopback1Prot"
		::= { pnMaintCommonEntry 15 }

	pnMaintTxSWMode OBJECT-TYPE
		SYNTAX		INTEGER (0..2)
		ACCESS		read-only
		STATUS		mandatory
		DESCRIPTION	"TX SW MODE
					  0:Invalid,
					  1:Auto(No.1),
					  2:Auto(No.2),
					  3:Manual(No.1),
					  4:Manual(No.2)
					TRAP=eventTrapPnSTDMaintTxSWMode"
		::= { pnMaintCommonEntry 16 }

	pnMaintRxSWMode OBJECT-TYPE
		SYNTAX		INTEGER (0..2)
		ACCESS		read-only
		STATUS		mandatory
		DESCRIPTION	"RX SW MODE
					  0:Invalid,
					  1:Auto(No.1),
					  2:Auto(No.2),
					  3:Manual(No.1),
					  4:Manual(No.2)
					TRAP=eventTrapPnSTDMaintRxSWMode"
		::= { pnMaintCommonEntry 17 }

	pnMaintAPSSWMode OBJECT-TYPE
		SYNTAX		INTEGER (0..2)
		ACCESS		read-only
		STATUS		mandatory
		DESCRIPTION	"APS SW MODE
					  0:Invalid,
					  1:Auto(Working),
					  2:Auto(Protection),
					  3:Manual(Working),
					  4:Manual(Protection)
					TRAP=eventTrapPnSTDMaintAPSSWMode"
		::= { pnMaintCommonEntry 18 }

	pnMaintLoopback3CH OBJECT-TYPE
		SYNTAX		OCTET STRING (SIZE (6))
		ACCESS		read-write
		STATUS		mandatory
		DESCRIPTION	"Main CH Loopback-2(DIR-B)(CHxx)
				 (xx:01-48)
					  0:Invalid,
					  1:OFF,
					  2:ON
					TRAP=eventTrapPnSTDMaintLoopback3CH"
		::= { pnMaintCommonEntry 19 }

	pnMaintSysTable OBJECT-TYPE
		SYNTAX		SEQUENCE OF PnMaintSysEntry
		ACCESS		not-accessible
		STATUS		mandatory
		DESCRIPTION	"MAINT SYS Table"
		::= { pnMaintenanceGroup 2 }

	pnMaintSysEntry OBJECT-TYPE
		SYNTAX		PnMaintSysEntry
		ACCESS		not-accessible
		STATUS		mandatory
		INDEX		{
						pnMaintSysPasoIndex,
						pnMaintSysIndex
					}
		::= { pnMaintSysTable 1 }

	PnMaintSysEntry ::= SEQUENCE {
					  pnMaintSysPasoIndex              IpAddress,
					  pnMaintSysIndex                  INTEGER,
					  pnMaintSysATPCManualControl      INTEGER,
					  pnMaintSysATPCManualContPower    INTEGER,
					  pnMaintSysTxMuteControl          INTEGER,
					  pnMaintSysTxMuteContReleaseTime  INTEGER,
					  pnMaintSysCW                     INTEGER,
					  pnMaintSysIFLoopback             INTEGER,
					  pnMaintSysForcedXPICCont         INTEGER,
					  pnMaintSysForcedLinearizerCont   INTEGER,
					  pnMaintSysRFShiftFreqSet         DisplayString,
					  pnMaintSysAntennaAlignMode       INTEGER
					}

	pnMaintSysPasoIndex OBJECT-TYPE
		SYNTAX		IpAddress 
		ACCESS		read-only
		STATUS		mandatory
		DESCRIPTION	"Pasolink IP Address Index"
		::= { pnMaintSysEntry 1 }

	pnMaintSysIndex OBJECT-TYPE
		SYNTAX		INTEGER{
					  no1-dirA(1),
					  no2-dirB(2)
					}
		ACCESS		read-only
		STATUS		mandatory
		DESCRIPTION	"Main Sys Index
					 1:No.1 when EQUIPMENT CONFIG is TERM.
					   DIR-A when EQUIPMENT CONFIG is 2-way
					 2:No.2 when EQUIPMENT CONFIG is TERM.
					   DIR-B when EQUIPMENT CONFIG is 2-way."
		::= { pnMaintSysEntry 2 }

	pnMaintSysATPCManualControl OBJECT-TYPE
		SYNTAX		OffOnValue
		ACCESS		read-only
		STATUS		mandatory
		DESCRIPTION	"ATPC MANUAL CONTROL
					TRAP=eventTrapPnSTDMaintATPCManualControl"
		::= { pnMaintSysEntry 3 }

	pnMaintSysATPCManualContPower OBJECT-TYPE
		SYNTAX		INTEGER
		ACCESS		read-only
		STATUS		mandatory
		DESCRIPTION	"ATPC MANUAL POWER[dB]
					TRAP=eventTrapPnSTDMaintATPCManualContPower"
		::= { pnMaintSysEntry 4 }

	pnMaintSysTxMuteControl OBJECT-TYPE
		SYNTAX		OffOnValue
		ACCESS		read-only
		STATUS		mandatory
		DESCRIPTION	"TX MUTE CONTROL
					TRAP=eventTrapPnSTDMaintTxMuteControl"
		::= { pnMaintSysEntry 5 }

	pnMaintSysTxMuteContReleaseTime OBJECT-TYPE
		SYNTAX		INTEGER
		ACCESS		read-only
		STATUS		mandatory
		DESCRIPTION	"TX MUTE OFF TIMER[sec]
					TRAP=eventTrapPnSTDMaintTxMuteContReleaseTime"
		::= { pnMaintSysEntry 6 }

	pnMaintSysCW OBJECT-TYPE
		SYNTAX		OffOnValue
		ACCESS		read-only
		STATUS		mandatory
		DESCRIPTION	"CW CONTROL
					TRAP=eventTrapPnSTDMaintCW"
		::= { pnMaintSysEntry 7 }

	pnMaintSysIFLoopback OBJECT-TYPE
		SYNTAX		OffOnValue
		ACCESS		read-only
		STATUS		mandatory
		DESCRIPTION	"IF LOOPBACK
					TRAP=eventTrapPnSTDMaintIfLoopback"
		::= { pnMaintSysEntry 8 }

	pnMaintSysForcedXPICCont OBJECT-TYPE
		SYNTAX		INTEGER (0..2)
		ACCESS		read-only
		STATUS		mandatory
		DESCRIPTION	"XPIC CONTROL
					  0:Invalid,
					  1:Auto,
					  2:Force Reset
					TRAP=eventTrapPnSTDMaintForcedXPICCont"
		::= { pnMaintSysEntry 9 }

	pnMaintSysForcedLinearizerCont OBJECT-TYPE
		SYNTAX		INTEGER (0..2)
		ACCESS		read-only
		STATUS		mandatory
		DESCRIPTION	"LINEARIZER CONTROL
					  0:Invalid,
					  1:Auto,
					  2:Force Reset
					TRAP=eventTrapPnSTDMaintForcedLinearizerCont"
		::= { pnMaintSysEntry 10 }

	pnMaintSysRFShiftFreqSet OBJECT-TYPE
		SYNTAX		DisplayString (SIZE (0..4))
		ACCESS		read-only
		STATUS		mandatory
		DESCRIPTION	"This item is not used.
				 RF SHIFT FREQUENCY[MHz]
					 This value is only 1008 or 1010
					TRAP=eventTrapPnSTDMaintRFShiftFreqSet"
		::= { pnMaintSysEntry 12 }

	pnMaintSysAntennaAlignMode OBJECT-TYPE
		SYNTAX		OffOnValue
		ACCESS		read-only
		STATUS		mandatory
		DESCRIPTION	"ANTENNA ALIGNMENT MODE
					TRAP=eventTrapPnSTDMaintAntennaAlignMode"
		::= { pnMaintSysEntry 13 }


-----------------------------------------------
-- pnInvEntryGroup Group Definitions
-----------------------------------------------

	pnInvModuleInfoMDUTable OBJECT-TYPE
		SYNTAX		SEQUENCE OF PnInvModuleInfoMDUEntry
		ACCESS		not-accessible
		STATUS		mandatory
		DESCRIPTION	"Module Info MDU Table"
		::= { pnInvEntryGroup 1 }

	pnInvModuleInfoMDUEntry OBJECT-TYPE
		SYNTAX		PnInvModuleInfoMDUEntry
		ACCESS		not-accessible
		STATUS		mandatory
		INDEX		{
						pnInvModuleInfoMDUPasoIndex,
						pnInvModuleInfoMDUIndex
					}
		::= { pnInvModuleInfoMDUTable 1 }

	PnInvModuleInfoMDUEntry ::= SEQUENCE {
					  pnInvModuleInfoMDUPasoIndex  IpAddress,
					  pnInvModuleInfoMDUIndex  INTEGER,
					  pnInvModuleInfoMDUData   OCTET STRING
					}

	pnInvModuleInfoMDUPasoIndex OBJECT-TYPE
		SYNTAX		IpAddress 
		ACCESS		read-only
		STATUS		mandatory
		DESCRIPTION	"Pasolink IP Address Index"
		::= { pnInvModuleInfoMDUEntry 1 }

	pnInvModuleInfoMDUIndex OBJECT-TYPE
		SYNTAX		INTEGER{
					  modem-no1(1),
					  modem-no2(2),
					  ctrl(3),
					  main-work(4),
					  sub-prot(5)
					}
		ACCESS		read-only
		STATUS		mandatory
		DESCRIPTION	"Module Info MDU Index
					  1:Modem(No.1),
					  2:Modem(No.2),
					  3:CTRL,
					  4:MAIN(WORK),
					  5:SUB(PROT)
					
					  *) Modem(No.1) means Modem(DIR-A) when Redundancy is 2-way.
					  *) Modem(No.2) means Modem(DIR-B) when Redundancy is 2-way.
					  *) SUB(PROT) is available only when System Architecture is SDH."
		::= { pnInvModuleInfoMDUEntry 2 }

	pnInvModuleInfoMDUData OBJECT-TYPE
		SYNTAX		OCTET STRING (SIZE (56))
		ACCESS		read-only
		STATUS		mandatory
		DESCRIPTION	"Module Info MDU Data
					  [Description]
					  (Byte 0 - Byte 15)  = CODE No. (VALUE(ASC(16))
					  (Byte 16 - Byte 31) = PACKAGE NAME (VALUE(ASC(16))
					  (Byte 32 - Byte 39) = SERIAL No. (VALUE(ASC(8))
					  (Byte 40 - Byte 47) = DATE OF MANUFACTURE (VALUE(ASC(8))
					  (Byte 48 - Byte 55) = H/W VERSION (VALUE(ASC(8))"
		::= { pnInvModuleInfoMDUEntry 3 }

	pnInvModuleInfoTRUTable OBJECT-TYPE
		SYNTAX		SEQUENCE OF PnInvModuleInfoTRUEntry
		ACCESS		not-accessible
		STATUS		mandatory
		DESCRIPTION	"Module Info ODU Table"
		::= { pnInvEntryGroup 2 }

	pnInvModuleInfoTRUEntry OBJECT-TYPE
		SYNTAX		PnInvModuleInfoTRUEntry
		ACCESS		not-accessible
		STATUS		mandatory
		INDEX		{
						pnInvModuleInfoTRUPasoIndex,
						pnInvModuleInfoTRUSysIndex
					}
		::= { pnInvModuleInfoTRUTable 1 }

	PnInvModuleInfoTRUEntry ::= SEQUENCE {
					  pnInvModuleInfoTRUPasoIndex  IpAddress,
					  pnInvModuleInfoTRUSysIndex  INTEGER,
					  pnInvModuleInfoTRUData      OCTET STRING
					}

	pnInvModuleInfoTRUPasoIndex OBJECT-TYPE
		SYNTAX		IpAddress 
		ACCESS		read-only
		STATUS		mandatory
		DESCRIPTION	"Pasolink IP Address Index"
		::= { pnInvModuleInfoTRUEntry 1 }

	pnInvModuleInfoTRUSysIndex OBJECT-TYPE
		SYNTAX		INTEGER{
					  no1-dirA(1),
					  no2-dirB(2)
					}
		ACCESS		read-only
		STATUS		mandatory
		DESCRIPTION	"Module Info ODU Sys Index
					 1:No.1 when EQUIPMENT CONFIG is TERM.
					   DIR-A when EQUIPMENT CONFIG is 2-WAY
					 2:No.2 when EQUIPMENT CONFIG is TERM.
					   DIR-B when EQUIPMENT CONFIG is 2-WAY."
		::= { pnInvModuleInfoTRUEntry 2 }

	pnInvModuleInfoTRUData OBJECT-TYPE
		SYNTAX		OCTET STRING (SIZE (60))
		ACCESS		read-only
		STATUS		mandatory
		DESCRIPTION	"Module Info ODU Data
					  [Description]
					  (Byte 0 - Byte 15)  = CODE No. (VALUE(ASC(16))
					  (Byte 16 - Byte 31) = PACKAGE NAME (VALUE(ASC(16))
					  (Byte 32 - Byte 39) = SERIAL No. (VALUE(ASC(8))
					  (Byte 40 - Byte 47) = DATE OF MANUFACTURE (VALUE(ASC(8))
					  (Byte 48 - Byte 55) = H/W VERSION (VALUE(ASC(8))
					  (Byte 56 - Byte 59) = F/W VERSION (VALUE(ASC(4))"
		::= { pnInvModuleInfoTRUEntry 3 }

	pnInvFPGAInfoTable OBJECT-TYPE
		SYNTAX		SEQUENCE OF PnInvFPGAInfoEntry
		ACCESS		not-accessible
		STATUS		mandatory
		DESCRIPTION	"FPGA Info Table"
		::= { pnInvEntryGroup 3 }

	pnInvFPGAInfoEntry OBJECT-TYPE
		SYNTAX		PnInvFPGAInfoEntry
		ACCESS		not-accessible
		STATUS		mandatory
		INDEX		{
						pnInvFPGAInfoPasoIndex,
						pnInvFPGAInfoIndex
					}
		::= { pnInvFPGAInfoTable 1 }

	PnInvFPGAInfoEntry ::= SEQUENCE {
					  pnInvFPGAInfoPasoIndex  IpAddress,
					  pnInvFPGAInfoIndex  INTEGER,
					  pnInvFPGAInfoData   OCTET STRING
					}

	pnInvFPGAInfoPasoIndex OBJECT-TYPE
		SYNTAX		IpAddress 
		ACCESS		read-only
		STATUS		mandatory
		DESCRIPTION	"Pasolink IP Address Index"
		::= { pnInvFPGAInfoEntry 1 }

	pnInvFPGAInfoIndex OBJECT-TYPE
		SYNTAX		INTEGER{
					  modem1(1),
					  modem2(2),
					  ctrl(3),
					  mainWork(4),
					  subProt(5),
					  sfpModule-mainWork(6),
					  sfpModule-subProt(7),
					  ctrlProgramVer(8)
					}
		ACCESS		read-only
		STATUS		mandatory
		DESCRIPTION	"FPGA Info Index
					  1:Modem No.1,
					  2:Modem No.2,
					  3:CTRL,
					  4:Main(Work),
					  5:SUB(PROT),
					  6:SFP Module(Main - Work),
					  7:SFP Module(Sub - PROT),
					  8:CTRL PROGRAM VER
					
					  *) SFP Module is available only when MAIN(Work) is STM-1(OPT) and SUB(PROT) is STM-1(OPT).
					  *) Modem(No.1) means Modem(DIR-A) when Redundancy is 2-way.
					  *) Modem(No.2) means Modem(DIR-B) when Redundancy is 2-way."
		::= { pnInvFPGAInfoEntry 2 }

	pnInvFPGAInfoData OBJECT-TYPE
		SYNTAX		OCTET STRING (SIZE (128))
		ACCESS		read-only
		STATUS		mandatory
		DESCRIPTION	"FPGA Info Data
					
					  [Description]
					  (Byte 0 - Byte 15)  = FPGA1 CODE No. (VALUE(ASC(16)))
					  (Byte 16 - Byte 31) = FPGA1 NAME     (VALUE(ASC(16)))
					  (Byte 32 - Byte 37) = FPGA1 VERSION  (VALUE(ASC(6)))
					  (Byte 38 - Byte 53) = FPGA2 CODE No. (VALUE(ASC(16)))  -- Not used
					  (Byte 54 - Byte 69) = FPGA2 NAME     (VALUE(ASC(16)))  -- Not used
					  (Byte 70 - Byte 75) = FPGA2 VERSION  (VALUE(ASC(6)))  -- Not used
					  (Byte 76 - Byte 128) = (Fixed to 0)"
		::= { pnInvFPGAInfoEntry 3 }


	pnInvTRUProvRangeInfoTable OBJECT-TYPE
		SYNTAX		SEQUENCE OF PnInvTRUProvRangeInfoEntry
		ACCESS		not-accessible
		STATUS		mandatory
		DESCRIPTION	"TRU(ODU) Prov Range Info Table"
		::= { pnInvEntryGroup 4 }

	pnInvTRUProvRangeInfoEntry OBJECT-TYPE
		SYNTAX		PnInvTRUProvRangeInfoEntry
		ACCESS		not-accessible
		STATUS		mandatory
		INDEX		{
						pnInvTRUProvRangeInfoPasoIndex
				}
		::= { pnInvTRUProvRangeInfoTable 1 }

	PnInvTRUProvRangeInfoEntry ::= SEQUENCE {
					  pnInvTRUProvRangeInfoPasoIndex  IpAddress,
					  pnInvTRUProvRangeInfoValue   OCTET STRING
					}

	pnInvTRUProvRangeInfoPasoIndex OBJECT-TYPE
		SYNTAX		IpAddress 
		ACCESS		read-only
		STATUS		mandatory
		DESCRIPTION	"Pasolink IP Address Index"
		::= { pnInvTRUProvRangeInfoEntry 1 }

	pnInvTRUProvRangeInfoValue OBJECT-TYPE
		SYNTAX		OCTET STRING (SIZE (32))
		ACCESS		read-only
		STATUS		mandatory
		DESCRIPTION	"ODU Prov Range Info Value
					  [Description]
					  (Byte 0) = ATPC(MAX) (No.1/DIR-A) (VAL(INT))
					  (Byte 1) = ATPC(MIN) (No.1/DIR-A) (VAL(INT))
					  (Byte 2) = MTPC(MAX) (No.1/DIR-A) (VAL(INT))
					  (Byte 3) = MTPC(MIN) (No.1/DIR-A) (VAL(INT))
					  (Byte 4) = RX THRESHOLD LEVEL(MAX) (No.1/DIR-A) integral number(signed char) (VAL(INT))
					  (Byte 5) = RX THRESHOLD LEVEL(MAX) (No.1/DIR-A) a place of decimal(0-9) (VAL(INT))
					  (Byte 6) = RX THRESHOLD LEVEL(MIN) (No.1/DIR-A) integral number(signed char) (VAL(INT))
					  (Byte 7) = RX THRESHOLD LEVEL(MIN) (No.1/DIR-A) a place of decimal(0-9) (VAL(INT))
					  (Byte 8) = ADDITIONAL ATT(MAX) (No.1/DIR-A) (VAL(INT))
					  (Byte 9) = ADDITIONAL ATT(MIN) (No.1/DIR-A) (VAL(INT))
					  (Byte 10) = (Don't care)
					  (Byte 11) = HYSTERESIS(MAX) (No.1/DIR-A) (VAL(INT))
					  (Byte 12) = HYSTERESIS(MIN) (No.1/DIR-A) (VAL(INT))
					  (Byte 13) = BB LNZ POWER(MAX) (No.1/DIR-A) (VAL(INT))
					  (Byte 14) = BB LNZ POWER(MIN) (No.1/DIR-A) (VAL(INT))
					  (Byte 15) = (Don't care)
					  (Byte 16) = ATPC(MAX) (No.2/DIR-B) (VAL(INT))
					  (Byte 17) = ATPC(MIN) (No.2/DIR-B) (VAL(INT))
					  (Byte 18) = MTPC(MAX) (No.2/DIR-B) (VAL(INT))
					  (Byte 19) = MTPC(MIN) (No.2/DIR-B) (VAL(INT))
					  (Byte 20) = RX THRESHOLD LEVEL(MAX) (No.2/DIR-B) integral number(signed char) (VAL(INT))
					  (Byte 21) = RX THRESHOLD LEVEL(MAX) (No.2/DIR-B) a place of decimal(0-9) (VAL(INT))
					  (Byte 22) = RX THRESHOLD LEVEL(MIN) (No.2/DIR-B) integral number(signed char) (VAL(INT))
					  (Byte 23) = RX THRESHOLD LEVEL(MIN) (No.2/DIR-B) a place of decimal(0-9) (VAL(INT))
					  (Byte 24) = ADDITIONAL ATT(MAX) (No.2/DIR-B) (VAL(INT))
					  (Byte 25) = ADDITIONAL ATT(MIN) (No.2/DIR-B) (VAL(INT))
					  (Byte 26) = (Don't care)
					  (Byte 27) = HYSTERESIS(MAX) (No.2/DIR-B) (VAL(INT))
					  (Byte 28) = HYSTERESIS(MIN) (No.2/DIR-B) (VAL(INT))
					  (Byte 29) = BB LNZ POWER(MAX) (No.2/DIR-B) (VAL(INT))
					  (Byte 30) = BB LNZ POWER(MIN) (No.2/DIR-B) (VAL(INT))
					  (Byte 31) = (Don't care)"
		::= { pnInvTRUProvRangeInfoEntry 2 }

	pnInvTRUFreqInfoTable OBJECT-TYPE
		SYNTAX		SEQUENCE OF PnInvTRUFreqInfoEntry
		ACCESS		not-accessible
		STATUS		mandatory
		DESCRIPTION	"TRU(ODU) Freq Info Table"
		::= { pnInvEntryGroup 5 }

	pnInvTRUFreqInfoEntry OBJECT-TYPE
		SYNTAX		PnInvTRUFreqInfoEntry
		ACCESS		not-accessible
		STATUS		mandatory
		INDEX		{
						pnInvTRUFreqInfoSysIndex
					}
		::= { pnInvTRUFreqInfoTable 1 }

	PnInvTRUFreqInfoEntry ::= SEQUENCE {
					  pnInvTRUFreqInfoPasoIndex  IpAddress,
					  pnInvTRUFreqInfoSysIndex  INTEGER,
					  pnInvTRUFreqInfoValue     OCTET STRING
					}

	pnInvTRUFreqInfoPasoIndex OBJECT-TYPE
		SYNTAX		IpAddress 
		ACCESS		read-only
		STATUS		mandatory
		DESCRIPTION	"Pasolink IP Address Index"
		::= { pnInvTRUFreqInfoEntry 1 }

	pnInvTRUFreqInfoSysIndex OBJECT-TYPE
		SYNTAX		INTEGER{
					  no1-dirA(1),
					  no2-dirB(2)
					}
		ACCESS		read-only
		STATUS		mandatory
		DESCRIPTION	"TRU Freq Info Sys Index
					 1:No.1 when EQUIPMENT CONFIG is TERM.
					   DIR-A when EQUIPMENT CONFIG is 2-way
					 2:No.2 when EQUIPMENT CONFIG is TERM.
					   DIR-B when EQUIPMENT CONFIG is 2-way."
		::= { pnInvTRUFreqInfoEntry 2 }

	pnInvTRUFreqInfoValue OBJECT-TYPE
		SYNTAX		OCTET STRING (SIZE (58))
		ACCESS		read-only
		STATUS		mandatory
		DESCRIPTION	"TRU Freq Info Value
					  [Description]
					  (Byte 0 - Byte 8)   = TX START FREQUNENCY[MHz] (VALUE(ASC 9))
					  (Byte 9 - Byte 17)  = TX STOP FREQUNENCY[MHz]  (VALUE(ASC 9))
					  (Byte 18 - Byte 26) = RX START FREQUNENCY[MHz] (VALUE(ASC 9))
					  (Byte 27 - Byte 35) = RX STOP FREQUNENCY[MHz]  (VALUE(ASC 9))
					  (Byte 36 - Byte 42) = FREQUENCY STEP[MHz]      (VALUE(ASC 7))
					  (Byte 43 - Byte 50) = SHIFT FREQUENCY[MHz]     (VALUE(ASC 8))
					  (Byte 51)           = UPPER/LOWER              (0:LOWER, 1:UPPER)
					  (Byte 52 -Byte 54)  = (Don't care)
					  (Byte 55)           = SUB BAND                 (VALUE(ASC 1))
					  (Byte 56)           = TX/RX INDEPENDENT INFO   (0: TX&RX, 1:TX/RX)
					  (Byte 57)           = (Don't care)
					"
		::= { pnInvTRUFreqInfoEntry 3 }


	pnInvEquipmentSupportabilityTable OBJECT-TYPE
		SYNTAX		SEQUENCE OF PnInvEquipmentSupportabilityEntry
		ACCESS		not-accessible
		STATUS		mandatory
		DESCRIPTION	"Inv Equipment Supportability Table"
		::= { pnInvEntryGroup 6 }

	pnInvEquipmentSupportabilityEntry OBJECT-TYPE
		SYNTAX		PnInvEquipmentSupportabilityEntry
		ACCESS		not-accessible
		STATUS		mandatory
		INDEX		{
						pnInvEquipmentSupportabilityPasoIndex
					}
		::= { pnInvEquipmentSupportabilityTable 1 }

	PnInvEquipmentSupportabilityEntry ::= SEQUENCE {
					  pnInvEquipmentSupportabilityPasoIndex  IpAddress,
					  pnInvEquipmentSupportabilityInfo     OCTET STRING
					}

	pnInvEquipmentSupportabilityPasoIndex OBJECT-TYPE
		SYNTAX		IpAddress 
		ACCESS		read-only
		STATUS		mandatory
		DESCRIPTION	"Pasolink IP Address Index"
		::= { pnInvEquipmentSupportabilityEntry 1 }

	pnInvEquipmentSupportabilityInfo OBJECT-TYPE
		SYNTAX		OCTET STRING (SIZE (7))
		ACCESS		read-only
		STATUS		mandatory
		DESCRIPTION	"Equipment Supportability Info
				 This item is used for only PNMS and PNMT.
				 NEO STD MIB (Less than Ver.1.84) are OCTET STRING (SIZE (6))."
		::= { pnInvEquipmentSupportabilityEntry 2 }

	pnInvUpdateInfoTable OBJECT-TYPE
		SYNTAX		SEQUENCE OF PnInvUpdateInfoEntry
		ACCESS		not-accessible
		STATUS		mandatory
		DESCRIPTION	"TRU(ODU) Freq Info Table"
		::= { pnInvEntryGroup 7 }

	pnInvUpdateInfoEntry OBJECT-TYPE
		SYNTAX		PnInvUpdateInfoEntry
		ACCESS		not-accessible
		STATUS		mandatory
		INDEX		{
						pnInvUpdateInfoPasoIndex
					}
		::= { pnInvUpdateInfoTable 1 }

	PnInvUpdateInfoEntry ::= SEQUENCE {
					  pnInvUpdateInfoPasoIndex  IpAddress,
					  pnInvUpdateInfoMainWorkModule	INTEGER,
					  pnInvUpdateInfoSubProtModule	INTEGER,
					  pnInvUpdateInfoSummary	OCTET STRING
					}

	pnInvUpdateInfoPasoIndex OBJECT-TYPE
		SYNTAX		IpAddress 
		ACCESS		read-only
		STATUS		mandatory
		DESCRIPTION	"Pasolink IP Address Index"
		::= { pnInvUpdateInfoEntry 1 }

	pnInvUpdateInfoMainWorkModule OBJECT-TYPE
		SYNTAX		INTEGER (0..255)
		ACCESS		read-only
		STATUS		mandatory
		DESCRIPTION	"INTFC(1) PKG CHANGED
					  0:INVALID,
					  1:BLANK,
					  2:16xE1 BASIC PKG,
					  3:16xE1 STANDARD PKG(E/W LAN),
					  4:32xE1 PKG(E/W LAN),
					  5:48xE1 PKG,
					  6:4PORT LAN WITH E1,
					  7:STM-1(OPTICAL),
					  8:STM-1(ELECTRICAL),
					  9:2PORT LAN OVER STM-1,
					  10:GbE OVER STM-1,
					  11:E3 PKG(E/W LAN),
					  12:16E1 2-WAY/XC PKG(E/W LAN),
					  14:GbE(10/100/1000B) OVER STM-1
					TRAP=eventTrapPnSTDinvUpdateMainWorkModule"
		::= { pnInvUpdateInfoEntry 2 }

	pnInvUpdateInfoSubProtModule OBJECT-TYPE
		SYNTAX		INTEGER (0..255)
		ACCESS		read-only
		STATUS		mandatory
		DESCRIPTION	"INTFC(2) PKG CHANGED
					  0:INVALID,
					  1:BLANK,
					  2:STM-1(OPTICAL),
					  3:WS/LAN,
					  4:WS
					TRAP=eventTrapPnSTDinvUpdateSubProtModule"
		::= { pnInvUpdateInfoEntry 3 }

	pnInvUpdateInfoSummary OBJECT-TYPE
		SYNTAX		OCTET STRING (SIZE (2))
		ACCESS		read-only
		STATUS		mandatory
		DESCRIPTION	"INVENTORY UPDATE INFO SUMMARY
					
					  [Description]
					  (Bit 0) = CTRL (0:Not Changed, 1:Updated)
					  (Bit 1) = MODEM1
					  (Bit 2) = MODEM2
					  (Bit 3) = MAIN(WORK)
					  (Bit 4) = SUB(PROT)
					  (Bit 5) = TRU1
					  (Bit 6) = TRU2
					  (Bit 7) = CTRL PROGRAM VERSION
					  (Bit 8) = TRU PROVISIONING INFO
					  (Bit 9) = TRU FREQ INFO
					  (Bit 10) = SUPPORTABILITY
					  (Bit 11) = (Fixed to 0)
					  (Bit 12) = (Fixed to 0)
					  (Bit 13) = (Fixed to 0)
					  (Bit 14) = (Fixed to 0)
					  (Bit 15) = (Fixed to 0)
					
					TRAP=eventTrapPnSTDinvUpdateSummary"
		::= { pnInvUpdateInfoEntry 4 }


-----------------------------------------------
-- pnMeteringGroup Group Definitions
-----------------------------------------------

	pnMeteringSysTable OBJECT-TYPE
		SYNTAX		SEQUENCE OF PnMeteringSysEntry
		ACCESS		not-accessible
		STATUS		mandatory
		DESCRIPTION	"Metering Sys Table"
		::= { pnMeteringGroup 1 }

	pnMeteringSysEntry OBJECT-TYPE
		SYNTAX		PnMeteringSysEntry
		ACCESS		not-accessible
		STATUS		mandatory
		INDEX		{
						pnMetSysPasoIndex,
						pnMetSysIndex
					}
		::= { pnMeteringSysTable 1 }

	PnMeteringSysEntry ::= SEQUENCE {
					  pnMetSysPasoIndex           IpAddress,
					  pnMetSysIndex               INTEGER,
					  pnMetSysTxPowerStatus       INTEGER,
					  pnMetSysTxPowerValue        DisplayString,
					  pnMetSysRxLevelStatus       INTEGER,
					  pnMetSysRxLevelValue        DisplayString,
					  pnMetSysPSVoltageStatus     INTEGER,
					  pnMetSysPSVoltageValue      DisplayString,
					  pnMetSysBitErrorRateStatus  INTEGER,
					  pnMetSysBitErrorRateXValue  INTEGER,
					  pnMetSysBitErrorRateYValue  INTEGER
					}

	pnMetSysPasoIndex OBJECT-TYPE
		SYNTAX		IpAddress 
		ACCESS		read-only
		STATUS		mandatory
		DESCRIPTION	"Pasolink IP Address Index"
		::= { pnMeteringSysEntry 1 }

	pnMetSysIndex OBJECT-TYPE
		SYNTAX		INTEGER{
					  no1-dirA(1),
					  no2-dirB(2)
					}
		ACCESS		read-only
		STATUS		mandatory
		DESCRIPTION	"Meterigy Sys Index
					 1:No.1 when EQUIPMENT CONFIG is TERM.
					   DIR-A when EQUIPMENT CONFIG is 2-WAY
					 2:No.2 when EQUIPMENT CONFIG is TERM.
					   DIR-B when EQUIPMENT CONFIG is 2-WAY."
		::= { pnMeteringSysEntry 2 }

	pnMetSysTxPowerStatus OBJECT-TYPE
		SYNTAX		INTEGER (0..2)
		ACCESS		read-only
		STATUS		mandatory
		DESCRIPTION	"TX POWER Status
					  0:Invalid(Not obtained, Over range),
					  1:Invalid(Index No.2, when Redundancy is 1+0 term.),
					  2:Valid"
		::= { pnMeteringSysEntry 3 }

	pnMetSysTxPowerValue OBJECT-TYPE
		SYNTAX		DisplayString (SIZE (0..5))
		ACCESS		read-only
		STATUS		mandatory
		DESCRIPTION	"TX POWER [dBm]
					  expression: +/-**.*(5bytes)
					
					  *)This value is not guaranteed when pnMetSysTxPowerStatus is Invalid(0 and 1)."
		::= { pnMeteringSysEntry 4 }

	pnMetSysRxLevelStatus OBJECT-TYPE
		SYNTAX		INTEGER (0..2)
		ACCESS		read-only
		STATUS		mandatory
		DESCRIPTION	"RX Level Status
					  0:Invalid(Not obtained, Over range),
					  1:Invalid(Index No.2, when Redundancy is 1+0 term.),
					  2:Valid"
		::= { pnMeteringSysEntry 5 }

	pnMetSysRxLevelValue OBJECT-TYPE
		SYNTAX		DisplayString (SIZE (0..5))
		ACCESS		read-only
		STATUS		mandatory
		DESCRIPTION	"RX Level [dBm]
					  expression: +/-**.*(5bytes)
					
					  *)This value is not guaranteed when pnMetSysRxLevelStatus is Invalid(0 and 1)."
		::= { pnMeteringSysEntry 6 }

	pnMetSysPSVoltageStatus OBJECT-TYPE
		SYNTAX		INTEGER (0..2)
		ACCESS		read-only
		STATUS		mandatory
		DESCRIPTION	"ODU PS Status
					  0:Invalid(Not obtained, Over range),
					  1:Invalid(Index No.2, when Redundancy is 1+0 term.),
					  2:Valid"
		::= { pnMeteringSysEntry 7 }

	pnMetSysPSVoltageValue OBJECT-TYPE
		SYNTAX		DisplayString (SIZE (0..3))
		ACCESS		read-only
		STATUS		mandatory
		DESCRIPTION	"ODU PS [V]
					  expression: -**(3bytes)
					
					  *)This value is not guaranteed when pnMetSysPSVoltageStasus is Invalid(0 and 1).
					  "
		::= { pnMeteringSysEntry 8 }

	pnMetSysBitErrorRateStatus OBJECT-TYPE
		SYNTAX		INTEGER (0..255)
		ACCESS		read-only
		STATUS		mandatory
		DESCRIPTION	"Bit Error Rate Status
					  0:Invalid,
					  42:Invalid(Equipment Level),
					  127:Calculating,
					  255:latest value
					  *) Index 2 is unavailable."
		::= { pnMeteringSysEntry 9 }

	pnMetSysBitErrorRateXValue OBJECT-TYPE
		SYNTAX		INTEGER (-1..99)
		ACCESS		read-only
		STATUS		mandatory
		DESCRIPTION	"BER (Significand Part)
					  This Value shows significant Value for BER times 10.
					  This stautus is invalid when value is -1.
					
					  (Example)
					   BER = 1.2E-6
					
					   This value is 12."
		::= { pnMeteringSysEntry 10 }

	pnMetSysBitErrorRateYValue OBJECT-TYPE
		SYNTAX		INTEGER (-1..99)
		ACCESS		read-only
		STATUS		mandatory
		DESCRIPTION	"BER (Exponential Part)
					  This Value shows Exponential Part for BER.
					  This stautus is invalid when value is -1.
					
					  (Example)
					   BER = 1.2E-6
					
					   This value is 6."
		::= { pnMeteringSysEntry 11 }


-----------------------------------------------
-- Pasolink NEO GET METERING DATA Table
-----------------------------------------------

	pnGetMeteringInfoData OBJECT IDENTIFIER
 		::= { pnGetMeasurementDataGroup 1 }

	pnGetMeteringInfoDataTable OBJECT-TYPE
		SYNTAX		SEQUENCE OF PnGetMeteringInfoDataEntry
		ACCESS		not-accessible
		STATUS		mandatory
		DESCRIPTION	"Measurement Data Table"
		::= { pnGetMeteringInfoData 1 }
	
	pnGetMeteringInfoDataEntry OBJECT-TYPE
		SYNTAX		PnGetMeteringInfoDataEntry
		ACCESS		not-accessible
		STATUS		mandatory
		DESCRIPTION	"Measurement Table Entry"
		INDEX { pngmiManagerIndex } 
		::= { pnGetMeteringInfoDataTable 1 }

	PnGetMeteringInfoDataEntry ::= SEQUENCE {
		pngmiManagerIndex		IpAddress,
		pngmiRequestID		        INTEGER,
		pngmiTargetPasolink		IpAddress,
		pngmiDataStatus	        	INTEGER	
	}

	pngmiManagerIndex OBJECT-TYPE
		SYNTAX		IpAddress
		ACCESS		read-only
		STATUS		mandatory
		DESCRIPTION	"Upper Manager IpAddress"
		::= { pnGetMeteringInfoDataEntry 1 }

	pngmiRequestID OBJECT-TYPE
		SYNTAX		INTEGER (1..9999)
		ACCESS		read-write
		STATUS		mandatory
		DESCRIPTION	"Request ID"
		::= { pnGetMeteringInfoDataEntry 2 }
		
	pngmiTargetPasolink OBJECT-TYPE
		SYNTAX		IpAddress
		ACCESS		read-write
		STATUS		mandatory
		DESCRIPTION	"Target Pasolink IpAddress"
		::= { pnGetMeteringInfoDataEntry 3 }
	
	pngmiDataStatus OBJECT-TYPE
		SYNTAX		INTEGER (0..3)
		ACCESS		read-only
		STATUS		mandatory
		DESCRIPTION	"Data Status
		                     invalid(0),
		                     ready(1),
		                     wait(2),
	                               fail(3)"
		::= { pnGetMeteringInfoDataEntry 4 }
		
-----------------------------------------------
-- End User MIB Object Definitions
-----------------------------------------------
END

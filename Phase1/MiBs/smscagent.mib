--
--        CMG SMSC Agent MIB
--
CMG-SMSC-MIB DEFINITIONS ::= BEGIN
    IMPORTS
        MODULE-IDENTITY, OBJECT-TYPE,NOTIFICATION-TYPE, Unsigned32
            FROM SNMPV2-SMI

        TEXTUAL-CONVENTION, DisplayString
            FROM SNMPV2-TC

        smscAgent,
        trapNotificationId, trapSeverity,
        trapData, trapEntityName,
        trapTimeStamp, trapNodeName,
        trapProbableCause, trapEventType,
        trapSpecificProblem
            FROM CMG-TRAP-MIB;
-- --------------------------------------
-- SMSC MIB entry starts here
--
	smscAgentInfo        OBJECT IDENTIFIER ::= { smscAgent 1 }
	smscAgentCfg         OBJECT IDENTIFIER ::= { smscAgent 2 }
	smscClassSmh         OBJECT IDENTIFIER ::= { smscAgent 3 }
	smscClassSiw         OBJECT IDENTIFIER ::= { smscAgent 4 }
	smscClassDiw         OBJECT IDENTIFIER ::= { smscAgent 5 }
	smscClassServerOld   OBJECT IDENTIFIER ::= { smscAgent 6 }
	smscClassOtherOld    OBJECT IDENTIFIER ::= { smscAgent 7 }
	smscTrapFilterCfgOld OBJECT IDENTIFIER ::= { smscAgent 8 }
	smscClassServer      OBJECT IDENTIFIER ::= { smscAgent 9 }
	smscClassOther       OBJECT IDENTIFIER ::= { smscAgent 10 }
	smscClassManagement  OBJECT IDENTIFIER ::= { smscAgent 11 }
	smscTrapFilterCfg    OBJECT IDENTIFIER ::= { smscAgent 12 }
	smscClassTrap        OBJECT IDENTIFIER ::= { smscAgent 13 }


	smscAgentDescription  OBJECT-TYPE
		SYNTAX  DisplayString
		MAX-ACCESS  read-only
		STATUS  current
		DESCRIPTION
			"Identifier of the SMSCAgent."
		::= { smscAgentInfo 1 }


	smscAgentRestart  OBJECT-TYPE
		SYNTAX  INTEGER {
			restart(1)
			}
		MAX-ACCESS  write-only
		STATUS  current
		DESCRIPTION
			"Restart of the SMSCAgent."
		::= { smscAgentCfg 1 }
-- --------------------------------------



-- --------------------------------------
-- Class SMH
-- 
smscSmh OBJECT-TYPE
	SYNTAX  SEQUENCE OF SmhInstanceEntry
	MAX-ACCESS  not-accessible
	STATUS  current
	DESCRIPTION
		"Mapping table for SMSC SMH entities."
   ::= { smscClassSmh   1  }

smhInstanceEntry  OBJECT-TYPE
	SYNTAX SmhInstanceEntry
	MAX-ACCESS  not-accessible
	STATUS  current
	DESCRIPTION
		"An entry (row) in the entityInstanceTable."
	INDEX { IMPLIED smscSmhName }
   ::= { smscSmh 1 }

SmhInstanceEntry ::= SEQUENCE {
		smscSmhName     DisplayString,
		smscSmhState   INTEGER,
		smscSmhLastupdate   TimeTicks,
		smscSmhNode	   DisplayString, 
		smscSmhAllocatedAddrblocks	 Unsigned32, 
		smscSmhBufTimeCumulative	 Unsigned32, 
		smscSmhForeignAddrblocks	 Unsigned32, 
		smscSmhSmInvalid	 Unsigned32, 
		smscSmhLengthSmCumulative	 Unsigned32, 
		smscSmhMsgBuffered	 Unsigned32, 
		smscSmhMsgReceived	 Unsigned32, 
		smscSmhMsgRejected	 Unsigned32, 
		smscSmhMsgTransmitted	 Unsigned32, 
		smscSmhNextDelivery	 Unsigned32, 
		smscSmhNotifBuffered	 Unsigned32, 
		smscSmhNotifFailed	 Unsigned32, 
		smscSmhNotifTransmitted	 Unsigned32, 
		smscSmhSmBuffered	 Unsigned32, 
		smscSmhSmFailed	 Unsigned32, 
		smscSmhSmReceived	 Unsigned32, 
		smscSmhSmTransmitted	 Unsigned32, 
		smscSmhSmDismissed	 Unsigned32, 
		smscSmhSmValid	 Unsigned32, 
		smscSmhWaitAddrblocks	 Unsigned32, 
		smscSmhMsgFailed	 Unsigned32, 
		smscSmhQelemUsed	 Unsigned32, 
		smscSmhQelemInProcqueue	 Unsigned32, 
		smscSmhQelemInExpqueue	 Unsigned32, 
		smscSmhNrTimersRunning	 Unsigned32, 
		smscSmhNrSystemTimers	 Unsigned32, 
		smscSmhImiRecallQelem	 Unsigned32, 
		smscSmhImiRecallQueues	 Unsigned32, 
		smscSmhIdiRecallQelem	 Unsigned32, 
		smscSmhIdiRecallQueues	 Unsigned32, 
		smscSmhIosRecallQelem	 Unsigned32, 
		smscSmhIosRecallQueues	 Unsigned32, 
		smscSmhLogRecallQelem	 Unsigned32, 
		smscSmhLogRecallQueues	 Unsigned32, 
		smscSmhTrcreqDiscarded	 Unsigned32, 
		smscSmhReplyPathEntries	 Unsigned32, 
		smscSmhLicenseLimitReached	 Unsigned32, 
		smscSmhMsgDeferred	 Unsigned32, 
		smscSmhSingleShotDelivered	 Unsigned32, 
		smscSmhSingleShotAccepted	 Unsigned32, 
		smscSmhSingleShotRejected	 Unsigned32, 
		smscSmhLicenseLimitDelay	 Unsigned32, 
		smscSmhPpTimeJammed	 Unsigned32, 
		smscSmhPpChargedPserInjam	 Unsigned32, 
		smscSmhPpFreePserInjam	 Unsigned32, 
		smscSmhPpBlockedPserInjam	 Unsigned32, 
		smscSmhPpRejectedPserInjam	 Unsigned32, 
		smscSmhPpChargedAserInjam	 Unsigned32, 
		smscSmhPpFreeAserInjam	 Unsigned32, 
		smscSmhPpBlockedAserInjam	 Unsigned32, 
		smscSmhPpPserTimeouts	 Unsigned32, 
		smscSmhPpAserTimeouts	 Unsigned32, 
		smscSmhUmfMsgsOk	 Unsigned32, 
		smscSmhUmfMsgsFailed	 Unsigned32, 
		smscSmhMultiReceived	 Unsigned32, 
		smscSmhSingleReceived	 Unsigned32, 
		smscSmhMultiTransmitted	 Unsigned32, 
		smscSmhSingleTransmitted	 Unsigned32, 
		smscSmhMsgSegments	 Unsigned32, 
		smscSmhCachedAddrblocks	 Unsigned32, 
		smscSmhMsgToRecQueued	 Unsigned32, 
		smscSmhMsgToRecCached	 Unsigned32, 
		smscSmhFirstDelivAttempt	 Unsigned32, 
		smscSmhRetryAttempt	 Unsigned32, 
		smscSmhDeliveryAttempt	 Unsigned32, 
		smscSmhMaxFirstDelDelay	 Unsigned32, 
		smscSmhMaxRetryDelay	 Unsigned32, 
		smscSmhRejectedFirstDel	 Unsigned32, 
		smscSmhDiscardedFirstDel	 Unsigned32, 
		smscSmhQueuedForFirstDel	 Unsigned32, 
		smscSmhQueuedForRetry	 Unsigned32, 
		smscSmhAbnDelivered	 Unsigned32, 
		smscSmhLogsrvInternLost	 Unsigned32, 
		smscSmhEnumWaitAddrblocks	 Unsigned32, 
		smscSmhEnumQueries	 Unsigned32, 
		smscSmhEnumAfterMtPlmn	 Unsigned32, 
		smscSmhEnumBeforeMtPlmn	 Unsigned32, 
		smscSmhEnumAfterMtGw	 Unsigned32, 
		smscSmhEnumBeforeMtGw	 Unsigned32, 
		smscSmhEnumNoResult	 Unsigned32
	}

smscSmhName  OBJECT-TYPE
	SYNTAX  DisplayString
	MAX-ACCESS  read-only
	STATUS   current
	DESCRIPTION
		"Identifies the name of the entity."
   ::= {smhInstanceEntry 1 }

smscSmhState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { smhInstanceEntry 2 }


smscSmhLastupdate OBJECT-TYPE
		SYNTAX	TimeTicks
		MAX-ACCESS read-only
		STATUS current
		DESCRIPTION
			"Value which reflects the last time the entities fields have been updated"
	::= { smhInstanceEntry	3 }

smscSmhNode  OBJECT-TYPE
	SYNTAX  DisplayString
	MAX-ACCESS  read-only
	STATUS   current
	DESCRIPTION
		"Identifies the node the entity is running on."
   ::= {smhInstanceEntry 4 }

smscSmhAllocatedAddrblocks OBJECT-TYPE
		SYNTAX	Unsigned32
		MAX-ACCESS read-only
		STATUS current
		DESCRIPTION
			"Allocated/active address blocks"
	::= { smhInstanceEntry	5 }

smscSmhBufTimeCumulative OBJECT-TYPE
		SYNTAX	Unsigned32
		MAX-ACCESS read-only
		STATUS current
		DESCRIPTION
			"Accumulated time buffered messages"
	::= { smhInstanceEntry	6 }

smscSmhForeignAddrblocks OBJECT-TYPE
		SYNTAX	Unsigned32
		MAX-ACCESS read-only
		STATUS current
		DESCRIPTION
			"Address blocks in foreign queue"
	::= { smhInstanceEntry	7 }

smscSmhSmInvalid OBJECT-TYPE
		SYNTAX	Unsigned32
		MAX-ACCESS read-only
		STATUS current
		DESCRIPTION
			"Received invalid short messages"
	::= { smhInstanceEntry	8 }

smscSmhLengthSmCumulative OBJECT-TYPE
		SYNTAX	Unsigned32
		MAX-ACCESS read-only
		STATUS current
		DESCRIPTION
			"Accumulated length of accepted short messages"
	::= { smhInstanceEntry	9 }

smscSmhMsgBuffered OBJECT-TYPE
		SYNTAX	Unsigned32
		MAX-ACCESS read-only
		STATUS current
		DESCRIPTION
			"Buffered short messages and notifications"
	::= { smhInstanceEntry	10 }

smscSmhMsgReceived OBJECT-TYPE
		SYNTAX	Unsigned32
		MAX-ACCESS read-only
		STATUS current
		DESCRIPTION
			"Received messages"
	::= { smhInstanceEntry	11 }

smscSmhMsgRejected OBJECT-TYPE
		SYNTAX	Unsigned32
		MAX-ACCESS read-only
		STATUS current
		DESCRIPTION
			"Received messages and rejected"
	::= { smhInstanceEntry	12 }

smscSmhMsgTransmitted OBJECT-TYPE
		SYNTAX	Unsigned32
		MAX-ACCESS read-only
		STATUS current
		DESCRIPTION
			"Transmitted messages"
	::= { smhInstanceEntry	13 }

smscSmhNextDelivery OBJECT-TYPE
		SYNTAX	Unsigned32
		MAX-ACCESS read-only
		STATUS current
		DESCRIPTION
			"Short messages and notif. in next delivery queues"
	::= { smhInstanceEntry	14 }

smscSmhNotifBuffered OBJECT-TYPE
		SYNTAX	Unsigned32
		MAX-ACCESS read-only
		STATUS current
		DESCRIPTION
			"Buffered notifications"
	::= { smhInstanceEntry	15 }

smscSmhNotifFailed OBJECT-TYPE
		SYNTAX	Unsigned32
		MAX-ACCESS read-only
		STATUS current
		DESCRIPTION
			"Notifications submitted and failed"
	::= { smhInstanceEntry	16 }

smscSmhNotifTransmitted OBJECT-TYPE
		SYNTAX	Unsigned32
		MAX-ACCESS read-only
		STATUS current
		DESCRIPTION
			"Transmitted notifications"
	::= { smhInstanceEntry	17 }

smscSmhSmBuffered OBJECT-TYPE
		SYNTAX	Unsigned32
		MAX-ACCESS read-only
		STATUS current
		DESCRIPTION
			"Buffered short messages"
	::= { smhInstanceEntry	18 }

smscSmhSmFailed OBJECT-TYPE
		SYNTAX	Unsigned32
		MAX-ACCESS read-only
		STATUS current
		DESCRIPTION
			"Short messages submitted and failed"
	::= { smhInstanceEntry	19 }

smscSmhSmReceived OBJECT-TYPE
		SYNTAX	Unsigned32
		MAX-ACCESS read-only
		STATUS current
		DESCRIPTION
			"Received short messages"
	::= { smhInstanceEntry	20 }

smscSmhSmTransmitted OBJECT-TYPE
		SYNTAX	Unsigned32
		MAX-ACCESS read-only
		STATUS current
		DESCRIPTION
			"Transmitted short messages"
	::= { smhInstanceEntry	21 }

smscSmhSmDismissed OBJECT-TYPE
		SYNTAX	Unsigned32
		MAX-ACCESS read-only
		STATUS current
		DESCRIPTION
			"Received valid and rejected short messages"
	::= { smhInstanceEntry	22 }

smscSmhSmValid OBJECT-TYPE
		SYNTAX	Unsigned32
		MAX-ACCESS read-only
		STATUS current
		DESCRIPTION
			"Received valid short messages"
	::= { smhInstanceEntry	23 }

smscSmhWaitAddrblocks OBJECT-TYPE
		SYNTAX	Unsigned32
		MAX-ACCESS read-only
		STATUS current
		DESCRIPTION
			"Address blocks waiting for response"
	::= { smhInstanceEntry	24 }

smscSmhMsgFailed OBJECT-TYPE
		SYNTAX	Unsigned32
		MAX-ACCESS read-only
		STATUS current
		DESCRIPTION
			"Messages that failed on sending"
	::= { smhInstanceEntry	25 }

smscSmhQelemUsed OBJECT-TYPE
		SYNTAX	Unsigned32
		MAX-ACCESS read-only
		STATUS current
		DESCRIPTION
			"Number of elements in internal queues"
	::= { smhInstanceEntry	26 }

smscSmhQelemInProcqueue OBJECT-TYPE
		SYNTAX	Unsigned32
		MAX-ACCESS read-only
		STATUS current
		DESCRIPTION
			"Number of elements used in process queue"
	::= { smhInstanceEntry	27 }

smscSmhQelemInExpqueue OBJECT-TYPE
		SYNTAX	Unsigned32
		MAX-ACCESS read-only
		STATUS current
		DESCRIPTION
			"Number of elements used in expedited queue"
	::= { smhInstanceEntry	28 }

smscSmhNrTimersRunning OBJECT-TYPE
		SYNTAX	Unsigned32
		MAX-ACCESS read-only
		STATUS current
		DESCRIPTION
			"Total number of timers running"
	::= { smhInstanceEntry	29 }

smscSmhNrSystemTimers OBJECT-TYPE
		SYNTAX	Unsigned32
		MAX-ACCESS read-only
		STATUS current
		DESCRIPTION
			"Number of system timers running"
	::= { smhInstanceEntry	30 }

smscSmhImiRecallQelem OBJECT-TYPE
		SYNTAX	Unsigned32
		MAX-ACCESS read-only
		STATUS current
		DESCRIPTION
			"Number of IMI recall-queue elements used"
	::= { smhInstanceEntry	31 }

smscSmhImiRecallQueues OBJECT-TYPE
		SYNTAX	Unsigned32
		MAX-ACCESS read-only
		STATUS current
		DESCRIPTION
			"Number of IMI-recall-queues used"
	::= { smhInstanceEntry	32 }

smscSmhIdiRecallQelem OBJECT-TYPE
		SYNTAX	Unsigned32
		MAX-ACCESS read-only
		STATUS current
		DESCRIPTION
			"Number of IDI recall-queue elements used"
	::= { smhInstanceEntry	33 }

smscSmhIdiRecallQueues OBJECT-TYPE
		SYNTAX	Unsigned32
		MAX-ACCESS read-only
		STATUS current
		DESCRIPTION
			"Number of IDI recall-queues used"
	::= { smhInstanceEntry	34 }

smscSmhIosRecallQelem OBJECT-TYPE
		SYNTAX	Unsigned32
		MAX-ACCESS read-only
		STATUS current
		DESCRIPTION
			"Number of IOS recall-queue elements used"
	::= { smhInstanceEntry	35 }

smscSmhIosRecallQueues OBJECT-TYPE
		SYNTAX	Unsigned32
		MAX-ACCESS read-only
		STATUS current
		DESCRIPTION
			"Number of IOS recall-queues used"
	::= { smhInstanceEntry	36 }

smscSmhLogRecallQelem OBJECT-TYPE
		SYNTAX	Unsigned32
		MAX-ACCESS read-only
		STATUS current
		DESCRIPTION
			"Number of LOG recall-queue elements used"
	::= { smhInstanceEntry	37 }

smscSmhLogRecallQueues OBJECT-TYPE
		SYNTAX	Unsigned32
		MAX-ACCESS read-only
		STATUS current
		DESCRIPTION
			"Number of LOG recall-queues used"
	::= { smhInstanceEntry	38 }

smscSmhTrcreqDiscarded OBJECT-TYPE
		SYNTAX	Unsigned32
		MAX-ACCESS read-only
		STATUS current
		DESCRIPTION
			"Number of trace requests discarded"
	::= { smhInstanceEntry	39 }

smscSmhReplyPathEntries OBJECT-TYPE
		SYNTAX	Unsigned32
		MAX-ACCESS read-only
		STATUS current
		DESCRIPTION
			"Reply path entries"
	::= { smhInstanceEntry	40 }

smscSmhLicenseLimitReached OBJECT-TYPE
		SYNTAX	Unsigned32
		MAX-ACCESS read-only
		STATUS current
		DESCRIPTION
			"Number of times the license-limit was reached"
	::= { smhInstanceEntry	41 }

smscSmhMsgDeferred OBJECT-TYPE
		SYNTAX	Unsigned32
		MAX-ACCESS read-only
		STATUS current
		DESCRIPTION
			"Short mess. and notif. in def. del. queues"
	::= { smhInstanceEntry	42 }

smscSmhSingleShotDelivered OBJECT-TYPE
		SYNTAX	Unsigned32
		MAX-ACCESS read-only
		STATUS current
		DESCRIPTION
			"Number of delivered Single Shot messages"
	::= { smhInstanceEntry	43 }

smscSmhSingleShotAccepted OBJECT-TYPE
		SYNTAX	Unsigned32
		MAX-ACCESS read-only
		STATUS current
		DESCRIPTION
			"Number of accepted Single Shot messages"
	::= { smhInstanceEntry	44 }

smscSmhSingleShotRejected OBJECT-TYPE
		SYNTAX	Unsigned32
		MAX-ACCESS read-only
		STATUS current
		DESCRIPTION
			"Number of rejected Single Shot messages"
	::= { smhInstanceEntry	45 }

smscSmhLicenseLimitDelay OBJECT-TYPE
		SYNTAX	Unsigned32
		MAX-ACCESS read-only
		STATUS current
		DESCRIPTION
			"Maximum delay caused by the license limit  seconds"
	::= { smhInstanceEntry	46 }

smscSmhPpTimeJammed OBJECT-TYPE
		SYNTAX	Unsigned32
		MAX-ACCESS read-only
		STATUS current
		DESCRIPTION
			"Total time the Payment Broker interface was JAMMED  seconds"
	::= { smhInstanceEntry	47 }

smscSmhPpChargedPserInjam OBJECT-TYPE
		SYNTAX	Unsigned32
		MAX-ACCESS read-only
		STATUS current
		DESCRIPTION
			"Number of Charged Primary Services in JAMMED"
	::= { smhInstanceEntry	48 }

smscSmhPpFreePserInjam OBJECT-TYPE
		SYNTAX	Unsigned32
		MAX-ACCESS read-only
		STATUS current
		DESCRIPTION
			"Number of Free Primary Services in JAMMED"
	::= { smhInstanceEntry	49 }

smscSmhPpBlockedPserInjam OBJECT-TYPE
		SYNTAX	Unsigned32
		MAX-ACCESS read-only
		STATUS current
		DESCRIPTION
			"Number of Blocked Primary Services in JAMMED"
	::= { smhInstanceEntry	50 }

smscSmhPpRejectedPserInjam OBJECT-TYPE
		SYNTAX	Unsigned32
		MAX-ACCESS read-only
		STATUS current
		DESCRIPTION
			"Number of Rejected Primary Services in JAMMED"
	::= { smhInstanceEntry	51 }

smscSmhPpChargedAserInjam OBJECT-TYPE
		SYNTAX	Unsigned32
		MAX-ACCESS read-only
		STATUS current
		DESCRIPTION
			"Number of Charged Additional Services in JAMMED"
	::= { smhInstanceEntry	52 }

smscSmhPpFreeAserInjam OBJECT-TYPE
		SYNTAX	Unsigned32
		MAX-ACCESS read-only
		STATUS current
		DESCRIPTION
			"Number of Free Additional Services in JAMMED"
	::= { smhInstanceEntry	53 }

smscSmhPpBlockedAserInjam OBJECT-TYPE
		SYNTAX	Unsigned32
		MAX-ACCESS read-only
		STATUS current
		DESCRIPTION
			"Number of Blocked Additional Services in JAMMED"
	::= { smhInstanceEntry	54 }

smscSmhPpPserTimeouts OBJECT-TYPE
		SYNTAX	Unsigned32
		MAX-ACCESS read-only
		STATUS current
		DESCRIPTION
			"Number timed out Primary services"
	::= { smhInstanceEntry	55 }

smscSmhPpAserTimeouts OBJECT-TYPE
		SYNTAX	Unsigned32
		MAX-ACCESS read-only
		STATUS current
		DESCRIPTION
			"Number timed out Additional Services"
	::= { smhInstanceEntry	56 }

smscSmhUmfMsgsOk OBJECT-TYPE
		SYNTAX	Unsigned32
		MAX-ACCESS read-only
		STATUS current
		DESCRIPTION
			"Number of successfully forwarded UM messages"
	::= { smhInstanceEntry	57 }

smscSmhUmfMsgsFailed OBJECT-TYPE
		SYNTAX	Unsigned32
		MAX-ACCESS read-only
		STATUS current
		DESCRIPTION
			"Number of failed forwarded UM messages"
	::= { smhInstanceEntry	58 }

smscSmhMultiReceived OBJECT-TYPE
		SYNTAX	Unsigned32
		MAX-ACCESS read-only
		STATUS current
		DESCRIPTION
			"Received extended messages"
	::= { smhInstanceEntry	59 }

smscSmhSingleReceived OBJECT-TYPE
		SYNTAX	Unsigned32
		MAX-ACCESS read-only
		STATUS current
		DESCRIPTION
			"Received single messages"
	::= { smhInstanceEntry	60 }

smscSmhMultiTransmitted OBJECT-TYPE
		SYNTAX	Unsigned32
		MAX-ACCESS read-only
		STATUS current
		DESCRIPTION
			"Transmitted extended messages"
	::= { smhInstanceEntry	61 }

smscSmhSingleTransmitted OBJECT-TYPE
		SYNTAX	Unsigned32
		MAX-ACCESS read-only
		STATUS current
		DESCRIPTION
			"Transmitted single messages"
	::= { smhInstanceEntry	62 }

smscSmhMsgSegments OBJECT-TYPE
		SYNTAX	Unsigned32
		MAX-ACCESS read-only
		STATUS current
		DESCRIPTION
			"Total number of msg segments in queues"
	::= { smhInstanceEntry	63 }

smscSmhCachedAddrblocks OBJECT-TYPE
		SYNTAX	Unsigned32
		MAX-ACCESS read-only
		STATUS current
		DESCRIPTION
			"Address blocks with cached recipient information"
	::= { smhInstanceEntry	64 }

smscSmhMsgToRecQueued OBJECT-TYPE
		SYNTAX	Unsigned32
		MAX-ACCESS read-only
		STATUS current
		DESCRIPTION
			"Received SMS to recipients with messages queued"
	::= { smhInstanceEntry	65 }

smscSmhMsgToRecCached OBJECT-TYPE
		SYNTAX	Unsigned32
		MAX-ACCESS read-only
		STATUS current
		DESCRIPTION
			"Received SMS to cached recipients"
	::= { smhInstanceEntry	66 }

smscSmhFirstDelivAttempt OBJECT-TYPE
		SYNTAX	Unsigned32
		MAX-ACCESS read-only
		STATUS current
		DESCRIPTION
			"Counts the first delivery attempts"
	::= { smhInstanceEntry	67 }

smscSmhRetryAttempt OBJECT-TYPE
		SYNTAX	Unsigned32
		MAX-ACCESS read-only
		STATUS current
		DESCRIPTION
			"Counts the retry delivery attempts"
	::= { smhInstanceEntry	68 }

smscSmhDeliveryAttempt OBJECT-TYPE
		SYNTAX	Unsigned32
		MAX-ACCESS read-only
		STATUS current
		DESCRIPTION
			"Counts all delivery attempts"
	::= { smhInstanceEntry	69 }

smscSmhMaxFirstDelDelay OBJECT-TYPE
		SYNTAX	Unsigned32
		MAX-ACCESS read-only
		STATUS current
		DESCRIPTION
			"Maximum delay of first delivery  seconds"
	::= { smhInstanceEntry	70 }

smscSmhMaxRetryDelay OBJECT-TYPE
		SYNTAX	Unsigned32
		MAX-ACCESS read-only
		STATUS current
		DESCRIPTION
			"Maximum delay of retry delivery  seconds"
	::= { smhInstanceEntry	71 }

smscSmhRejectedFirstDel OBJECT-TYPE
		SYNTAX	Unsigned32
		MAX-ACCESS read-only
		STATUS current
		DESCRIPTION
			"Rejected first delivery messages"
	::= { smhInstanceEntry	72 }

smscSmhDiscardedFirstDel OBJECT-TYPE
		SYNTAX	Unsigned32
		MAX-ACCESS read-only
		STATUS current
		DESCRIPTION
			"Number of Trashbinned messages"
	::= { smhInstanceEntry	73 }

smscSmhQueuedForFirstDel OBJECT-TYPE
		SYNTAX	Unsigned32
		MAX-ACCESS read-only
		STATUS current
		DESCRIPTION
			"Number of messages queued for first delivery"
	::= { smhInstanceEntry	74 }

smscSmhQueuedForRetry OBJECT-TYPE
		SYNTAX	Unsigned32
		MAX-ACCESS read-only
		STATUS current
		DESCRIPTION
			"Number of messages queued for retry delivery"
	::= { smhInstanceEntry	75 }

smscSmhAbnDelivered OBJECT-TYPE
		SYNTAX	Unsigned32
		MAX-ACCESS read-only
		STATUS current
		DESCRIPTION
			"Number of delivered Account Balance Notifications"
	::= { smhInstanceEntry	76 }

smscSmhLogsrvInternLost OBJECT-TYPE
		SYNTAX	Unsigned32
		MAX-ACCESS read-only
		STATUS current
		DESCRIPTION
			"LOGSRV records dropped"
	::= { smhInstanceEntry	77 }

smscSmhEnumWaitAddrblocks OBJECT-TYPE
		SYNTAX	Unsigned32
		MAX-ACCESS read-only
		STATUS current
		DESCRIPTION
			"Address blocks waiting for ENUM response"
	::= { smhInstanceEntry	78 }

smscSmhEnumQueries OBJECT-TYPE
		SYNTAX	Unsigned32
		MAX-ACCESS read-only
		STATUS current
		DESCRIPTION
			"ENUM queries requested"
	::= { smhInstanceEntry	79 }

smscSmhEnumAfterMtPlmn OBJECT-TYPE
		SYNTAX	Unsigned32
		MAX-ACCESS read-only
		STATUS current
		DESCRIPTION
			"ENUM queries after MT indicating PLMN"
	::= { smhInstanceEntry	80 }

smscSmhEnumBeforeMtPlmn OBJECT-TYPE
		SYNTAX	Unsigned32
		MAX-ACCESS read-only
		STATUS current
		DESCRIPTION
			"ENUM queries before MT indicating PLMN"
	::= { smhInstanceEntry	81 }

smscSmhEnumAfterMtGw OBJECT-TYPE
		SYNTAX	Unsigned32
		MAX-ACCESS read-only
		STATUS current
		DESCRIPTION
			"ENUM queries after MT indicating Gateway"
	::= { smhInstanceEntry	82 }

smscSmhEnumBeforeMtGw OBJECT-TYPE
		SYNTAX	Unsigned32
		MAX-ACCESS read-only
		STATUS current
		DESCRIPTION
			"ENUM queries before MT indicating Gateway"
	::= { smhInstanceEntry	83 }

smscSmhEnumNoResult OBJECT-TYPE
		SYNTAX	Unsigned32
		MAX-ACCESS read-only
		STATUS current
		DESCRIPTION
			"ENUM queries without any routing result"
	::= { smhInstanceEntry	84 }



-- end of SMH description.
-- --------------------------------------


-- --------------------------------------
-- Class SIWMENU
-- 
smscSiwmenu OBJECT-TYPE
	SYNTAX  SEQUENCE OF SiwmenuInstanceEntry
	MAX-ACCESS  not-accessible
	STATUS  current
	DESCRIPTION
		"Mapping table for SMSC SIWMENU entities."
   ::= { smscClassSiw   1  }

siwmenuInstanceEntry  OBJECT-TYPE
	SYNTAX SiwmenuInstanceEntry
	MAX-ACCESS  not-accessible
	STATUS  current
	DESCRIPTION
		"An entry (row) in the entityInstanceTable."
	INDEX { IMPLIED smscSiwmenuName }
   ::= { smscSiwmenu 1 }

SiwmenuInstanceEntry ::= SEQUENCE {
		smscSiwmenuName     DisplayString,
		smscSiwmenuState   INTEGER,
		smscSiwmenuLastupdate   TimeTicks,
		smscSiwmenuNode	   DisplayString, 
		smscSiwmenuMsgReceived	 Unsigned32, 
		smscSiwmenuMsgRejected	 Unsigned32, 
		smscSiwmenuMsgTransmitted	 Unsigned32, 
		smscSiwmenuMsgFailed	 Unsigned32, 
		smscSiwmenuSmPstnReceived	 Unsigned32, 
		smscSiwmenuSmX25Received	 Unsigned32, 
		smscSiwmenuSmPstnInvalid	 Unsigned32, 
		smscSiwmenuSmX25Invalid	 Unsigned32, 
		smscSiwmenuLengthSmInPstn	 Unsigned32, 
		smscSiwmenuLengthSmInX25	 Unsigned32, 
		smscSiwmenuNotifPstnFailed	 Unsigned32, 
		smscSiwmenuNotifX25Failed	 Unsigned32, 
		smscSiwmenuSessRefPstn	 Unsigned32, 
		smscSiwmenuSessRefX25	 Unsigned32, 
		smscSiwmenuSmPstnFailed	 Unsigned32, 
		smscSiwmenuSmVpFailed	 Unsigned32, 
		smscSiwmenuNotifPstnTransmitted	 Unsigned32, 
		smscSiwmenuSmPstnTransmitted	 Unsigned32, 
		smscSiwmenuNotifX25Transmitted	 Unsigned32, 
		smscSiwmenuNotifbPstnRequested	 Unsigned32, 
		smscSiwmenuNotifbX25Requested	 Unsigned32, 
		smscSiwmenuNotifdPstnRequested	 Unsigned32, 
		smscSiwmenuNotifdX25Requested	 Unsigned32, 
		smscSiwmenuNotifndPstnRequested	 Unsigned32, 
		smscSiwmenuNotifndX25Requested	 Unsigned32, 
		smscSiwmenuQelemUsed	 Unsigned32, 
		smscSiwmenuQelemInProcqueue	 Unsigned32, 
		smscSiwmenuQelemInExpqueue	 Unsigned32, 
		smscSiwmenuNrTimersRunning	 Unsigned32, 
		smscSiwmenuNrSystemTimers	 Unsigned32, 
		smscSiwmenuImiRecallQelem	 Unsigned32, 
		smscSiwmenuImiRecallQueues	 Unsigned32, 
		smscSiwmenuIdiRecallQelem	 Unsigned32, 
		smscSiwmenuIdiRecallQueues	 Unsigned32, 
		smscSiwmenuIosRecallQelem	 Unsigned32, 
		smscSiwmenuIosRecallQueues	 Unsigned32, 
		smscSiwmenuLogRecallQelem	 Unsigned32, 
		smscSiwmenuLogRecallQueues	 Unsigned32, 
		smscSiwmenuTrcreqDiscarded	 Unsigned32
	}

smscSiwmenuName  OBJECT-TYPE
	SYNTAX  DisplayString
	MAX-ACCESS  read-only
	STATUS   current
	DESCRIPTION
		"Identifies the name of the entity."
   ::= {siwmenuInstanceEntry 1 }

smscSiwmenuState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { siwmenuInstanceEntry 2 }


smscSiwmenuLastupdate OBJECT-TYPE
		SYNTAX	TimeTicks
		MAX-ACCESS read-only
		STATUS current
		DESCRIPTION
			"Value which reflects the last time the entities fields have been updated"
	::= { siwmenuInstanceEntry	3 }

smscSiwmenuNode  OBJECT-TYPE
	SYNTAX  DisplayString
	MAX-ACCESS  read-only
	STATUS   current
	DESCRIPTION
		"Identifies the node the entity is running on."
   ::= {siwmenuInstanceEntry 4 }

smscSiwmenuMsgReceived OBJECT-TYPE
		SYNTAX	Unsigned32
		MAX-ACCESS read-only
		STATUS current
		DESCRIPTION
			"Received messages"
	::= { siwmenuInstanceEntry	5 }

smscSiwmenuMsgRejected OBJECT-TYPE
		SYNTAX	Unsigned32
		MAX-ACCESS read-only
		STATUS current
		DESCRIPTION
			"Received messages and rejected"
	::= { siwmenuInstanceEntry	6 }

smscSiwmenuMsgTransmitted OBJECT-TYPE
		SYNTAX	Unsigned32
		MAX-ACCESS read-only
		STATUS current
		DESCRIPTION
			"Transmitted messages"
	::= { siwmenuInstanceEntry	7 }

smscSiwmenuMsgFailed OBJECT-TYPE
		SYNTAX	Unsigned32
		MAX-ACCESS read-only
		STATUS current
		DESCRIPTION
			"Messages that failed on sending"
	::= { siwmenuInstanceEntry	8 }

smscSiwmenuSmPstnReceived OBJECT-TYPE
		SYNTAX	Unsigned32
		MAX-ACCESS read-only
		STATUS current
		DESCRIPTION
			"Short messages received from PSTN"
	::= { siwmenuInstanceEntry	9 }

smscSiwmenuSmX25Received OBJECT-TYPE
		SYNTAX	Unsigned32
		MAX-ACCESS read-only
		STATUS current
		DESCRIPTION
			"Short messages received from X25"
	::= { siwmenuInstanceEntry	10 }

smscSiwmenuSmPstnInvalid OBJECT-TYPE
		SYNTAX	Unsigned32
		MAX-ACCESS read-only
		STATUS current
		DESCRIPTION
			"Received invalid short messages from PSTN"
	::= { siwmenuInstanceEntry	11 }

smscSiwmenuSmX25Invalid OBJECT-TYPE
		SYNTAX	Unsigned32
		MAX-ACCESS read-only
		STATUS current
		DESCRIPTION
			"Received invalid short messages from X25"
	::= { siwmenuInstanceEntry	12 }

smscSiwmenuLengthSmInPstn OBJECT-TYPE
		SYNTAX	Unsigned32
		MAX-ACCESS read-only
		STATUS current
		DESCRIPTION
			"Accumulated length of short messages from PSTN"
	::= { siwmenuInstanceEntry	13 }

smscSiwmenuLengthSmInX25 OBJECT-TYPE
		SYNTAX	Unsigned32
		MAX-ACCESS read-only
		STATUS current
		DESCRIPTION
			"Accumulated length of short messages from X25"
	::= { siwmenuInstanceEntry	14 }

smscSiwmenuNotifPstnFailed OBJECT-TYPE
		SYNTAX	Unsigned32
		MAX-ACCESS read-only
		STATUS current
		DESCRIPTION
			"Submitted notifications for PSTN that failed"
	::= { siwmenuInstanceEntry	15 }

smscSiwmenuNotifX25Failed OBJECT-TYPE
		SYNTAX	Unsigned32
		MAX-ACCESS read-only
		STATUS current
		DESCRIPTION
			"Submitted notifications for X25 that failed"
	::= { siwmenuInstanceEntry	16 }

smscSiwmenuSessRefPstn OBJECT-TYPE
		SYNTAX	Unsigned32
		MAX-ACCESS read-only
		STATUS current
		DESCRIPTION
			"Refused sessions via PSTN"
	::= { siwmenuInstanceEntry	17 }

smscSiwmenuSessRefX25 OBJECT-TYPE
		SYNTAX	Unsigned32
		MAX-ACCESS read-only
		STATUS current
		DESCRIPTION
			"Refused sessions via X25"
	::= { siwmenuInstanceEntry	18 }

smscSiwmenuSmPstnFailed OBJECT-TYPE
		SYNTAX	Unsigned32
		MAX-ACCESS read-only
		STATUS current
		DESCRIPTION
			"Short messages submitted to PSTN that failed"
	::= { siwmenuInstanceEntry	19 }

smscSiwmenuSmVpFailed OBJECT-TYPE
		SYNTAX	Unsigned32
		MAX-ACCESS read-only
		STATUS current
		DESCRIPTION
			"Failed short messages submitted and validity period exceeded"
	::= { siwmenuInstanceEntry	20 }

smscSiwmenuNotifPstnTransmitted OBJECT-TYPE
		SYNTAX	Unsigned32
		MAX-ACCESS read-only
		STATUS current
		DESCRIPTION
			"Transmitted notifications to PSTN"
	::= { siwmenuInstanceEntry	21 }

smscSiwmenuSmPstnTransmitted OBJECT-TYPE
		SYNTAX	Unsigned32
		MAX-ACCESS read-only
		STATUS current
		DESCRIPTION
			"Transmitted short messages to PSTN"
	::= { siwmenuInstanceEntry	22 }

smscSiwmenuNotifX25Transmitted OBJECT-TYPE
		SYNTAX	Unsigned32
		MAX-ACCESS read-only
		STATUS current
		DESCRIPTION
			"Transmitted notifications to X25"
	::= { siwmenuInstanceEntry	23 }

smscSiwmenuNotifbPstnRequested OBJECT-TYPE
		SYNTAX	Unsigned32
		MAX-ACCESS read-only
		STATUS current
		DESCRIPTION
			"Requested buffered message notif. via PSTN"
	::= { siwmenuInstanceEntry	24 }

smscSiwmenuNotifbX25Requested OBJECT-TYPE
		SYNTAX	Unsigned32
		MAX-ACCESS read-only
		STATUS current
		DESCRIPTION
			"Requested buffered message notif. via X25"
	::= { siwmenuInstanceEntry	25 }

smscSiwmenuNotifdPstnRequested OBJECT-TYPE
		SYNTAX	Unsigned32
		MAX-ACCESS read-only
		STATUS current
		DESCRIPTION
			"Requested buffered message notif. via PSTN"
	::= { siwmenuInstanceEntry	26 }

smscSiwmenuNotifdX25Requested OBJECT-TYPE
		SYNTAX	Unsigned32
		MAX-ACCESS read-only
		STATUS current
		DESCRIPTION
			"Requested delivery notifications via X25"
	::= { siwmenuInstanceEntry	27 }

smscSiwmenuNotifndPstnRequested OBJECT-TYPE
		SYNTAX	Unsigned32
		MAX-ACCESS read-only
		STATUS current
		DESCRIPTION
			"Requested delivery notifications via PSTN"
	::= { siwmenuInstanceEntry	28 }

smscSiwmenuNotifndX25Requested OBJECT-TYPE
		SYNTAX	Unsigned32
		MAX-ACCESS read-only
		STATUS current
		DESCRIPTION
			"Requested non-delivery notifications via X25"
	::= { siwmenuInstanceEntry	29 }

smscSiwmenuQelemUsed OBJECT-TYPE
		SYNTAX	Unsigned32
		MAX-ACCESS read-only
		STATUS current
		DESCRIPTION
			"Number of elements in internal queues"
	::= { siwmenuInstanceEntry	30 }

smscSiwmenuQelemInProcqueue OBJECT-TYPE
		SYNTAX	Unsigned32
		MAX-ACCESS read-only
		STATUS current
		DESCRIPTION
			"Number of elements used in process queue"
	::= { siwmenuInstanceEntry	31 }

smscSiwmenuQelemInExpqueue OBJECT-TYPE
		SYNTAX	Unsigned32
		MAX-ACCESS read-only
		STATUS current
		DESCRIPTION
			"Number of elements used in expedited queue"
	::= { siwmenuInstanceEntry	32 }

smscSiwmenuNrTimersRunning OBJECT-TYPE
		SYNTAX	Unsigned32
		MAX-ACCESS read-only
		STATUS current
		DESCRIPTION
			"Total number of timers running"
	::= { siwmenuInstanceEntry	33 }

smscSiwmenuNrSystemTimers OBJECT-TYPE
		SYNTAX	Unsigned32
		MAX-ACCESS read-only
		STATUS current
		DESCRIPTION
			"Number of system timers running"
	::= { siwmenuInstanceEntry	34 }

smscSiwmenuImiRecallQelem OBJECT-TYPE
		SYNTAX	Unsigned32
		MAX-ACCESS read-only
		STATUS current
		DESCRIPTION
			"Number of IMI recall-queue elements used"
	::= { siwmenuInstanceEntry	35 }

smscSiwmenuImiRecallQueues OBJECT-TYPE
		SYNTAX	Unsigned32
		MAX-ACCESS read-only
		STATUS current
		DESCRIPTION
			"Number of IMI-recall-queues used"
	::= { siwmenuInstanceEntry	36 }

smscSiwmenuIdiRecallQelem OBJECT-TYPE
		SYNTAX	Unsigned32
		MAX-ACCESS read-only
		STATUS current
		DESCRIPTION
			"Number of IDI recall-queue elements used"
	::= { siwmenuInstanceEntry	37 }

smscSiwmenuIdiRecallQueues OBJECT-TYPE
		SYNTAX	Unsigned32
		MAX-ACCESS read-only
		STATUS current
		DESCRIPTION
			"Number of IDI recall-queues used"
	::= { siwmenuInstanceEntry	38 }

smscSiwmenuIosRecallQelem OBJECT-TYPE
		SYNTAX	Unsigned32
		MAX-ACCESS read-only
		STATUS current
		DESCRIPTION
			"Number of IOS recall-queue elements used"
	::= { siwmenuInstanceEntry	39 }

smscSiwmenuIosRecallQueues OBJECT-TYPE
		SYNTAX	Unsigned32
		MAX-ACCESS read-only
		STATUS current
		DESCRIPTION
			"Number of IOS recall-queues used"
	::= { siwmenuInstanceEntry	40 }

smscSiwmenuLogRecallQelem OBJECT-TYPE
		SYNTAX	Unsigned32
		MAX-ACCESS read-only
		STATUS current
		DESCRIPTION
			"Number of LOG recall-queue elements used"
	::= { siwmenuInstanceEntry	41 }

smscSiwmenuLogRecallQueues OBJECT-TYPE
		SYNTAX	Unsigned32
		MAX-ACCESS read-only
		STATUS current
		DESCRIPTION
			"Number of LOG recall-queues used"
	::= { siwmenuInstanceEntry	42 }

smscSiwmenuTrcreqDiscarded OBJECT-TYPE
		SYNTAX	Unsigned32
		MAX-ACCESS read-only
		STATUS current
		DESCRIPTION
			"Number of trace requests discarded"
	::= { siwmenuInstanceEntry	43 }



-- end of SIWMENU description.
-- --------------------------------------


-- --------------------------------------
-- Class SIWPC
-- 
smscSiwpc OBJECT-TYPE
	SYNTAX  SEQUENCE OF SiwpcInstanceEntry
	MAX-ACCESS  not-accessible
	STATUS  current
	DESCRIPTION
		"Mapping table for SMSC SIWPC entities."
   ::= { smscClassSiw   2  }

siwpcInstanceEntry  OBJECT-TYPE
	SYNTAX SiwpcInstanceEntry
	MAX-ACCESS  not-accessible
	STATUS  current
	DESCRIPTION
		"An entry (row) in the entityInstanceTable."
	INDEX { IMPLIED smscSiwpcName }
   ::= { smscSiwpc 1 }

SiwpcInstanceEntry ::= SEQUENCE {
		smscSiwpcName     DisplayString,
		smscSiwpcState   INTEGER,
		smscSiwpcLastupdate   TimeTicks,
		smscSiwpcNode	   DisplayString, 
		smscSiwpcMsgReceived	 Unsigned32, 
		smscSiwpcMsgRejected	 Unsigned32, 
		smscSiwpcMsgTransmitted	 Unsigned32, 
		smscSiwpcMsgFailed	 Unsigned32, 
		smscSiwpcSmPstnReceived	 Unsigned32, 
		smscSiwpcSmX25Received	 Unsigned32, 
		smscSiwpcSmPstnInvalid	 Unsigned32, 
		smscSiwpcSmX25Invalid	 Unsigned32, 
		smscSiwpcLengthSmInPstn	 Unsigned32, 
		smscSiwpcLengthSmInX25	 Unsigned32, 
		smscSiwpcNotifPstnFailed	 Unsigned32, 
		smscSiwpcNotifX25Failed	 Unsigned32, 
		smscSiwpcSessRefPstn	 Unsigned32, 
		smscSiwpcSessRefX25	 Unsigned32, 
		smscSiwpcSmPstnFailed	 Unsigned32, 
		smscSiwpcSmVpFailed	 Unsigned32, 
		smscSiwpcNotifPstnTransmitted	 Unsigned32, 
		smscSiwpcSmPstnTransmitted	 Unsigned32, 
		smscSiwpcLengthSmOutPstn	 Unsigned32, 
		smscSiwpcSmX25Failed	 Unsigned32, 
		smscSiwpcNotifX25Transmitted	 Unsigned32, 
		smscSiwpcSmX25Transmitted	 Unsigned32, 
		smscSiwpcLengthSmOutX25	 Unsigned32, 
		smscSiwpcNotifbPstnRequested	 Unsigned32, 
		smscSiwpcNotifbX25Requested	 Unsigned32, 
		smscSiwpcNotifdPstnRequested	 Unsigned32, 
		smscSiwpcNotifdX25Requested	 Unsigned32, 
		smscSiwpcNotifndPstnRequested	 Unsigned32, 
		smscSiwpcNotifndX25Requested	 Unsigned32, 
		smscSiwpcQelemUsed	 Unsigned32, 
		smscSiwpcQelemInProcqueue	 Unsigned32, 
		smscSiwpcQelemInExpqueue	 Unsigned32, 
		smscSiwpcNrTimersRunning	 Unsigned32, 
		smscSiwpcNrSystemTimers	 Unsigned32, 
		smscSiwpcImiRecallQelem	 Unsigned32, 
		smscSiwpcImiRecallQueues	 Unsigned32, 
		smscSiwpcIdiRecallQelem	 Unsigned32, 
		smscSiwpcIdiRecallQueues	 Unsigned32, 
		smscSiwpcIosRecallQelem	 Unsigned32, 
		smscSiwpcIosRecallQueues	 Unsigned32, 
		smscSiwpcLogRecallQelem	 Unsigned32, 
		smscSiwpcLogRecallQueues	 Unsigned32, 
		smscSiwpcTrcreqDiscarded	 Unsigned32, 
		smscSiwpcTimesTooFewInputBuf	 Unsigned32, 
		smscSiwpcTimesTooFewOutputBuf	 Unsigned32, 
		smscSiwpcMaxInputBuffersUsed	 Unsigned32, 
		smscSiwpcMaxOutputBuffersUsed	 Unsigned32, 
		smscSiwpcAdtUsedMemory	 Unsigned32, 
		smscSiwpcConSetupTotAtt	 Unsigned32, 
		smscSiwpcConSetupTotRej	 Unsigned32, 
		smscSiwpcConSetupRejRes	 Unsigned32, 
		smscSiwpcSesSetupTotAtt	 Unsigned32, 
		smscSiwpcSesSetupTotRej	 Unsigned32, 
		smscSiwpcSesSetupRejRes	 Unsigned32, 
		smscSiwpcSesSetupRejPswd	 Unsigned32, 
		smscSiwpcSesSetupRejNreg	 Unsigned32, 
		smscSiwpcSesSetupRejCnadr	 Unsigned32, 
		smscSiwpcSesSetupRejMaxses	 Unsigned32
	}

smscSiwpcName  OBJECT-TYPE
	SYNTAX  DisplayString
	MAX-ACCESS  read-only
	STATUS   current
	DESCRIPTION
		"Identifies the name of the entity."
   ::= {siwpcInstanceEntry 1 }

smscSiwpcState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { siwpcInstanceEntry 2 }


smscSiwpcLastupdate OBJECT-TYPE
		SYNTAX	TimeTicks
		MAX-ACCESS read-only
		STATUS current
		DESCRIPTION
			"Value which reflects the last time the entities fields have been updated"
	::= { siwpcInstanceEntry	3 }

smscSiwpcNode  OBJECT-TYPE
	SYNTAX  DisplayString
	MAX-ACCESS  read-only
	STATUS   current
	DESCRIPTION
		"Identifies the node the entity is running on."
   ::= {siwpcInstanceEntry 4 }

smscSiwpcMsgReceived OBJECT-TYPE
		SYNTAX	Unsigned32
		MAX-ACCESS read-only
		STATUS current
		DESCRIPTION
			"Received messages"
	::= { siwpcInstanceEntry	5 }

smscSiwpcMsgRejected OBJECT-TYPE
		SYNTAX	Unsigned32
		MAX-ACCESS read-only
		STATUS current
		DESCRIPTION
			"Received messages and rejected"
	::= { siwpcInstanceEntry	6 }

smscSiwpcMsgTransmitted OBJECT-TYPE
		SYNTAX	Unsigned32
		MAX-ACCESS read-only
		STATUS current
		DESCRIPTION
			"Transmitted messages"
	::= { siwpcInstanceEntry	7 }

smscSiwpcMsgFailed OBJECT-TYPE
		SYNTAX	Unsigned32
		MAX-ACCESS read-only
		STATUS current
		DESCRIPTION
			"Messages that failed on sending"
	::= { siwpcInstanceEntry	8 }

smscSiwpcSmPstnReceived OBJECT-TYPE
		SYNTAX	Unsigned32
		MAX-ACCESS read-only
		STATUS current
		DESCRIPTION
			"Short messages received from PSTN"
	::= { siwpcInstanceEntry	9 }

smscSiwpcSmX25Received OBJECT-TYPE
		SYNTAX	Unsigned32
		MAX-ACCESS read-only
		STATUS current
		DESCRIPTION
			"Short messages received from X25"
	::= { siwpcInstanceEntry	10 }

smscSiwpcSmPstnInvalid OBJECT-TYPE
		SYNTAX	Unsigned32
		MAX-ACCESS read-only
		STATUS current
		DESCRIPTION
			"Received invalid short messages from PSTN"
	::= { siwpcInstanceEntry	11 }

smscSiwpcSmX25Invalid OBJECT-TYPE
		SYNTAX	Unsigned32
		MAX-ACCESS read-only
		STATUS current
		DESCRIPTION
			"Received invalid short messages from X25"
	::= { siwpcInstanceEntry	12 }

smscSiwpcLengthSmInPstn OBJECT-TYPE
		SYNTAX	Unsigned32
		MAX-ACCESS read-only
		STATUS current
		DESCRIPTION
			"Accumulated length of short messages from PSTN"
	::= { siwpcInstanceEntry	13 }

smscSiwpcLengthSmInX25 OBJECT-TYPE
		SYNTAX	Unsigned32
		MAX-ACCESS read-only
		STATUS current
		DESCRIPTION
			"Accumulated length of short messages from X25"
	::= { siwpcInstanceEntry	14 }

smscSiwpcNotifPstnFailed OBJECT-TYPE
		SYNTAX	Unsigned32
		MAX-ACCESS read-only
		STATUS current
		DESCRIPTION
			"Submitted notifications for PSTN that failed"
	::= { siwpcInstanceEntry	15 }

smscSiwpcNotifX25Failed OBJECT-TYPE
		SYNTAX	Unsigned32
		MAX-ACCESS read-only
		STATUS current
		DESCRIPTION
			"Submitted notifications for X25 that failed"
	::= { siwpcInstanceEntry	16 }

smscSiwpcSessRefPstn OBJECT-TYPE
		SYNTAX	Unsigned32
		MAX-ACCESS read-only
		STATUS current
		DESCRIPTION
			"Refused sessions via PSTN"
	::= { siwpcInstanceEntry	17 }

smscSiwpcSessRefX25 OBJECT-TYPE
		SYNTAX	Unsigned32
		MAX-ACCESS read-only
		STATUS current
		DESCRIPTION
			"Refused sessions via X25"
	::= { siwpcInstanceEntry	18 }

smscSiwpcSmPstnFailed OBJECT-TYPE
		SYNTAX	Unsigned32
		MAX-ACCESS read-only
		STATUS current
		DESCRIPTION
			"Short messages submitted to PSTN that failed"
	::= { siwpcInstanceEntry	19 }

smscSiwpcSmVpFailed OBJECT-TYPE
		SYNTAX	Unsigned32
		MAX-ACCESS read-only
		STATUS current
		DESCRIPTION
			"Failed short messages submitted and validity period exceeded"
	::= { siwpcInstanceEntry	20 }

smscSiwpcNotifPstnTransmitted OBJECT-TYPE
		SYNTAX	Unsigned32
		MAX-ACCESS read-only
		STATUS current
		DESCRIPTION
			"Transmitted notifications to PSTN"
	::= { siwpcInstanceEntry	21 }

smscSiwpcSmPstnTransmitted OBJECT-TYPE
		SYNTAX	Unsigned32
		MAX-ACCESS read-only
		STATUS current
		DESCRIPTION
			"Transmitted short messages to PSTN"
	::= { siwpcInstanceEntry	22 }

smscSiwpcLengthSmOutPstn OBJECT-TYPE
		SYNTAX	Unsigned32
		MAX-ACCESS read-only
		STATUS current
		DESCRIPTION
			"Accumulated length of short messages to PSTN"
	::= { siwpcInstanceEntry	23 }

smscSiwpcSmX25Failed OBJECT-TYPE
		SYNTAX	Unsigned32
		MAX-ACCESS read-only
		STATUS current
		DESCRIPTION
			"Short messages submitted to X25 that failed"
	::= { siwpcInstanceEntry	24 }

smscSiwpcNotifX25Transmitted OBJECT-TYPE
		SYNTAX	Unsigned32
		MAX-ACCESS read-only
		STATUS current
		DESCRIPTION
			"Transmitted notifications to X25"
	::= { siwpcInstanceEntry	25 }

smscSiwpcSmX25Transmitted OBJECT-TYPE
		SYNTAX	Unsigned32
		MAX-ACCESS read-only
		STATUS current
		DESCRIPTION
			"Transmitted short messages to X25"
	::= { siwpcInstanceEntry	26 }

smscSiwpcLengthSmOutX25 OBJECT-TYPE
		SYNTAX	Unsigned32
		MAX-ACCESS read-only
		STATUS current
		DESCRIPTION
			"Accumulated length of short messages to X25"
	::= { siwpcInstanceEntry	27 }

smscSiwpcNotifbPstnRequested OBJECT-TYPE
		SYNTAX	Unsigned32
		MAX-ACCESS read-only
		STATUS current
		DESCRIPTION
			"Requested buffered message notif. via PSTN"
	::= { siwpcInstanceEntry	28 }

smscSiwpcNotifbX25Requested OBJECT-TYPE
		SYNTAX	Unsigned32
		MAX-ACCESS read-only
		STATUS current
		DESCRIPTION
			"Requested buffered message notif. via X25"
	::= { siwpcInstanceEntry	29 }

smscSiwpcNotifdPstnRequested OBJECT-TYPE
		SYNTAX	Unsigned32
		MAX-ACCESS read-only
		STATUS current
		DESCRIPTION
			"Requested buffered message notif. via PSTN"
	::= { siwpcInstanceEntry	30 }

smscSiwpcNotifdX25Requested OBJECT-TYPE
		SYNTAX	Unsigned32
		MAX-ACCESS read-only
		STATUS current
		DESCRIPTION
			"Requested delivery notifications via X25"
	::= { siwpcInstanceEntry	31 }

smscSiwpcNotifndPstnRequested OBJECT-TYPE
		SYNTAX	Unsigned32
		MAX-ACCESS read-only
		STATUS current
		DESCRIPTION
			"Requested delivery notifications via PSTN"
	::= { siwpcInstanceEntry	32 }

smscSiwpcNotifndX25Requested OBJECT-TYPE
		SYNTAX	Unsigned32
		MAX-ACCESS read-only
		STATUS current
		DESCRIPTION
			"Requested non-delivery notifications via X25"
	::= { siwpcInstanceEntry	33 }

smscSiwpcQelemUsed OBJECT-TYPE
		SYNTAX	Unsigned32
		MAX-ACCESS read-only
		STATUS current
		DESCRIPTION
			"Number of elements in internal queues"
	::= { siwpcInstanceEntry	34 }

smscSiwpcQelemInProcqueue OBJECT-TYPE
		SYNTAX	Unsigned32
		MAX-ACCESS read-only
		STATUS current
		DESCRIPTION
			"Number of elements used in process queue"
	::= { siwpcInstanceEntry	35 }

smscSiwpcQelemInExpqueue OBJECT-TYPE
		SYNTAX	Unsigned32
		MAX-ACCESS read-only
		STATUS current
		DESCRIPTION
			"Number of elements used in expedited queue"
	::= { siwpcInstanceEntry	36 }

smscSiwpcNrTimersRunning OBJECT-TYPE
		SYNTAX	Unsigned32
		MAX-ACCESS read-only
		STATUS current
		DESCRIPTION
			"Total number of timers running"
	::= { siwpcInstanceEntry	37 }

smscSiwpcNrSystemTimers OBJECT-TYPE
		SYNTAX	Unsigned32
		MAX-ACCESS read-only
		STATUS current
		DESCRIPTION
			"Number of system timers running"
	::= { siwpcInstanceEntry	38 }

smscSiwpcImiRecallQelem OBJECT-TYPE
		SYNTAX	Unsigned32
		MAX-ACCESS read-only
		STATUS current
		DESCRIPTION
			"Number of IMI recall-queue elements used"
	::= { siwpcInstanceEntry	39 }

smscSiwpcImiRecallQueues OBJECT-TYPE
		SYNTAX	Unsigned32
		MAX-ACCESS read-only
		STATUS current
		DESCRIPTION
			"Number of IMI-recall-queues used"
	::= { siwpcInstanceEntry	40 }

smscSiwpcIdiRecallQelem OBJECT-TYPE
		SYNTAX	Unsigned32
		MAX-ACCESS read-only
		STATUS current
		DESCRIPTION
			"Number of IDI recall-queue elements used"
	::= { siwpcInstanceEntry	41 }

smscSiwpcIdiRecallQueues OBJECT-TYPE
		SYNTAX	Unsigned32
		MAX-ACCESS read-only
		STATUS current
		DESCRIPTION
			"Number of IDI recall-queues used"
	::= { siwpcInstanceEntry	42 }

smscSiwpcIosRecallQelem OBJECT-TYPE
		SYNTAX	Unsigned32
		MAX-ACCESS read-only
		STATUS current
		DESCRIPTION
			"Number of IOS recall-queue elements used"
	::= { siwpcInstanceEntry	43 }

smscSiwpcIosRecallQueues OBJECT-TYPE
		SYNTAX	Unsigned32
		MAX-ACCESS read-only
		STATUS current
		DESCRIPTION
			"Number of IOS recall-queues used"
	::= { siwpcInstanceEntry	44 }

smscSiwpcLogRecallQelem OBJECT-TYPE
		SYNTAX	Unsigned32
		MAX-ACCESS read-only
		STATUS current
		DESCRIPTION
			"Number of LOG recall-queue elements used"
	::= { siwpcInstanceEntry	45 }

smscSiwpcLogRecallQueues OBJECT-TYPE
		SYNTAX	Unsigned32
		MAX-ACCESS read-only
		STATUS current
		DESCRIPTION
			"Number of LOG recall-queues used"
	::= { siwpcInstanceEntry	46 }

smscSiwpcTrcreqDiscarded OBJECT-TYPE
		SYNTAX	Unsigned32
		MAX-ACCESS read-only
		STATUS current
		DESCRIPTION
			"Number of trace requests discarded"
	::= { siwpcInstanceEntry	47 }

smscSiwpcTimesTooFewInputBuf OBJECT-TYPE
		SYNTAX	Unsigned32
		MAX-ACCESS read-only
		STATUS current
		DESCRIPTION
			"Number of times there were too few input buffers"
	::= { siwpcInstanceEntry	48 }

smscSiwpcTimesTooFewOutputBuf OBJECT-TYPE
		SYNTAX	Unsigned32
		MAX-ACCESS read-only
		STATUS current
		DESCRIPTION
			"Numberof times there were too few output buffers"
	::= { siwpcInstanceEntry	49 }

smscSiwpcMaxInputBuffersUsed OBJECT-TYPE
		SYNTAX	Unsigned32
		MAX-ACCESS read-only
		STATUS current
		DESCRIPTION
			"Maximum input buffers during the active period"
	::= { siwpcInstanceEntry	50 }

smscSiwpcMaxOutputBuffersUsed OBJECT-TYPE
		SYNTAX	Unsigned32
		MAX-ACCESS read-only
		STATUS current
		DESCRIPTION
			"Maximum output buffers during the active period"
	::= { siwpcInstanceEntry	51 }

smscSiwpcAdtUsedMemory OBJECT-TYPE
		SYNTAX	Unsigned32
		MAX-ACCESS read-only
		STATUS current
		DESCRIPTION
			"Memory blocks used by ADT tables of SIWPC."
	::= { siwpcInstanceEntry	52 }

smscSiwpcConSetupTotAtt OBJECT-TYPE
		SYNTAX	Unsigned32
		MAX-ACCESS read-only
		STATUS current
		DESCRIPTION
			"Total number of connection setup attempts"
	::= { siwpcInstanceEntry	53 }

smscSiwpcConSetupTotRej OBJECT-TYPE
		SYNTAX	Unsigned32
		MAX-ACCESS read-only
		STATUS current
		DESCRIPTION
			"Total number of rejected connections"
	::= { siwpcInstanceEntry	54 }

smscSiwpcConSetupRejRes OBJECT-TYPE
		SYNTAX	Unsigned32
		MAX-ACCESS read-only
		STATUS current
		DESCRIPTION
			"Number of rejected connections - resource problem"
	::= { siwpcInstanceEntry	55 }

smscSiwpcSesSetupTotAtt OBJECT-TYPE
		SYNTAX	Unsigned32
		MAX-ACCESS read-only
		STATUS current
		DESCRIPTION
			"Total number of session setup attempts"
	::= { siwpcInstanceEntry	56 }

smscSiwpcSesSetupTotRej OBJECT-TYPE
		SYNTAX	Unsigned32
		MAX-ACCESS read-only
		STATUS current
		DESCRIPTION
			"Total number of rejected session setups"
	::= { siwpcInstanceEntry	57 }

smscSiwpcSesSetupRejRes OBJECT-TYPE
		SYNTAX	Unsigned32
		MAX-ACCESS read-only
		STATUS current
		DESCRIPTION
			"Number of rejected sessions - resource problem"
	::= { siwpcInstanceEntry	58 }

smscSiwpcSesSetupRejPswd OBJECT-TYPE
		SYNTAX	Unsigned32
		MAX-ACCESS read-only
		STATUS current
		DESCRIPTION
			"Number of rejected sessions - invalid password"
	::= { siwpcInstanceEntry	59 }

smscSiwpcSesSetupRejNreg OBJECT-TYPE
		SYNTAX	Unsigned32
		MAX-ACCESS read-only
		STATUS current
		DESCRIPTION
			"Number of rejected sessions - LA not registered"
	::= { siwpcInstanceEntry	60 }

smscSiwpcSesSetupRejCnadr OBJECT-TYPE
		SYNTAX	Unsigned32
		MAX-ACCESS read-only
		STATUS current
		DESCRIPTION
			"Number of rejected sessions - wrong connect addr"
	::= { siwpcInstanceEntry	61 }

smscSiwpcSesSetupRejMaxses OBJECT-TYPE
		SYNTAX	Unsigned32
		MAX-ACCESS read-only
		STATUS current
		DESCRIPTION
			"Number of rejected sessions - maxsession limit"
	::= { siwpcInstanceEntry	62 }



-- end of SIWPC description.
-- --------------------------------------


-- --------------------------------------
-- Class SIWPLMN
-- 
smscSiwplmn OBJECT-TYPE
	SYNTAX  SEQUENCE OF SiwplmnInstanceEntry
	MAX-ACCESS  not-accessible
	STATUS  current
	DESCRIPTION
		"Mapping table for SMSC SIWPLMN entities."
   ::= { smscClassSiw   3  }

siwplmnInstanceEntry  OBJECT-TYPE
	SYNTAX SiwplmnInstanceEntry
	MAX-ACCESS  not-accessible
	STATUS  current
	DESCRIPTION
		"An entry (row) in the entityInstanceTable."
	INDEX { IMPLIED smscSiwplmnName }
   ::= { smscSiwplmn 1 }

SiwplmnInstanceEntry ::= SEQUENCE {
		smscSiwplmnName     DisplayString,
		smscSiwplmnState   INTEGER,
		smscSiwplmnLastupdate   TimeTicks,
		smscSiwplmnNode	   DisplayString, 
		smscSiwplmnSmInvalid	 Unsigned32, 
		smscSiwplmnMsgReceived	 Unsigned32, 
		smscSiwplmnMsgRejected	 Unsigned32, 
		smscSiwplmnMsgTransmitted	 Unsigned32, 
		smscSiwplmnSmReceived	 Unsigned32, 
		smscSiwplmnMsgFailed	 Unsigned32, 
		smscSiwplmnNotifbRequested	 Unsigned32, 
		smscSiwplmnNotifdRequested	 Unsigned32, 
		smscSiwplmnNotifndRequested	 Unsigned32, 
		smscSiwplmnLengthSmInPlmn	 Unsigned32, 
		smscSiwplmnQelemUsed	 Unsigned32, 
		smscSiwplmnQelemInProcqueue	 Unsigned32, 
		smscSiwplmnQelemInExpqueue	 Unsigned32, 
		smscSiwplmnNrTimersRunning	 Unsigned32, 
		smscSiwplmnNrSystemTimers	 Unsigned32, 
		smscSiwplmnImiRecallQelem	 Unsigned32, 
		smscSiwplmnImiRecallQueues	 Unsigned32, 
		smscSiwplmnIdiRecallQelem	 Unsigned32, 
		smscSiwplmnIdiRecallQueues	 Unsigned32, 
		smscSiwplmnIosRecallQelem	 Unsigned32, 
		smscSiwplmnIosRecallQueues	 Unsigned32, 
		smscSiwplmnLogRecallQelem	 Unsigned32, 
		smscSiwplmnLogRecallQueues	 Unsigned32, 
		smscSiwplmnTrcreqDiscarded	 Unsigned32, 
		smscSiwplmnSessionsPending	 Unsigned32, 
		smscSiwplmnAdtUsedMemory	 Unsigned32, 
		smscSiwplmnSmResourceFail	 Unsigned32
	}

smscSiwplmnName  OBJECT-TYPE
	SYNTAX  DisplayString
	MAX-ACCESS  read-only
	STATUS   current
	DESCRIPTION
		"Identifies the name of the entity."
   ::= {siwplmnInstanceEntry 1 }

smscSiwplmnState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { siwplmnInstanceEntry 2 }


smscSiwplmnLastupdate OBJECT-TYPE
		SYNTAX	TimeTicks
		MAX-ACCESS read-only
		STATUS current
		DESCRIPTION
			"Value which reflects the last time the entities fields have been updated"
	::= { siwplmnInstanceEntry	3 }

smscSiwplmnNode  OBJECT-TYPE
	SYNTAX  DisplayString
	MAX-ACCESS  read-only
	STATUS   current
	DESCRIPTION
		"Identifies the node the entity is running on."
   ::= {siwplmnInstanceEntry 4 }

smscSiwplmnSmInvalid OBJECT-TYPE
		SYNTAX	Unsigned32
		MAX-ACCESS read-only
		STATUS current
		DESCRIPTION
			"Received invalid short messages"
	::= { siwplmnInstanceEntry	5 }

smscSiwplmnMsgReceived OBJECT-TYPE
		SYNTAX	Unsigned32
		MAX-ACCESS read-only
		STATUS current
		DESCRIPTION
			"Received messages"
	::= { siwplmnInstanceEntry	6 }

smscSiwplmnMsgRejected OBJECT-TYPE
		SYNTAX	Unsigned32
		MAX-ACCESS read-only
		STATUS current
		DESCRIPTION
			"Received messages and rejected"
	::= { siwplmnInstanceEntry	7 }

smscSiwplmnMsgTransmitted OBJECT-TYPE
		SYNTAX	Unsigned32
		MAX-ACCESS read-only
		STATUS current
		DESCRIPTION
			"Transmitted messages"
	::= { siwplmnInstanceEntry	8 }

smscSiwplmnSmReceived OBJECT-TYPE
		SYNTAX	Unsigned32
		MAX-ACCESS read-only
		STATUS current
		DESCRIPTION
			"Received short messages"
	::= { siwplmnInstanceEntry	9 }

smscSiwplmnMsgFailed OBJECT-TYPE
		SYNTAX	Unsigned32
		MAX-ACCESS read-only
		STATUS current
		DESCRIPTION
			"Messages that failed on sending"
	::= { siwplmnInstanceEntry	10 }

smscSiwplmnNotifbRequested OBJECT-TYPE
		SYNTAX	Unsigned32
		MAX-ACCESS read-only
		STATUS current
		DESCRIPTION
			"Requested buffered message notifications"
	::= { siwplmnInstanceEntry	11 }

smscSiwplmnNotifdRequested OBJECT-TYPE
		SYNTAX	Unsigned32
		MAX-ACCESS read-only
		STATUS current
		DESCRIPTION
			"Requested delivery notifications"
	::= { siwplmnInstanceEntry	12 }

smscSiwplmnNotifndRequested OBJECT-TYPE
		SYNTAX	Unsigned32
		MAX-ACCESS read-only
		STATUS current
		DESCRIPTION
			"Requested non-delivery notifications"
	::= { siwplmnInstanceEntry	13 }

smscSiwplmnLengthSmInPlmn OBJECT-TYPE
		SYNTAX	Unsigned32
		MAX-ACCESS read-only
		STATUS current
		DESCRIPTION
			"Accumulated length of short messages via PLMN"
	::= { siwplmnInstanceEntry	14 }

smscSiwplmnQelemUsed OBJECT-TYPE
		SYNTAX	Unsigned32
		MAX-ACCESS read-only
		STATUS current
		DESCRIPTION
			"Number of elements in internal queues"
	::= { siwplmnInstanceEntry	15 }

smscSiwplmnQelemInProcqueue OBJECT-TYPE
		SYNTAX	Unsigned32
		MAX-ACCESS read-only
		STATUS current
		DESCRIPTION
			"Number of elements used in process queue"
	::= { siwplmnInstanceEntry	16 }

smscSiwplmnQelemInExpqueue OBJECT-TYPE
		SYNTAX	Unsigned32
		MAX-ACCESS read-only
		STATUS current
		DESCRIPTION
			"Number of elements used in expedited queue"
	::= { siwplmnInstanceEntry	17 }

smscSiwplmnNrTimersRunning OBJECT-TYPE
		SYNTAX	Unsigned32
		MAX-ACCESS read-only
		STATUS current
		DESCRIPTION
			"Total number of timers running"
	::= { siwplmnInstanceEntry	18 }

smscSiwplmnNrSystemTimers OBJECT-TYPE
		SYNTAX	Unsigned32
		MAX-ACCESS read-only
		STATUS current
		DESCRIPTION
			"Number of system timers running"
	::= { siwplmnInstanceEntry	19 }

smscSiwplmnImiRecallQelem OBJECT-TYPE
		SYNTAX	Unsigned32
		MAX-ACCESS read-only
		STATUS current
		DESCRIPTION
			"Number of IMI recall-queue elements used"
	::= { siwplmnInstanceEntry	20 }

smscSiwplmnImiRecallQueues OBJECT-TYPE
		SYNTAX	Unsigned32
		MAX-ACCESS read-only
		STATUS current
		DESCRIPTION
			"Number of IMI-recall-queues used"
	::= { siwplmnInstanceEntry	21 }

smscSiwplmnIdiRecallQelem OBJECT-TYPE
		SYNTAX	Unsigned32
		MAX-ACCESS read-only
		STATUS current
		DESCRIPTION
			"Number of IDI recall-queue elements used"
	::= { siwplmnInstanceEntry	22 }

smscSiwplmnIdiRecallQueues OBJECT-TYPE
		SYNTAX	Unsigned32
		MAX-ACCESS read-only
		STATUS current
		DESCRIPTION
			"Number of IDI recall-queues used"
	::= { siwplmnInstanceEntry	23 }

smscSiwplmnIosRecallQelem OBJECT-TYPE
		SYNTAX	Unsigned32
		MAX-ACCESS read-only
		STATUS current
		DESCRIPTION
			"Number of IOS recall-queue elements used"
	::= { siwplmnInstanceEntry	24 }

smscSiwplmnIosRecallQueues OBJECT-TYPE
		SYNTAX	Unsigned32
		MAX-ACCESS read-only
		STATUS current
		DESCRIPTION
			"Number of IOS recall-queues used"
	::= { siwplmnInstanceEntry	25 }

smscSiwplmnLogRecallQelem OBJECT-TYPE
		SYNTAX	Unsigned32
		MAX-ACCESS read-only
		STATUS current
		DESCRIPTION
			"Number of LOG recall-queue elements used"
	::= { siwplmnInstanceEntry	26 }

smscSiwplmnLogRecallQueues OBJECT-TYPE
		SYNTAX	Unsigned32
		MAX-ACCESS read-only
		STATUS current
		DESCRIPTION
			"Number of LOG recall-queues used"
	::= { siwplmnInstanceEntry	27 }

smscSiwplmnTrcreqDiscarded OBJECT-TYPE
		SYNTAX	Unsigned32
		MAX-ACCESS read-only
		STATUS current
		DESCRIPTION
			"Number of trace requests discarded"
	::= { siwplmnInstanceEntry	28 }

smscSiwplmnSessionsPending OBJECT-TYPE
		SYNTAX	Unsigned32
		MAX-ACCESS read-only
		STATUS current
		DESCRIPTION
			"Number of sessions (currently) pending"
	::= { siwplmnInstanceEntry	29 }

smscSiwplmnAdtUsedMemory OBJECT-TYPE
		SYNTAX	Unsigned32
		MAX-ACCESS read-only
		STATUS current
		DESCRIPTION
			"Memory blocks used by ADT tables of SIWPLMN."
	::= { siwplmnInstanceEntry	30 }

smscSiwplmnSmResourceFail OBJECT-TYPE
		SYNTAX	Unsigned32
		MAX-ACCESS read-only
		STATUS current
		DESCRIPTION
			"Number of rejected SM due to resource shortage"
	::= { siwplmnInstanceEntry	31 }



-- end of SIWPLMN description.
-- --------------------------------------


-- --------------------------------------
-- Class SIWIMPORT
-- 
smscSiwimport OBJECT-TYPE
	SYNTAX  SEQUENCE OF SiwimportInstanceEntry
	MAX-ACCESS  not-accessible
	STATUS  current
	DESCRIPTION
		"Mapping table for SMSC SIWIMPORT entities."
   ::= { smscClassSiw   4  }

siwimportInstanceEntry  OBJECT-TYPE
	SYNTAX SiwimportInstanceEntry
	MAX-ACCESS  not-accessible
	STATUS  current
	DESCRIPTION
		"An entry (row) in the entityInstanceTable."
	INDEX { IMPLIED smscSiwimportName }
   ::= { smscSiwimport 1 }

SiwimportInstanceEntry ::= SEQUENCE {
		smscSiwimportName     DisplayString,
		smscSiwimportState   INTEGER,
		smscSiwimportLastupdate   TimeTicks,
		smscSiwimportNode	   DisplayString, 
		smscSiwimportMsgReceived	 Unsigned32, 
		smscSiwimportMsgRejected	 Unsigned32, 
		smscSiwimportMsgTransmitted	 Unsigned32, 
		smscSiwimportMsgFailed	 Unsigned32, 
		smscSiwimportQelemUsed	 Unsigned32, 
		smscSiwimportQelemInProcqueue	 Unsigned32, 
		smscSiwimportQelemInExpqueue	 Unsigned32, 
		smscSiwimportNrTimersRunning	 Unsigned32, 
		smscSiwimportNrSystemTimers	 Unsigned32, 
		smscSiwimportImiRecallQelem	 Unsigned32, 
		smscSiwimportImiRecallQueues	 Unsigned32, 
		smscSiwimportIdiRecallQelem	 Unsigned32, 
		smscSiwimportIdiRecallQueues	 Unsigned32, 
		smscSiwimportIosRecallQelem	 Unsigned32, 
		smscSiwimportIosRecallQueues	 Unsigned32, 
		smscSiwimportLogRecallQelem	 Unsigned32, 
		smscSiwimportLogRecallQueues	 Unsigned32, 
		smscSiwimportTrcreqDiscarded	 Unsigned32, 
		smscSiwimportDummyStatistic	 Unsigned32, 
		smscSiwimportSmsImported	 Unsigned32, 
		smscSiwimportTimeToComplete	 Unsigned32, 
		smscSiwimportTransmitRate	 Unsigned32
	}

smscSiwimportName  OBJECT-TYPE
	SYNTAX  DisplayString
	MAX-ACCESS  read-only
	STATUS   current
	DESCRIPTION
		"Identifies the name of the entity."
   ::= {siwimportInstanceEntry 1 }

smscSiwimportState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { siwimportInstanceEntry 2 }


smscSiwimportLastupdate OBJECT-TYPE
		SYNTAX	TimeTicks
		MAX-ACCESS read-only
		STATUS current
		DESCRIPTION
			"Value which reflects the last time the entities fields have been updated"
	::= { siwimportInstanceEntry	3 }

smscSiwimportNode  OBJECT-TYPE
	SYNTAX  DisplayString
	MAX-ACCESS  read-only
	STATUS   current
	DESCRIPTION
		"Identifies the node the entity is running on."
   ::= {siwimportInstanceEntry 4 }

smscSiwimportMsgReceived OBJECT-TYPE
		SYNTAX	Unsigned32
		MAX-ACCESS read-only
		STATUS current
		DESCRIPTION
			"Received messages"
	::= { siwimportInstanceEntry	5 }

smscSiwimportMsgRejected OBJECT-TYPE
		SYNTAX	Unsigned32
		MAX-ACCESS read-only
		STATUS current
		DESCRIPTION
			"Received messages and rejected"
	::= { siwimportInstanceEntry	6 }

smscSiwimportMsgTransmitted OBJECT-TYPE
		SYNTAX	Unsigned32
		MAX-ACCESS read-only
		STATUS current
		DESCRIPTION
			"Transmitted messages"
	::= { siwimportInstanceEntry	7 }

smscSiwimportMsgFailed OBJECT-TYPE
		SYNTAX	Unsigned32
		MAX-ACCESS read-only
		STATUS current
		DESCRIPTION
			"Messages that failed on sending"
	::= { siwimportInstanceEntry	8 }

smscSiwimportQelemUsed OBJECT-TYPE
		SYNTAX	Unsigned32
		MAX-ACCESS read-only
		STATUS current
		DESCRIPTION
			"Number of elements in internal queues"
	::= { siwimportInstanceEntry	9 }

smscSiwimportQelemInProcqueue OBJECT-TYPE
		SYNTAX	Unsigned32
		MAX-ACCESS read-only
		STATUS current
		DESCRIPTION
			"Number of elements used in process queue"
	::= { siwimportInstanceEntry	10 }

smscSiwimportQelemInExpqueue OBJECT-TYPE
		SYNTAX	Unsigned32
		MAX-ACCESS read-only
		STATUS current
		DESCRIPTION
			"Number of elements used in expedited queue"
	::= { siwimportInstanceEntry	11 }

smscSiwimportNrTimersRunning OBJECT-TYPE
		SYNTAX	Unsigned32
		MAX-ACCESS read-only
		STATUS current
		DESCRIPTION
			"Total number of timers running"
	::= { siwimportInstanceEntry	12 }

smscSiwimportNrSystemTimers OBJECT-TYPE
		SYNTAX	Unsigned32
		MAX-ACCESS read-only
		STATUS current
		DESCRIPTION
			"Number of system timers running"
	::= { siwimportInstanceEntry	13 }

smscSiwimportImiRecallQelem OBJECT-TYPE
		SYNTAX	Unsigned32
		MAX-ACCESS read-only
		STATUS current
		DESCRIPTION
			"Number of IMI recall-queue elements used"
	::= { siwimportInstanceEntry	14 }

smscSiwimportImiRecallQueues OBJECT-TYPE
		SYNTAX	Unsigned32
		MAX-ACCESS read-only
		STATUS current
		DESCRIPTION
			"Number of IMI-recall-queues used"
	::= { siwimportInstanceEntry	15 }

smscSiwimportIdiRecallQelem OBJECT-TYPE
		SYNTAX	Unsigned32
		MAX-ACCESS read-only
		STATUS current
		DESCRIPTION
			"Number of IDI recall-queue elements used"
	::= { siwimportInstanceEntry	16 }

smscSiwimportIdiRecallQueues OBJECT-TYPE
		SYNTAX	Unsigned32
		MAX-ACCESS read-only
		STATUS current
		DESCRIPTION
			"Number of IDI recall-queues used"
	::= { siwimportInstanceEntry	17 }

smscSiwimportIosRecallQelem OBJECT-TYPE
		SYNTAX	Unsigned32
		MAX-ACCESS read-only
		STATUS current
		DESCRIPTION
			"Number of IOS recall-queue elements used"
	::= { siwimportInstanceEntry	18 }

smscSiwimportIosRecallQueues OBJECT-TYPE
		SYNTAX	Unsigned32
		MAX-ACCESS read-only
		STATUS current
		DESCRIPTION
			"Number of IOS recall-queues used"
	::= { siwimportInstanceEntry	19 }

smscSiwimportLogRecallQelem OBJECT-TYPE
		SYNTAX	Unsigned32
		MAX-ACCESS read-only
		STATUS current
		DESCRIPTION
			"Number of LOG recall-queue elements used"
	::= { siwimportInstanceEntry	20 }

smscSiwimportLogRecallQueues OBJECT-TYPE
		SYNTAX	Unsigned32
		MAX-ACCESS read-only
		STATUS current
		DESCRIPTION
			"Number of LOG recall-queues used"
	::= { siwimportInstanceEntry	21 }

smscSiwimportTrcreqDiscarded OBJECT-TYPE
		SYNTAX	Unsigned32
		MAX-ACCESS read-only
		STATUS current
		DESCRIPTION
			"Number of trace requests discarded"
	::= { siwimportInstanceEntry	22 }

smscSiwimportDummyStatistic OBJECT-TYPE
		SYNTAX	Unsigned32
		MAX-ACCESS read-only
		STATUS current
		DESCRIPTION
			"No statistical counters"
	::= { siwimportInstanceEntry	23 }

smscSiwimportSmsImported OBJECT-TYPE
		SYNTAX	Unsigned32
		MAX-ACCESS read-only
		STATUS current
		DESCRIPTION
			"The number of imported Short Messages"
	::= { siwimportInstanceEntry	24 }

smscSiwimportTimeToComplete OBJECT-TYPE
		SYNTAX	Unsigned32
		MAX-ACCESS read-only
		STATUS current
		DESCRIPTION
			"Meantime left for the import process to complete  minutes"
	::= { siwimportInstanceEntry	25 }

smscSiwimportTransmitRate OBJECT-TYPE
		SYNTAX	Unsigned32
		MAX-ACCESS read-only
		STATUS current
		DESCRIPTION
			"Actual rate of transmission"
	::= { siwimportInstanceEntry	26 }



-- end of SIWIMPORT description.
-- --------------------------------------


-- --------------------------------------
-- Class SIWVMS
-- 
smscSiwvms OBJECT-TYPE
	SYNTAX  SEQUENCE OF SiwvmsInstanceEntry
	MAX-ACCESS  not-accessible
	STATUS  current
	DESCRIPTION
		"Mapping table for SMSC SIWVMS entities."
   ::= { smscClassSiw   5  }

siwvmsInstanceEntry  OBJECT-TYPE
	SYNTAX SiwvmsInstanceEntry
	MAX-ACCESS  not-accessible
	STATUS  current
	DESCRIPTION
		"An entry (row) in the entityInstanceTable."
	INDEX { IMPLIED smscSiwvmsName }
   ::= { smscSiwvms 1 }

SiwvmsInstanceEntry ::= SEQUENCE {
		smscSiwvmsName     DisplayString,
		smscSiwvmsState   INTEGER,
		smscSiwvmsLastupdate   TimeTicks,
		smscSiwvmsNode	   DisplayString, 
		smscSiwvmsMsgReceived	 Unsigned32, 
		smscSiwvmsMsgRejected	 Unsigned32, 
		smscSiwvmsMsgTransmitted	 Unsigned32, 
		smscSiwvmsNotifFailed	 Unsigned32, 
		smscSiwvmsNotifTransmitted	 Unsigned32, 
		smscSiwvmsMsgFailed	 Unsigned32, 
		smscSiwvmsAlertMsInvalid	 Unsigned32, 
		smscSiwvmsAlertMsReceived	 Unsigned32, 
		smscSiwvmsAlertVmsFailed	 Unsigned32, 
		smscSiwvmsAlertVmsTransmitted	 Unsigned32, 
		smscSiwvmsSmDeletedInvalid	 Unsigned32, 
		smscSiwvmsSmDeletedReceived	 Unsigned32, 
		smscSiwvmsQelemUsed	 Unsigned32, 
		smscSiwvmsQelemInProcqueue	 Unsigned32, 
		smscSiwvmsQelemInExpqueue	 Unsigned32, 
		smscSiwvmsNrTimersRunning	 Unsigned32, 
		smscSiwvmsNrSystemTimers	 Unsigned32, 
		smscSiwvmsImiRecallQelem	 Unsigned32, 
		smscSiwvmsImiRecallQueues	 Unsigned32, 
		smscSiwvmsIdiRecallQelem	 Unsigned32, 
		smscSiwvmsIdiRecallQueues	 Unsigned32, 
		smscSiwvmsIosRecallQelem	 Unsigned32, 
		smscSiwvmsIosRecallQueues	 Unsigned32, 
		smscSiwvmsLogRecallQelem	 Unsigned32, 
		smscSiwvmsLogRecallQueues	 Unsigned32, 
		smscSiwvmsTrcreqDiscarded	 Unsigned32
	}

smscSiwvmsName  OBJECT-TYPE
	SYNTAX  DisplayString
	MAX-ACCESS  read-only
	STATUS   current
	DESCRIPTION
		"Identifies the name of the entity."
   ::= {siwvmsInstanceEntry 1 }

smscSiwvmsState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { siwvmsInstanceEntry 2 }


smscSiwvmsLastupdate OBJECT-TYPE
		SYNTAX	TimeTicks
		MAX-ACCESS read-only
		STATUS current
		DESCRIPTION
			"Value which reflects the last time the entities fields have been updated"
	::= { siwvmsInstanceEntry	3 }

smscSiwvmsNode  OBJECT-TYPE
	SYNTAX  DisplayString
	MAX-ACCESS  read-only
	STATUS   current
	DESCRIPTION
		"Identifies the node the entity is running on."
   ::= {siwvmsInstanceEntry 4 }

smscSiwvmsMsgReceived OBJECT-TYPE
		SYNTAX	Unsigned32
		MAX-ACCESS read-only
		STATUS current
		DESCRIPTION
			"Received messages"
	::= { siwvmsInstanceEntry	5 }

smscSiwvmsMsgRejected OBJECT-TYPE
		SYNTAX	Unsigned32
		MAX-ACCESS read-only
		STATUS current
		DESCRIPTION
			"Received messages and rejected"
	::= { siwvmsInstanceEntry	6 }

smscSiwvmsMsgTransmitted OBJECT-TYPE
		SYNTAX	Unsigned32
		MAX-ACCESS read-only
		STATUS current
		DESCRIPTION
			"Transmitted messages"
	::= { siwvmsInstanceEntry	7 }

smscSiwvmsNotifFailed OBJECT-TYPE
		SYNTAX	Unsigned32
		MAX-ACCESS read-only
		STATUS current
		DESCRIPTION
			"Notifications submitted and failed"
	::= { siwvmsInstanceEntry	8 }

smscSiwvmsNotifTransmitted OBJECT-TYPE
		SYNTAX	Unsigned32
		MAX-ACCESS read-only
		STATUS current
		DESCRIPTION
			"Transmitted notifications"
	::= { siwvmsInstanceEntry	9 }

smscSiwvmsMsgFailed OBJECT-TYPE
		SYNTAX	Unsigned32
		MAX-ACCESS read-only
		STATUS current
		DESCRIPTION
			"Messages that failed on sending"
	::= { siwvmsInstanceEntry	10 }

smscSiwvmsAlertMsInvalid OBJECT-TYPE
		SYNTAX	Unsigned32
		MAX-ACCESS read-only
		STATUS current
		DESCRIPTION
			"Number of received invalid ALERT_MS messages"
	::= { siwvmsInstanceEntry	11 }

smscSiwvmsAlertMsReceived OBJECT-TYPE
		SYNTAX	Unsigned32
		MAX-ACCESS read-only
		STATUS current
		DESCRIPTION
			"Number of received ALERT_MS messages"
	::= { siwvmsInstanceEntry	12 }

smscSiwvmsAlertVmsFailed OBJECT-TYPE
		SYNTAX	Unsigned32
		MAX-ACCESS read-only
		STATUS current
		DESCRIPTION
			"Number of failed ALERT_VMS messages"
	::= { siwvmsInstanceEntry	13 }

smscSiwvmsAlertVmsTransmitted OBJECT-TYPE
		SYNTAX	Unsigned32
		MAX-ACCESS read-only
		STATUS current
		DESCRIPTION
			"Number of successfully transmitted ALERT_VMS messages"
	::= { siwvmsInstanceEntry	14 }

smscSiwvmsSmDeletedInvalid OBJECT-TYPE
		SYNTAX	Unsigned32
		MAX-ACCESS read-only
		STATUS current
		DESCRIPTION
			"Received number of invalid SM_DELETED messages"
	::= { siwvmsInstanceEntry	15 }

smscSiwvmsSmDeletedReceived OBJECT-TYPE
		SYNTAX	Unsigned32
		MAX-ACCESS read-only
		STATUS current
		DESCRIPTION
			"Received number of SM_DELETED messages"
	::= { siwvmsInstanceEntry	16 }

smscSiwvmsQelemUsed OBJECT-TYPE
		SYNTAX	Unsigned32
		MAX-ACCESS read-only
		STATUS current
		DESCRIPTION
			"Number of elements in internal queues"
	::= { siwvmsInstanceEntry	17 }

smscSiwvmsQelemInProcqueue OBJECT-TYPE
		SYNTAX	Unsigned32
		MAX-ACCESS read-only
		STATUS current
		DESCRIPTION
			"Number of elements used in process queue"
	::= { siwvmsInstanceEntry	18 }

smscSiwvmsQelemInExpqueue OBJECT-TYPE
		SYNTAX	Unsigned32
		MAX-ACCESS read-only
		STATUS current
		DESCRIPTION
			"Number of elements used in expedited queue"
	::= { siwvmsInstanceEntry	19 }

smscSiwvmsNrTimersRunning OBJECT-TYPE
		SYNTAX	Unsigned32
		MAX-ACCESS read-only
		STATUS current
		DESCRIPTION
			"Total number of timers running"
	::= { siwvmsInstanceEntry	20 }

smscSiwvmsNrSystemTimers OBJECT-TYPE
		SYNTAX	Unsigned32
		MAX-ACCESS read-only
		STATUS current
		DESCRIPTION
			"Number of system timers running"
	::= { siwvmsInstanceEntry	21 }

smscSiwvmsImiRecallQelem OBJECT-TYPE
		SYNTAX	Unsigned32
		MAX-ACCESS read-only
		STATUS current
		DESCRIPTION
			"Number of IMI recall-queue elements used"
	::= { siwvmsInstanceEntry	22 }

smscSiwvmsImiRecallQueues OBJECT-TYPE
		SYNTAX	Unsigned32
		MAX-ACCESS read-only
		STATUS current
		DESCRIPTION
			"Number of IMI-recall-queues used"
	::= { siwvmsInstanceEntry	23 }

smscSiwvmsIdiRecallQelem OBJECT-TYPE
		SYNTAX	Unsigned32
		MAX-ACCESS read-only
		STATUS current
		DESCRIPTION
			"Number of IDI recall-queue elements used"
	::= { siwvmsInstanceEntry	24 }

smscSiwvmsIdiRecallQueues OBJECT-TYPE
		SYNTAX	Unsigned32
		MAX-ACCESS read-only
		STATUS current
		DESCRIPTION
			"Number of IDI recall-queues used"
	::= { siwvmsInstanceEntry	25 }

smscSiwvmsIosRecallQelem OBJECT-TYPE
		SYNTAX	Unsigned32
		MAX-ACCESS read-only
		STATUS current
		DESCRIPTION
			"Number of IOS recall-queue elements used"
	::= { siwvmsInstanceEntry	26 }

smscSiwvmsIosRecallQueues OBJECT-TYPE
		SYNTAX	Unsigned32
		MAX-ACCESS read-only
		STATUS current
		DESCRIPTION
			"Number of IOS recall-queues used"
	::= { siwvmsInstanceEntry	27 }

smscSiwvmsLogRecallQelem OBJECT-TYPE
		SYNTAX	Unsigned32
		MAX-ACCESS read-only
		STATUS current
		DESCRIPTION
			"Number of LOG recall-queue elements used"
	::= { siwvmsInstanceEntry	28 }

smscSiwvmsLogRecallQueues OBJECT-TYPE
		SYNTAX	Unsigned32
		MAX-ACCESS read-only
		STATUS current
		DESCRIPTION
			"Number of LOG recall-queues used"
	::= { siwvmsInstanceEntry	29 }

smscSiwvmsTrcreqDiscarded OBJECT-TYPE
		SYNTAX	Unsigned32
		MAX-ACCESS read-only
		STATUS current
		DESCRIPTION
			"Number of trace requests discarded"
	::= { siwvmsInstanceEntry	30 }



-- end of SIWVMS description.
-- --------------------------------------


-- --------------------------------------
-- Class SIWIVR
-- 
smscSiwivr OBJECT-TYPE
	SYNTAX  SEQUENCE OF SiwivrInstanceEntry
	MAX-ACCESS  not-accessible
	STATUS  current
	DESCRIPTION
		"Mapping table for SMSC SIWIVR entities."
   ::= { smscClassSiw   6  }

siwivrInstanceEntry  OBJECT-TYPE
	SYNTAX SiwivrInstanceEntry
	MAX-ACCESS  not-accessible
	STATUS  current
	DESCRIPTION
		"An entry (row) in the entityInstanceTable."
	INDEX { IMPLIED smscSiwivrName }
   ::= { smscSiwivr 1 }

SiwivrInstanceEntry ::= SEQUENCE {
		smscSiwivrName     DisplayString,
		smscSiwivrState   INTEGER,
		smscSiwivrLastupdate   TimeTicks,
		smscSiwivrNode	   DisplayString, 
		smscSiwivrSmInvalid	 Unsigned32, 
		smscSiwivrMsgReceived	 Unsigned32, 
		smscSiwivrMsgRejected	 Unsigned32, 
		smscSiwivrMsgTransmitted	 Unsigned32, 
		smscSiwivrNotifFailed	 Unsigned32, 
		smscSiwivrNotifTransmitted	 Unsigned32, 
		smscSiwivrSmReceived	 Unsigned32, 
		smscSiwivrMsgFailed	 Unsigned32, 
		smscSiwivrQelemUsed	 Unsigned32, 
		smscSiwivrQelemInProcqueue	 Unsigned32, 
		smscSiwivrQelemInExpqueue	 Unsigned32, 
		smscSiwivrNrTimersRunning	 Unsigned32, 
		smscSiwivrNrSystemTimers	 Unsigned32, 
		smscSiwivrImiRecallQelem	 Unsigned32, 
		smscSiwivrImiRecallQueues	 Unsigned32, 
		smscSiwivrIdiRecallQelem	 Unsigned32, 
		smscSiwivrIdiRecallQueues	 Unsigned32, 
		smscSiwivrIosRecallQelem	 Unsigned32, 
		smscSiwivrIosRecallQueues	 Unsigned32, 
		smscSiwivrLogRecallQelem	 Unsigned32, 
		smscSiwivrLogRecallQueues	 Unsigned32, 
		smscSiwivrTrcreqDiscarded	 Unsigned32
	}

smscSiwivrName  OBJECT-TYPE
	SYNTAX  DisplayString
	MAX-ACCESS  read-only
	STATUS   current
	DESCRIPTION
		"Identifies the name of the entity."
   ::= {siwivrInstanceEntry 1 }

smscSiwivrState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { siwivrInstanceEntry 2 }


smscSiwivrLastupdate OBJECT-TYPE
		SYNTAX	TimeTicks
		MAX-ACCESS read-only
		STATUS current
		DESCRIPTION
			"Value which reflects the last time the entities fields have been updated"
	::= { siwivrInstanceEntry	3 }

smscSiwivrNode  OBJECT-TYPE
	SYNTAX  DisplayString
	MAX-ACCESS  read-only
	STATUS   current
	DESCRIPTION
		"Identifies the node the entity is running on."
   ::= {siwivrInstanceEntry 4 }

smscSiwivrSmInvalid OBJECT-TYPE
		SYNTAX	Unsigned32
		MAX-ACCESS read-only
		STATUS current
		DESCRIPTION
			"Received invalid short messages"
	::= { siwivrInstanceEntry	5 }

smscSiwivrMsgReceived OBJECT-TYPE
		SYNTAX	Unsigned32
		MAX-ACCESS read-only
		STATUS current
		DESCRIPTION
			"Received messages"
	::= { siwivrInstanceEntry	6 }

smscSiwivrMsgRejected OBJECT-TYPE
		SYNTAX	Unsigned32
		MAX-ACCESS read-only
		STATUS current
		DESCRIPTION
			"Received messages and rejected"
	::= { siwivrInstanceEntry	7 }

smscSiwivrMsgTransmitted OBJECT-TYPE
		SYNTAX	Unsigned32
		MAX-ACCESS read-only
		STATUS current
		DESCRIPTION
			"Transmitted messages"
	::= { siwivrInstanceEntry	8 }

smscSiwivrNotifFailed OBJECT-TYPE
		SYNTAX	Unsigned32
		MAX-ACCESS read-only
		STATUS current
		DESCRIPTION
			"Notifications submitted and failed"
	::= { siwivrInstanceEntry	9 }

smscSiwivrNotifTransmitted OBJECT-TYPE
		SYNTAX	Unsigned32
		MAX-ACCESS read-only
		STATUS current
		DESCRIPTION
			"Transmitted notifications"
	::= { siwivrInstanceEntry	10 }

smscSiwivrSmReceived OBJECT-TYPE
		SYNTAX	Unsigned32
		MAX-ACCESS read-only
		STATUS current
		DESCRIPTION
			"Received short messages"
	::= { siwivrInstanceEntry	11 }

smscSiwivrMsgFailed OBJECT-TYPE
		SYNTAX	Unsigned32
		MAX-ACCESS read-only
		STATUS current
		DESCRIPTION
			"Messages that failed on sending"
	::= { siwivrInstanceEntry	12 }

smscSiwivrQelemUsed OBJECT-TYPE
		SYNTAX	Unsigned32
		MAX-ACCESS read-only
		STATUS current
		DESCRIPTION
			"Number of elements in internal queues"
	::= { siwivrInstanceEntry	13 }

smscSiwivrQelemInProcqueue OBJECT-TYPE
		SYNTAX	Unsigned32
		MAX-ACCESS read-only
		STATUS current
		DESCRIPTION
			"Number of elements used in process queue"
	::= { siwivrInstanceEntry	14 }

smscSiwivrQelemInExpqueue OBJECT-TYPE
		SYNTAX	Unsigned32
		MAX-ACCESS read-only
		STATUS current
		DESCRIPTION
			"Number of elements used in expedited queue"
	::= { siwivrInstanceEntry	15 }

smscSiwivrNrTimersRunning OBJECT-TYPE
		SYNTAX	Unsigned32
		MAX-ACCESS read-only
		STATUS current
		DESCRIPTION
			"Total number of timers running"
	::= { siwivrInstanceEntry	16 }

smscSiwivrNrSystemTimers OBJECT-TYPE
		SYNTAX	Unsigned32
		MAX-ACCESS read-only
		STATUS current
		DESCRIPTION
			"Number of system timers running"
	::= { siwivrInstanceEntry	17 }

smscSiwivrImiRecallQelem OBJECT-TYPE
		SYNTAX	Unsigned32
		MAX-ACCESS read-only
		STATUS current
		DESCRIPTION
			"Number of IMI recall-queue elements used"
	::= { siwivrInstanceEntry	18 }

smscSiwivrImiRecallQueues OBJECT-TYPE
		SYNTAX	Unsigned32
		MAX-ACCESS read-only
		STATUS current
		DESCRIPTION
			"Number of IMI-recall-queues used"
	::= { siwivrInstanceEntry	19 }

smscSiwivrIdiRecallQelem OBJECT-TYPE
		SYNTAX	Unsigned32
		MAX-ACCESS read-only
		STATUS current
		DESCRIPTION
			"Number of IDI recall-queue elements used"
	::= { siwivrInstanceEntry	20 }

smscSiwivrIdiRecallQueues OBJECT-TYPE
		SYNTAX	Unsigned32
		MAX-ACCESS read-only
		STATUS current
		DESCRIPTION
			"Number of IDI recall-queues used"
	::= { siwivrInstanceEntry	21 }

smscSiwivrIosRecallQelem OBJECT-TYPE
		SYNTAX	Unsigned32
		MAX-ACCESS read-only
		STATUS current
		DESCRIPTION
			"Number of IOS recall-queue elements used"
	::= { siwivrInstanceEntry	22 }

smscSiwivrIosRecallQueues OBJECT-TYPE
		SYNTAX	Unsigned32
		MAX-ACCESS read-only
		STATUS current
		DESCRIPTION
			"Number of IOS recall-queues used"
	::= { siwivrInstanceEntry	23 }

smscSiwivrLogRecallQelem OBJECT-TYPE
		SYNTAX	Unsigned32
		MAX-ACCESS read-only
		STATUS current
		DESCRIPTION
			"Number of LOG recall-queue elements used"
	::= { siwivrInstanceEntry	24 }

smscSiwivrLogRecallQueues OBJECT-TYPE
		SYNTAX	Unsigned32
		MAX-ACCESS read-only
		STATUS current
		DESCRIPTION
			"Number of LOG recall-queues used"
	::= { siwivrInstanceEntry	25 }

smscSiwivrTrcreqDiscarded OBJECT-TYPE
		SYNTAX	Unsigned32
		MAX-ACCESS read-only
		STATUS current
		DESCRIPTION
			"Number of trace requests discarded"
	::= { siwivrInstanceEntry	26 }



-- end of SIWIVR description.
-- --------------------------------------


-- --------------------------------------
-- Class SIWVSMPP
-- 
smscSiwvsmpp OBJECT-TYPE
	SYNTAX  SEQUENCE OF SiwvsmppInstanceEntry
	MAX-ACCESS  not-accessible
	STATUS  current
	DESCRIPTION
		"Mapping table for SMSC SIWVSMPP entities."
   ::= { smscClassSiw   7  }

siwvsmppInstanceEntry  OBJECT-TYPE
	SYNTAX SiwvsmppInstanceEntry
	MAX-ACCESS  not-accessible
	STATUS  current
	DESCRIPTION
		"An entry (row) in the entityInstanceTable."
	INDEX { IMPLIED smscSiwvsmppName }
   ::= { smscSiwvsmpp 1 }

SiwvsmppInstanceEntry ::= SEQUENCE {
		smscSiwvsmppName     DisplayString,
		smscSiwvsmppState   INTEGER,
		smscSiwvsmppLastupdate   TimeTicks,
		smscSiwvsmppNode	   DisplayString, 
		smscSiwvsmppMsgReceived	 Unsigned32, 
		smscSiwvsmppMsgRejected	 Unsigned32, 
		smscSiwvsmppMsgTransmitted	 Unsigned32, 
		smscSiwvsmppNotifFailed	 Unsigned32, 
		smscSiwvsmppNotifTransmitted	 Unsigned32, 
		smscSiwvsmppMsgFailed	 Unsigned32, 
		smscSiwvsmppAlertMsInvalid	 Unsigned32, 
		smscSiwvsmppAlertMsReceived	 Unsigned32, 
		smscSiwvsmppAlertVmsFailed	 Unsigned32, 
		smscSiwvsmppAlertVmsTransmitted	 Unsigned32, 
		smscSiwvsmppSmDeletedInvalid	 Unsigned32, 
		smscSiwvsmppSmDeletedReceived	 Unsigned32, 
		smscSiwvsmppQelemUsed	 Unsigned32, 
		smscSiwvsmppQelemInProcqueue	 Unsigned32, 
		smscSiwvsmppQelemInExpqueue	 Unsigned32, 
		smscSiwvsmppNrTimersRunning	 Unsigned32, 
		smscSiwvsmppNrSystemTimers	 Unsigned32, 
		smscSiwvsmppImiRecallQelem	 Unsigned32, 
		smscSiwvsmppImiRecallQueues	 Unsigned32, 
		smscSiwvsmppIdiRecallQelem	 Unsigned32, 
		smscSiwvsmppIdiRecallQueues	 Unsigned32, 
		smscSiwvsmppIosRecallQelem	 Unsigned32, 
		smscSiwvsmppIosRecallQueues	 Unsigned32, 
		smscSiwvsmppLogRecallQelem	 Unsigned32, 
		smscSiwvsmppLogRecallQueues	 Unsigned32, 
		smscSiwvsmppTrcreqDiscarded	 Unsigned32
	}

smscSiwvsmppName  OBJECT-TYPE
	SYNTAX  DisplayString
	MAX-ACCESS  read-only
	STATUS   current
	DESCRIPTION
		"Identifies the name of the entity."
   ::= {siwvsmppInstanceEntry 1 }

smscSiwvsmppState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { siwvsmppInstanceEntry 2 }


smscSiwvsmppLastupdate OBJECT-TYPE
		SYNTAX	TimeTicks
		MAX-ACCESS read-only
		STATUS current
		DESCRIPTION
			"Value which reflects the last time the entities fields have been updated"
	::= { siwvsmppInstanceEntry	3 }

smscSiwvsmppNode  OBJECT-TYPE
	SYNTAX  DisplayString
	MAX-ACCESS  read-only
	STATUS   current
	DESCRIPTION
		"Identifies the node the entity is running on."
   ::= {siwvsmppInstanceEntry 4 }

smscSiwvsmppMsgReceived OBJECT-TYPE
		SYNTAX	Unsigned32
		MAX-ACCESS read-only
		STATUS current
		DESCRIPTION
			"Received messages"
	::= { siwvsmppInstanceEntry	5 }

smscSiwvsmppMsgRejected OBJECT-TYPE
		SYNTAX	Unsigned32
		MAX-ACCESS read-only
		STATUS current
		DESCRIPTION
			"Received messages and rejected"
	::= { siwvsmppInstanceEntry	6 }

smscSiwvsmppMsgTransmitted OBJECT-TYPE
		SYNTAX	Unsigned32
		MAX-ACCESS read-only
		STATUS current
		DESCRIPTION
			"Transmitted messages"
	::= { siwvsmppInstanceEntry	7 }

smscSiwvsmppNotifFailed OBJECT-TYPE
		SYNTAX	Unsigned32
		MAX-ACCESS read-only
		STATUS current
		DESCRIPTION
			"Notifications submitted and failed"
	::= { siwvsmppInstanceEntry	8 }

smscSiwvsmppNotifTransmitted OBJECT-TYPE
		SYNTAX	Unsigned32
		MAX-ACCESS read-only
		STATUS current
		DESCRIPTION
			"Transmitted notifications"
	::= { siwvsmppInstanceEntry	9 }

smscSiwvsmppMsgFailed OBJECT-TYPE
		SYNTAX	Unsigned32
		MAX-ACCESS read-only
		STATUS current
		DESCRIPTION
			"Messages that failed on sending"
	::= { siwvsmppInstanceEntry	10 }

smscSiwvsmppAlertMsInvalid OBJECT-TYPE
		SYNTAX	Unsigned32
		MAX-ACCESS read-only
		STATUS current
		DESCRIPTION
			"Number of received invalid ALERT_MS messages"
	::= { siwvsmppInstanceEntry	11 }

smscSiwvsmppAlertMsReceived OBJECT-TYPE
		SYNTAX	Unsigned32
		MAX-ACCESS read-only
		STATUS current
		DESCRIPTION
			"Number of received ALERT_MS messages"
	::= { siwvsmppInstanceEntry	12 }

smscSiwvsmppAlertVmsFailed OBJECT-TYPE
		SYNTAX	Unsigned32
		MAX-ACCESS read-only
		STATUS current
		DESCRIPTION
			"Number of failed ALERT_VMS messages"
	::= { siwvsmppInstanceEntry	13 }

smscSiwvsmppAlertVmsTransmitted OBJECT-TYPE
		SYNTAX	Unsigned32
		MAX-ACCESS read-only
		STATUS current
		DESCRIPTION
			"Number of successfull transmitted ALERT_VMS messages"
	::= { siwvsmppInstanceEntry	14 }

smscSiwvsmppSmDeletedInvalid OBJECT-TYPE
		SYNTAX	Unsigned32
		MAX-ACCESS read-only
		STATUS current
		DESCRIPTION
			"Received number of invalid SM_DELETED messages"
	::= { siwvsmppInstanceEntry	15 }

smscSiwvsmppSmDeletedReceived OBJECT-TYPE
		SYNTAX	Unsigned32
		MAX-ACCESS read-only
		STATUS current
		DESCRIPTION
			"Received number of SM_DELETED messages"
	::= { siwvsmppInstanceEntry	16 }

smscSiwvsmppQelemUsed OBJECT-TYPE
		SYNTAX	Unsigned32
		MAX-ACCESS read-only
		STATUS current
		DESCRIPTION
			"Number of elements in internal queues"
	::= { siwvsmppInstanceEntry	17 }

smscSiwvsmppQelemInProcqueue OBJECT-TYPE
		SYNTAX	Unsigned32
		MAX-ACCESS read-only
		STATUS current
		DESCRIPTION
			"Number of elements used in process queue"
	::= { siwvsmppInstanceEntry	18 }

smscSiwvsmppQelemInExpqueue OBJECT-TYPE
		SYNTAX	Unsigned32
		MAX-ACCESS read-only
		STATUS current
		DESCRIPTION
			"Number of elements used in expedited queue"
	::= { siwvsmppInstanceEntry	19 }

smscSiwvsmppNrTimersRunning OBJECT-TYPE
		SYNTAX	Unsigned32
		MAX-ACCESS read-only
		STATUS current
		DESCRIPTION
			"Total number of timers running"
	::= { siwvsmppInstanceEntry	20 }

smscSiwvsmppNrSystemTimers OBJECT-TYPE
		SYNTAX	Unsigned32
		MAX-ACCESS read-only
		STATUS current
		DESCRIPTION
			"Number of system timers running"
	::= { siwvsmppInstanceEntry	21 }

smscSiwvsmppImiRecallQelem OBJECT-TYPE
		SYNTAX	Unsigned32
		MAX-ACCESS read-only
		STATUS current
		DESCRIPTION
			"Number of IMI recall-queue elements used"
	::= { siwvsmppInstanceEntry	22 }

smscSiwvsmppImiRecallQueues OBJECT-TYPE
		SYNTAX	Unsigned32
		MAX-ACCESS read-only
		STATUS current
		DESCRIPTION
			"Number of IMI-recall-queues used"
	::= { siwvsmppInstanceEntry	23 }

smscSiwvsmppIdiRecallQelem OBJECT-TYPE
		SYNTAX	Unsigned32
		MAX-ACCESS read-only
		STATUS current
		DESCRIPTION
			"Number of IDI recall-queue elements used"
	::= { siwvsmppInstanceEntry	24 }

smscSiwvsmppIdiRecallQueues OBJECT-TYPE
		SYNTAX	Unsigned32
		MAX-ACCESS read-only
		STATUS current
		DESCRIPTION
			"Number of IDI recall-queues used"
	::= { siwvsmppInstanceEntry	25 }

smscSiwvsmppIosRecallQelem OBJECT-TYPE
		SYNTAX	Unsigned32
		MAX-ACCESS read-only
		STATUS current
		DESCRIPTION
			"Number of IOS recall-queue elements used"
	::= { siwvsmppInstanceEntry	26 }

smscSiwvsmppIosRecallQueues OBJECT-TYPE
		SYNTAX	Unsigned32
		MAX-ACCESS read-only
		STATUS current
		DESCRIPTION
			"Number of IOS recall-queues used"
	::= { siwvsmppInstanceEntry	27 }

smscSiwvsmppLogRecallQelem OBJECT-TYPE
		SYNTAX	Unsigned32
		MAX-ACCESS read-only
		STATUS current
		DESCRIPTION
			"Number of LOG recall-queue elements used"
	::= { siwvsmppInstanceEntry	28 }

smscSiwvsmppLogRecallQueues OBJECT-TYPE
		SYNTAX	Unsigned32
		MAX-ACCESS read-only
		STATUS current
		DESCRIPTION
			"Number of LOG recall-queues used"
	::= { siwvsmppInstanceEntry	29 }

smscSiwvsmppTrcreqDiscarded OBJECT-TYPE
		SYNTAX	Unsigned32
		MAX-ACCESS read-only
		STATUS current
		DESCRIPTION
			"Number of trace requests discarded"
	::= { siwvsmppInstanceEntry	30 }



-- end of SIWVSMPP description.
-- --------------------------------------


-- --------------------------------------
-- Class SIWTAP
-- 
smscSiwtap OBJECT-TYPE
	SYNTAX  SEQUENCE OF SiwtapInstanceEntry
	MAX-ACCESS  not-accessible
	STATUS  current
	DESCRIPTION
		"Mapping table for SMSC SIWTAP entities."
   ::= { smscClassSiw   8  }

siwtapInstanceEntry  OBJECT-TYPE
	SYNTAX SiwtapInstanceEntry
	MAX-ACCESS  not-accessible
	STATUS  current
	DESCRIPTION
		"An entry (row) in the entityInstanceTable."
	INDEX { IMPLIED smscSiwtapName }
   ::= { smscSiwtap 1 }

SiwtapInstanceEntry ::= SEQUENCE {
		smscSiwtapName     DisplayString,
		smscSiwtapState   INTEGER,
		smscSiwtapLastupdate   TimeTicks,
		smscSiwtapNode	   DisplayString, 
		smscSiwtapMsgReceived	 Unsigned32, 
		smscSiwtapMsgRejected	 Unsigned32, 
		smscSiwtapMsgTransmitted	 Unsigned32, 
		smscSiwtapMsgFailed	 Unsigned32, 
		smscSiwtapSmPstnReceived	 Unsigned32, 
		smscSiwtapSmX25Received	 Unsigned32, 
		smscSiwtapSmTcpReceived	 Unsigned32, 
		smscSiwtapSmPstnInvalid	 Unsigned32, 
		smscSiwtapSmX25Invalid	 Unsigned32, 
		smscSiwtapSmTcpInvalid	 Unsigned32, 
		smscSiwtapLengthSmInPstn	 Unsigned32, 
		smscSiwtapLengthSmInX25	 Unsigned32, 
		smscSiwtapLengthSmInTcp	 Unsigned32, 
		smscSiwtapQelemUsed	 Unsigned32, 
		smscSiwtapQelemInProcqueue	 Unsigned32, 
		smscSiwtapQelemInExpqueue	 Unsigned32, 
		smscSiwtapNrTimersRunning	 Unsigned32, 
		smscSiwtapNrSystemTimers	 Unsigned32, 
		smscSiwtapImiRecallQelem	 Unsigned32, 
		smscSiwtapImiRecallQueues	 Unsigned32, 
		smscSiwtapIdiRecallQelem	 Unsigned32, 
		smscSiwtapIdiRecallQueues	 Unsigned32, 
		smscSiwtapIosRecallQelem	 Unsigned32, 
		smscSiwtapIosRecallQueues	 Unsigned32, 
		smscSiwtapLogRecallQelem	 Unsigned32, 
		smscSiwtapLogRecallQueues	 Unsigned32, 
		smscSiwtapTrcreqDiscarded	 Unsigned32, 
		smscSiwtapSmPstnTruncated	 Unsigned32, 
		smscSiwtapSmX25Truncated	 Unsigned32, 
		smscSiwtapSmTcpTruncated	 Unsigned32
	}

smscSiwtapName  OBJECT-TYPE
	SYNTAX  DisplayString
	MAX-ACCESS  read-only
	STATUS   current
	DESCRIPTION
		"Identifies the name of the entity."
   ::= {siwtapInstanceEntry 1 }

smscSiwtapState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { siwtapInstanceEntry 2 }


smscSiwtapLastupdate OBJECT-TYPE
		SYNTAX	TimeTicks
		MAX-ACCESS read-only
		STATUS current
		DESCRIPTION
			"Value which reflects the last time the entities fields have been updated"
	::= { siwtapInstanceEntry	3 }

smscSiwtapNode  OBJECT-TYPE
	SYNTAX  DisplayString
	MAX-ACCESS  read-only
	STATUS   current
	DESCRIPTION
		"Identifies the node the entity is running on."
   ::= {siwtapInstanceEntry 4 }

smscSiwtapMsgReceived OBJECT-TYPE
		SYNTAX	Unsigned32
		MAX-ACCESS read-only
		STATUS current
		DESCRIPTION
			"Received messages"
	::= { siwtapInstanceEntry	5 }

smscSiwtapMsgRejected OBJECT-TYPE
		SYNTAX	Unsigned32
		MAX-ACCESS read-only
		STATUS current
		DESCRIPTION
			"Received messages and rejected"
	::= { siwtapInstanceEntry	6 }

smscSiwtapMsgTransmitted OBJECT-TYPE
		SYNTAX	Unsigned32
		MAX-ACCESS read-only
		STATUS current
		DESCRIPTION
			"Transmitted messages"
	::= { siwtapInstanceEntry	7 }

smscSiwtapMsgFailed OBJECT-TYPE
		SYNTAX	Unsigned32
		MAX-ACCESS read-only
		STATUS current
		DESCRIPTION
			"Messages that failed on sending"
	::= { siwtapInstanceEntry	8 }

smscSiwtapSmPstnReceived OBJECT-TYPE
		SYNTAX	Unsigned32
		MAX-ACCESS read-only
		STATUS current
		DESCRIPTION
			"Short messages received from PSTN"
	::= { siwtapInstanceEntry	9 }

smscSiwtapSmX25Received OBJECT-TYPE
		SYNTAX	Unsigned32
		MAX-ACCESS read-only
		STATUS current
		DESCRIPTION
			"Short messages received from X25"
	::= { siwtapInstanceEntry	10 }

smscSiwtapSmTcpReceived OBJECT-TYPE
		SYNTAX	Unsigned32
		MAX-ACCESS read-only
		STATUS current
		DESCRIPTION
			"Short messages received from TCP"
	::= { siwtapInstanceEntry	11 }

smscSiwtapSmPstnInvalid OBJECT-TYPE
		SYNTAX	Unsigned32
		MAX-ACCESS read-only
		STATUS current
		DESCRIPTION
			"Received invalid short messages from PSTN"
	::= { siwtapInstanceEntry	12 }

smscSiwtapSmX25Invalid OBJECT-TYPE
		SYNTAX	Unsigned32
		MAX-ACCESS read-only
		STATUS current
		DESCRIPTION
			"Received invalid short messages from X25"
	::= { siwtapInstanceEntry	13 }

smscSiwtapSmTcpInvalid OBJECT-TYPE
		SYNTAX	Unsigned32
		MAX-ACCESS read-only
		STATUS current
		DESCRIPTION
			"Received invalid short messages from TCP"
	::= { siwtapInstanceEntry	14 }

smscSiwtapLengthSmInPstn OBJECT-TYPE
		SYNTAX	Unsigned32
		MAX-ACCESS read-only
		STATUS current
		DESCRIPTION
			"Accumulated length of short messages from PSTN"
	::= { siwtapInstanceEntry	15 }

smscSiwtapLengthSmInX25 OBJECT-TYPE
		SYNTAX	Unsigned32
		MAX-ACCESS read-only
		STATUS current
		DESCRIPTION
			"Accumulated length of short messages from X25"
	::= { siwtapInstanceEntry	16 }

smscSiwtapLengthSmInTcp OBJECT-TYPE
		SYNTAX	Unsigned32
		MAX-ACCESS read-only
		STATUS current
		DESCRIPTION
			"Accumulated length of short messages from TCP"
	::= { siwtapInstanceEntry	17 }

smscSiwtapQelemUsed OBJECT-TYPE
		SYNTAX	Unsigned32
		MAX-ACCESS read-only
		STATUS current
		DESCRIPTION
			"Number of elements in internal queues"
	::= { siwtapInstanceEntry	18 }

smscSiwtapQelemInProcqueue OBJECT-TYPE
		SYNTAX	Unsigned32
		MAX-ACCESS read-only
		STATUS current
		DESCRIPTION
			"Number of elements used in process queue"
	::= { siwtapInstanceEntry	19 }

smscSiwtapQelemInExpqueue OBJECT-TYPE
		SYNTAX	Unsigned32
		MAX-ACCESS read-only
		STATUS current
		DESCRIPTION
			"Number of elements used in expedited queue"
	::= { siwtapInstanceEntry	20 }

smscSiwtapNrTimersRunning OBJECT-TYPE
		SYNTAX	Unsigned32
		MAX-ACCESS read-only
		STATUS current
		DESCRIPTION
			"Total number of timers running"
	::= { siwtapInstanceEntry	21 }

smscSiwtapNrSystemTimers OBJECT-TYPE
		SYNTAX	Unsigned32
		MAX-ACCESS read-only
		STATUS current
		DESCRIPTION
			"Number of system timers running"
	::= { siwtapInstanceEntry	22 }

smscSiwtapImiRecallQelem OBJECT-TYPE
		SYNTAX	Unsigned32
		MAX-ACCESS read-only
		STATUS current
		DESCRIPTION
			"Number of IMI recall-queue elements used"
	::= { siwtapInstanceEntry	23 }

smscSiwtapImiRecallQueues OBJECT-TYPE
		SYNTAX	Unsigned32
		MAX-ACCESS read-only
		STATUS current
		DESCRIPTION
			"Number of IMI-recall-queues used"
	::= { siwtapInstanceEntry	24 }

smscSiwtapIdiRecallQelem OBJECT-TYPE
		SYNTAX	Unsigned32
		MAX-ACCESS read-only
		STATUS current
		DESCRIPTION
			"Number of IDI recall-queue elements used"
	::= { siwtapInstanceEntry	25 }

smscSiwtapIdiRecallQueues OBJECT-TYPE
		SYNTAX	Unsigned32
		MAX-ACCESS read-only
		STATUS current
		DESCRIPTION
			"Number of IDI recall-queues used"
	::= { siwtapInstanceEntry	26 }

smscSiwtapIosRecallQelem OBJECT-TYPE
		SYNTAX	Unsigned32
		MAX-ACCESS read-only
		STATUS current
		DESCRIPTION
			"Number of IOS recall-queue elements used"
	::= { siwtapInstanceEntry	27 }

smscSiwtapIosRecallQueues OBJECT-TYPE
		SYNTAX	Unsigned32
		MAX-ACCESS read-only
		STATUS current
		DESCRIPTION
			"Number of IOS recall-queues used"
	::= { siwtapInstanceEntry	28 }

smscSiwtapLogRecallQelem OBJECT-TYPE
		SYNTAX	Unsigned32
		MAX-ACCESS read-only
		STATUS current
		DESCRIPTION
			"Number of LOG recall-queue elements used"
	::= { siwtapInstanceEntry	29 }

smscSiwtapLogRecallQueues OBJECT-TYPE
		SYNTAX	Unsigned32
		MAX-ACCESS read-only
		STATUS current
		DESCRIPTION
			"Number of LOG recall-queues used"
	::= { siwtapInstanceEntry	30 }

smscSiwtapTrcreqDiscarded OBJECT-TYPE
		SYNTAX	Unsigned32
		MAX-ACCESS read-only
		STATUS current
		DESCRIPTION
			"Number of trace requests discarded"
	::= { siwtapInstanceEntry	31 }

smscSiwtapSmPstnTruncated OBJECT-TYPE
		SYNTAX	Unsigned32
		MAX-ACCESS read-only
		STATUS current
		DESCRIPTION
			"Truncated short messages from PSTN"
	::= { siwtapInstanceEntry	32 }

smscSiwtapSmX25Truncated OBJECT-TYPE
		SYNTAX	Unsigned32
		MAX-ACCESS read-only
		STATUS current
		DESCRIPTION
			"Truncated short messages from X25"
	::= { siwtapInstanceEntry	33 }

smscSiwtapSmTcpTruncated OBJECT-TYPE
		SYNTAX	Unsigned32
		MAX-ACCESS read-only
		STATUS current
		DESCRIPTION
			"Truncated short messages from TCP"
	::= { siwtapInstanceEntry	34 }



-- end of SIWTAP description.
-- --------------------------------------


-- --------------------------------------
-- Class SIWSMPP
-- 
smscSiwsmpp OBJECT-TYPE
	SYNTAX  SEQUENCE OF SiwsmppInstanceEntry
	MAX-ACCESS  not-accessible
	STATUS  current
	DESCRIPTION
		"Mapping table for SMSC SIWSMPP entities."
   ::= { smscClassSiw   9  }

siwsmppInstanceEntry  OBJECT-TYPE
	SYNTAX SiwsmppInstanceEntry
	MAX-ACCESS  not-accessible
	STATUS  current
	DESCRIPTION
		"An entry (row) in the entityInstanceTable."
	INDEX { IMPLIED smscSiwsmppName }
   ::= { smscSiwsmpp 1 }

SiwsmppInstanceEntry ::= SEQUENCE {
		smscSiwsmppName     DisplayString,
		smscSiwsmppState   INTEGER,
		smscSiwsmppLastupdate   TimeTicks,
		smscSiwsmppNode	   DisplayString, 
		smscSiwsmppMsgReceived	 Unsigned32, 
		smscSiwsmppMsgRejected	 Unsigned32, 
		smscSiwsmppMsgTransmitted	 Unsigned32, 
		smscSiwsmppMsgFailed	 Unsigned32, 
		smscSiwsmppQelemUsed	 Unsigned32, 
		smscSiwsmppQelemInProcqueue	 Unsigned32, 
		smscSiwsmppQelemInExpqueue	 Unsigned32, 
		smscSiwsmppNrTimersRunning	 Unsigned32, 
		smscSiwsmppNrSystemTimers	 Unsigned32, 
		smscSiwsmppImiRecallQelem	 Unsigned32, 
		smscSiwsmppImiRecallQueues	 Unsigned32, 
		smscSiwsmppIdiRecallQelem	 Unsigned32, 
		smscSiwsmppIdiRecallQueues	 Unsigned32, 
		smscSiwsmppIosRecallQelem	 Unsigned32, 
		smscSiwsmppIosRecallQueues	 Unsigned32, 
		smscSiwsmppLogRecallQelem	 Unsigned32, 
		smscSiwsmppLogRecallQueues	 Unsigned32, 
		smscSiwsmppTrcreqDiscarded	 Unsigned32, 
		smscSiwsmppDummyStatistic	 Unsigned32, 
		smscSiwsmppRcvAddSub	 Unsigned32, 
		smscSiwsmppErrAddSub	 Unsigned32, 
		smscSiwsmppOkAddSub	 Unsigned32, 
		smscSiwsmppRcvModSub	 Unsigned32, 
		smscSiwsmppErrModSub	 Unsigned32, 
		smscSiwsmppOkModSub	 Unsigned32, 
		smscSiwsmppRcvDelSub	 Unsigned32, 
		smscSiwsmppErrDelSub	 Unsigned32, 
		smscSiwsmppOkDelSub	 Unsigned32, 
		smscSiwsmppRcvEnqSub	 Unsigned32, 
		smscSiwsmppErrEnqSub	 Unsigned32, 
		smscSiwsmppOkEnqSub	 Unsigned32, 
		smscSiwsmppAdtUsedMemory	 Unsigned32, 
		smscSiwsmppConSetupTotAtt	 Unsigned32, 
		smscSiwsmppConSetupTotRej	 Unsigned32, 
		smscSiwsmppConSetupRejRes	 Unsigned32, 
		smscSiwsmppSesSetupTotAtt	 Unsigned32, 
		smscSiwsmppSesSetupTotRej	 Unsigned32, 
		smscSiwsmppSesSetupRejRes	 Unsigned32, 
		smscSiwsmppSesSetupRejPswd	 Unsigned32, 
		smscSiwsmppSesSetupRejNreg	 Unsigned32, 
		smscSiwsmppSesSetupRejCnadr	 Unsigned32, 
		smscSiwsmppSesSetupRejMaxses	 Unsigned32, 
		smscSiwsmppTlvProfRejMsg	 Unsigned32
	}

smscSiwsmppName  OBJECT-TYPE
	SYNTAX  DisplayString
	MAX-ACCESS  read-only
	STATUS   current
	DESCRIPTION
		"Identifies the name of the entity."
   ::= {siwsmppInstanceEntry 1 }

smscSiwsmppState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { siwsmppInstanceEntry 2 }


smscSiwsmppLastupdate OBJECT-TYPE
		SYNTAX	TimeTicks
		MAX-ACCESS read-only
		STATUS current
		DESCRIPTION
			"Value which reflects the last time the entities fields have been updated"
	::= { siwsmppInstanceEntry	3 }

smscSiwsmppNode  OBJECT-TYPE
	SYNTAX  DisplayString
	MAX-ACCESS  read-only
	STATUS   current
	DESCRIPTION
		"Identifies the node the entity is running on."
   ::= {siwsmppInstanceEntry 4 }

smscSiwsmppMsgReceived OBJECT-TYPE
		SYNTAX	Unsigned32
		MAX-ACCESS read-only
		STATUS current
		DESCRIPTION
			"Received messages"
	::= { siwsmppInstanceEntry	5 }

smscSiwsmppMsgRejected OBJECT-TYPE
		SYNTAX	Unsigned32
		MAX-ACCESS read-only
		STATUS current
		DESCRIPTION
			"Received messages and rejected"
	::= { siwsmppInstanceEntry	6 }

smscSiwsmppMsgTransmitted OBJECT-TYPE
		SYNTAX	Unsigned32
		MAX-ACCESS read-only
		STATUS current
		DESCRIPTION
			"Transmitted messages"
	::= { siwsmppInstanceEntry	7 }

smscSiwsmppMsgFailed OBJECT-TYPE
		SYNTAX	Unsigned32
		MAX-ACCESS read-only
		STATUS current
		DESCRIPTION
			"Messages that failed on sending"
	::= { siwsmppInstanceEntry	8 }

smscSiwsmppQelemUsed OBJECT-TYPE
		SYNTAX	Unsigned32
		MAX-ACCESS read-only
		STATUS current
		DESCRIPTION
			"Number of elements in internal queues"
	::= { siwsmppInstanceEntry	9 }

smscSiwsmppQelemInProcqueue OBJECT-TYPE
		SYNTAX	Unsigned32
		MAX-ACCESS read-only
		STATUS current
		DESCRIPTION
			"Number of elements used in process queue"
	::= { siwsmppInstanceEntry	10 }

smscSiwsmppQelemInExpqueue OBJECT-TYPE
		SYNTAX	Unsigned32
		MAX-ACCESS read-only
		STATUS current
		DESCRIPTION
			"Number of elements used in expedited queue"
	::= { siwsmppInstanceEntry	11 }

smscSiwsmppNrTimersRunning OBJECT-TYPE
		SYNTAX	Unsigned32
		MAX-ACCESS read-only
		STATUS current
		DESCRIPTION
			"Total number of timers running"
	::= { siwsmppInstanceEntry	12 }

smscSiwsmppNrSystemTimers OBJECT-TYPE
		SYNTAX	Unsigned32
		MAX-ACCESS read-only
		STATUS current
		DESCRIPTION
			"Number of system timers running"
	::= { siwsmppInstanceEntry	13 }

smscSiwsmppImiRecallQelem OBJECT-TYPE
		SYNTAX	Unsigned32
		MAX-ACCESS read-only
		STATUS current
		DESCRIPTION
			"Number of IMI recall-queue elements used"
	::= { siwsmppInstanceEntry	14 }

smscSiwsmppImiRecallQueues OBJECT-TYPE
		SYNTAX	Unsigned32
		MAX-ACCESS read-only
		STATUS current
		DESCRIPTION
			"Number of IMI-recall-queues used"
	::= { siwsmppInstanceEntry	15 }

smscSiwsmppIdiRecallQelem OBJECT-TYPE
		SYNTAX	Unsigned32
		MAX-ACCESS read-only
		STATUS current
		DESCRIPTION
			"Number of IDI recall-queue elements used"
	::= { siwsmppInstanceEntry	16 }

smscSiwsmppIdiRecallQueues OBJECT-TYPE
		SYNTAX	Unsigned32
		MAX-ACCESS read-only
		STATUS current
		DESCRIPTION
			"Number of IDI recall-queues used"
	::= { siwsmppInstanceEntry	17 }

smscSiwsmppIosRecallQelem OBJECT-TYPE
		SYNTAX	Unsigned32
		MAX-ACCESS read-only
		STATUS current
		DESCRIPTION
			"Number of IOS recall-queue elements used"
	::= { siwsmppInstanceEntry	18 }

smscSiwsmppIosRecallQueues OBJECT-TYPE
		SYNTAX	Unsigned32
		MAX-ACCESS read-only
		STATUS current
		DESCRIPTION
			"Number of IOS recall-queues used"
	::= { siwsmppInstanceEntry	19 }

smscSiwsmppLogRecallQelem OBJECT-TYPE
		SYNTAX	Unsigned32
		MAX-ACCESS read-only
		STATUS current
		DESCRIPTION
			"Number of LOG recall-queue elements used"
	::= { siwsmppInstanceEntry	20 }

smscSiwsmppLogRecallQueues OBJECT-TYPE
		SYNTAX	Unsigned32
		MAX-ACCESS read-only
		STATUS current
		DESCRIPTION
			"Number of LOG recall-queues used"
	::= { siwsmppInstanceEntry	21 }

smscSiwsmppTrcreqDiscarded OBJECT-TYPE
		SYNTAX	Unsigned32
		MAX-ACCESS read-only
		STATUS current
		DESCRIPTION
			"Number of trace requests discarded"
	::= { siwsmppInstanceEntry	22 }

smscSiwsmppDummyStatistic OBJECT-TYPE
		SYNTAX	Unsigned32
		MAX-ACCESS read-only
		STATUS current
		DESCRIPTION
			"No statistical counters"
	::= { siwsmppInstanceEntry	23 }

smscSiwsmppRcvAddSub OBJECT-TYPE
		SYNTAX	Unsigned32
		MAX-ACCESS read-only
		STATUS current
		DESCRIPTION
			"Number of received ADD_SUB commands"
	::= { siwsmppInstanceEntry	24 }

smscSiwsmppErrAddSub OBJECT-TYPE
		SYNTAX	Unsigned32
		MAX-ACCESS read-only
		STATUS current
		DESCRIPTION
			"Number of failed ADD_SUB commands"
	::= { siwsmppInstanceEntry	25 }

smscSiwsmppOkAddSub OBJECT-TYPE
		SYNTAX	Unsigned32
		MAX-ACCESS read-only
		STATUS current
		DESCRIPTION
			"Number of succeeded ADD_SUB commands"
	::= { siwsmppInstanceEntry	26 }

smscSiwsmppRcvModSub OBJECT-TYPE
		SYNTAX	Unsigned32
		MAX-ACCESS read-only
		STATUS current
		DESCRIPTION
			"Number of received MOD_SUB commands"
	::= { siwsmppInstanceEntry	27 }

smscSiwsmppErrModSub OBJECT-TYPE
		SYNTAX	Unsigned32
		MAX-ACCESS read-only
		STATUS current
		DESCRIPTION
			"Number of failed MOD_SUB commands"
	::= { siwsmppInstanceEntry	28 }

smscSiwsmppOkModSub OBJECT-TYPE
		SYNTAX	Unsigned32
		MAX-ACCESS read-only
		STATUS current
		DESCRIPTION
			"Number of succeeded MOD_SUB commands"
	::= { siwsmppInstanceEntry	29 }

smscSiwsmppRcvDelSub OBJECT-TYPE
		SYNTAX	Unsigned32
		MAX-ACCESS read-only
		STATUS current
		DESCRIPTION
			"Number of received DEL_SUB commands"
	::= { siwsmppInstanceEntry	30 }

smscSiwsmppErrDelSub OBJECT-TYPE
		SYNTAX	Unsigned32
		MAX-ACCESS read-only
		STATUS current
		DESCRIPTION
			"Number of failed DEL_SUB commands"
	::= { siwsmppInstanceEntry	31 }

smscSiwsmppOkDelSub OBJECT-TYPE
		SYNTAX	Unsigned32
		MAX-ACCESS read-only
		STATUS current
		DESCRIPTION
			"Number of succeeded DEL_SUB commands"
	::= { siwsmppInstanceEntry	32 }

smscSiwsmppRcvEnqSub OBJECT-TYPE
		SYNTAX	Unsigned32
		MAX-ACCESS read-only
		STATUS current
		DESCRIPTION
			"Number of received ENQUIRE_SUB commands"
	::= { siwsmppInstanceEntry	33 }

smscSiwsmppErrEnqSub OBJECT-TYPE
		SYNTAX	Unsigned32
		MAX-ACCESS read-only
		STATUS current
		DESCRIPTION
			"Number of failed ENQUIRE_SUB commands"
	::= { siwsmppInstanceEntry	34 }

smscSiwsmppOkEnqSub OBJECT-TYPE
		SYNTAX	Unsigned32
		MAX-ACCESS read-only
		STATUS current
		DESCRIPTION
			"Number of succeeded ENQUIRE_SUB commands"
	::= { siwsmppInstanceEntry	35 }

smscSiwsmppAdtUsedMemory OBJECT-TYPE
		SYNTAX	Unsigned32
		MAX-ACCESS read-only
		STATUS current
		DESCRIPTION
			"Memory blocks used by ADT tables of SIWSMPP."
	::= { siwsmppInstanceEntry	36 }

smscSiwsmppConSetupTotAtt OBJECT-TYPE
		SYNTAX	Unsigned32
		MAX-ACCESS read-only
		STATUS current
		DESCRIPTION
			"Total number of connection setup attempts"
	::= { siwsmppInstanceEntry	37 }

smscSiwsmppConSetupTotRej OBJECT-TYPE
		SYNTAX	Unsigned32
		MAX-ACCESS read-only
		STATUS current
		DESCRIPTION
			"Total number of rejected connections"
	::= { siwsmppInstanceEntry	38 }

smscSiwsmppConSetupRejRes OBJECT-TYPE
		SYNTAX	Unsigned32
		MAX-ACCESS read-only
		STATUS current
		DESCRIPTION
			"Number of rejected connections - resource problem"
	::= { siwsmppInstanceEntry	39 }

smscSiwsmppSesSetupTotAtt OBJECT-TYPE
		SYNTAX	Unsigned32
		MAX-ACCESS read-only
		STATUS current
		DESCRIPTION
			"Total number of session setup attempts"
	::= { siwsmppInstanceEntry	40 }

smscSiwsmppSesSetupTotRej OBJECT-TYPE
		SYNTAX	Unsigned32
		MAX-ACCESS read-only
		STATUS current
		DESCRIPTION
			"Total number of rejected session setups"
	::= { siwsmppInstanceEntry	41 }

smscSiwsmppSesSetupRejRes OBJECT-TYPE
		SYNTAX	Unsigned32
		MAX-ACCESS read-only
		STATUS current
		DESCRIPTION
			"Number of rejected sessions - resource problem"
	::= { siwsmppInstanceEntry	42 }

smscSiwsmppSesSetupRejPswd OBJECT-TYPE
		SYNTAX	Unsigned32
		MAX-ACCESS read-only
		STATUS current
		DESCRIPTION
			"Number of rejected sessions - invalid password"
	::= { siwsmppInstanceEntry	43 }

smscSiwsmppSesSetupRejNreg OBJECT-TYPE
		SYNTAX	Unsigned32
		MAX-ACCESS read-only
		STATUS current
		DESCRIPTION
			"Number of rejected sessions - LA not registered"
	::= { siwsmppInstanceEntry	44 }

smscSiwsmppSesSetupRejCnadr OBJECT-TYPE
		SYNTAX	Unsigned32
		MAX-ACCESS read-only
		STATUS current
		DESCRIPTION
			"Number of rejected sessions - wrong connect addr"
	::= { siwsmppInstanceEntry	45 }

smscSiwsmppSesSetupRejMaxses OBJECT-TYPE
		SYNTAX	Unsigned32
		MAX-ACCESS read-only
		STATUS current
		DESCRIPTION
			"Number of rejected sessions - maxsession limit"
	::= { siwsmppInstanceEntry	46 }

smscSiwsmppTlvProfRejMsg OBJECT-TYPE
		SYNTAX	Unsigned32
		MAX-ACCESS read-only
		STATUS current
		DESCRIPTION
			"Number of rejected messages - TLV-Profiles"
	::= { siwsmppInstanceEntry	47 }



-- end of SIWSMPP description.
-- --------------------------------------


-- --------------------------------------
-- Class SIWOIS
-- 
smscSiwois OBJECT-TYPE
	SYNTAX  SEQUENCE OF SiwoisInstanceEntry
	MAX-ACCESS  not-accessible
	STATUS  current
	DESCRIPTION
		"Mapping table for SMSC SIWOIS entities."
   ::= { smscClassSiw   10  }

siwoisInstanceEntry  OBJECT-TYPE
	SYNTAX SiwoisInstanceEntry
	MAX-ACCESS  not-accessible
	STATUS  current
	DESCRIPTION
		"An entry (row) in the entityInstanceTable."
	INDEX { IMPLIED smscSiwoisName }
   ::= { smscSiwois 1 }

SiwoisInstanceEntry ::= SEQUENCE {
		smscSiwoisName     DisplayString,
		smscSiwoisState   INTEGER,
		smscSiwoisLastupdate   TimeTicks,
		smscSiwoisNode	   DisplayString, 
		smscSiwoisMsgReceived	 Unsigned32, 
		smscSiwoisMsgRejected	 Unsigned32, 
		smscSiwoisMsgTransmitted	 Unsigned32, 
		smscSiwoisMsgFailed	 Unsigned32, 
		smscSiwoisSessionsPending	 Unsigned32, 
		smscSiwoisQelemUsed	 Unsigned32, 
		smscSiwoisQelemInProcqueue	 Unsigned32, 
		smscSiwoisQelemInExpqueue	 Unsigned32, 
		smscSiwoisNrTimersRunning	 Unsigned32, 
		smscSiwoisNrSystemTimers	 Unsigned32, 
		smscSiwoisImiRecallQelem	 Unsigned32, 
		smscSiwoisImiRecallQueues	 Unsigned32, 
		smscSiwoisIdiRecallQelem	 Unsigned32, 
		smscSiwoisIdiRecallQueues	 Unsigned32, 
		smscSiwoisIosRecallQelem	 Unsigned32, 
		smscSiwoisIosRecallQueues	 Unsigned32, 
		smscSiwoisLogRecallQelem	 Unsigned32, 
		smscSiwoisLogRecallQueues	 Unsigned32, 
		smscSiwoisTrcreqDiscarded	 Unsigned32, 
		smscSiwoisConTcpRef	 Unsigned32, 
		smscSiwoisConX25Ref	 Unsigned32, 
		smscSiwoisSmTcpReceived	 Unsigned32, 
		smscSiwoisSmX25Received	 Unsigned32, 
		smscSiwoisSmTcpRejected	 Unsigned32, 
		smscSiwoisSmX25Rejected	 Unsigned32, 
		smscSiwoisNotifTcpTransmitted	 Unsigned32, 
		smscSiwoisNotifX25Transmitted	 Unsigned32, 
		smscSiwoisSmTcpTransmitted	 Unsigned32, 
		smscSiwoisSmX25Transmitted	 Unsigned32, 
		smscSiwoisSmTcpFailed	 Unsigned32, 
		smscSiwoisSmX25Failed	 Unsigned32, 
		smscSiwoisNotifTcpFailed	 Unsigned32, 
		smscSiwoisNotifX25Failed	 Unsigned32, 
		smscSiwoisTimeoutErrors	 Unsigned32, 
		smscSiwoisProtocolErrors	 Unsigned32, 
		smscSiwoisResourceErrors	 Unsigned32
	}

smscSiwoisName  OBJECT-TYPE
	SYNTAX  DisplayString
	MAX-ACCESS  read-only
	STATUS   current
	DESCRIPTION
		"Identifies the name of the entity."
   ::= {siwoisInstanceEntry 1 }

smscSiwoisState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { siwoisInstanceEntry 2 }


smscSiwoisLastupdate OBJECT-TYPE
		SYNTAX	TimeTicks
		MAX-ACCESS read-only
		STATUS current
		DESCRIPTION
			"Value which reflects the last time the entities fields have been updated"
	::= { siwoisInstanceEntry	3 }

smscSiwoisNode  OBJECT-TYPE
	SYNTAX  DisplayString
	MAX-ACCESS  read-only
	STATUS   current
	DESCRIPTION
		"Identifies the node the entity is running on."
   ::= {siwoisInstanceEntry 4 }

smscSiwoisMsgReceived OBJECT-TYPE
		SYNTAX	Unsigned32
		MAX-ACCESS read-only
		STATUS current
		DESCRIPTION
			"Received messages"
	::= { siwoisInstanceEntry	5 }

smscSiwoisMsgRejected OBJECT-TYPE
		SYNTAX	Unsigned32
		MAX-ACCESS read-only
		STATUS current
		DESCRIPTION
			"Received messages and rejected"
	::= { siwoisInstanceEntry	6 }

smscSiwoisMsgTransmitted OBJECT-TYPE
		SYNTAX	Unsigned32
		MAX-ACCESS read-only
		STATUS current
		DESCRIPTION
			"Transmitted messages"
	::= { siwoisInstanceEntry	7 }

smscSiwoisMsgFailed OBJECT-TYPE
		SYNTAX	Unsigned32
		MAX-ACCESS read-only
		STATUS current
		DESCRIPTION
			"Messages that failed on sending"
	::= { siwoisInstanceEntry	8 }

smscSiwoisSessionsPending OBJECT-TYPE
		SYNTAX	Unsigned32
		MAX-ACCESS read-only
		STATUS current
		DESCRIPTION
			"Number of sessions (currently) pending"
	::= { siwoisInstanceEntry	9 }

smscSiwoisQelemUsed OBJECT-TYPE
		SYNTAX	Unsigned32
		MAX-ACCESS read-only
		STATUS current
		DESCRIPTION
			"Number of elements in internal queues"
	::= { siwoisInstanceEntry	10 }

smscSiwoisQelemInProcqueue OBJECT-TYPE
		SYNTAX	Unsigned32
		MAX-ACCESS read-only
		STATUS current
		DESCRIPTION
			"Number of elements used in process queue"
	::= { siwoisInstanceEntry	11 }

smscSiwoisQelemInExpqueue OBJECT-TYPE
		SYNTAX	Unsigned32
		MAX-ACCESS read-only
		STATUS current
		DESCRIPTION
			"Number of elements used in expedited queue"
	::= { siwoisInstanceEntry	12 }

smscSiwoisNrTimersRunning OBJECT-TYPE
		SYNTAX	Unsigned32
		MAX-ACCESS read-only
		STATUS current
		DESCRIPTION
			"Total number of timers running"
	::= { siwoisInstanceEntry	13 }

smscSiwoisNrSystemTimers OBJECT-TYPE
		SYNTAX	Unsigned32
		MAX-ACCESS read-only
		STATUS current
		DESCRIPTION
			"Number of system timers running"
	::= { siwoisInstanceEntry	14 }

smscSiwoisImiRecallQelem OBJECT-TYPE
		SYNTAX	Unsigned32
		MAX-ACCESS read-only
		STATUS current
		DESCRIPTION
			"Number of IMI recall-queue elements used"
	::= { siwoisInstanceEntry	15 }

smscSiwoisImiRecallQueues OBJECT-TYPE
		SYNTAX	Unsigned32
		MAX-ACCESS read-only
		STATUS current
		DESCRIPTION
			"Number of IMI-recall-queues used"
	::= { siwoisInstanceEntry	16 }

smscSiwoisIdiRecallQelem OBJECT-TYPE
		SYNTAX	Unsigned32
		MAX-ACCESS read-only
		STATUS current
		DESCRIPTION
			"Number of IDI recall-queue elements used"
	::= { siwoisInstanceEntry	17 }

smscSiwoisIdiRecallQueues OBJECT-TYPE
		SYNTAX	Unsigned32
		MAX-ACCESS read-only
		STATUS current
		DESCRIPTION
			"Number of IDI recall-queues used"
	::= { siwoisInstanceEntry	18 }

smscSiwoisIosRecallQelem OBJECT-TYPE
		SYNTAX	Unsigned32
		MAX-ACCESS read-only
		STATUS current
		DESCRIPTION
			"Number of IOS recall-queue elements used"
	::= { siwoisInstanceEntry	19 }

smscSiwoisIosRecallQueues OBJECT-TYPE
		SYNTAX	Unsigned32
		MAX-ACCESS read-only
		STATUS current
		DESCRIPTION
			"Number of IOS recall-queues used"
	::= { siwoisInstanceEntry	20 }

smscSiwoisLogRecallQelem OBJECT-TYPE
		SYNTAX	Unsigned32
		MAX-ACCESS read-only
		STATUS current
		DESCRIPTION
			"Number of LOG recall-queue elements used"
	::= { siwoisInstanceEntry	21 }

smscSiwoisLogRecallQueues OBJECT-TYPE
		SYNTAX	Unsigned32
		MAX-ACCESS read-only
		STATUS current
		DESCRIPTION
			"Number of LOG recall-queues used"
	::= { siwoisInstanceEntry	22 }

smscSiwoisTrcreqDiscarded OBJECT-TYPE
		SYNTAX	Unsigned32
		MAX-ACCESS read-only
		STATUS current
		DESCRIPTION
			"Number of trace requests discarded"
	::= { siwoisInstanceEntry	23 }

smscSiwoisConTcpRef OBJECT-TYPE
		SYNTAX	Unsigned32
		MAX-ACCESS read-only
		STATUS current
		DESCRIPTION
			"Nr. of refused connections via TCP"
	::= { siwoisInstanceEntry	24 }

smscSiwoisConX25Ref OBJECT-TYPE
		SYNTAX	Unsigned32
		MAX-ACCESS read-only
		STATUS current
		DESCRIPTION
			"Nr. of refused connections via X25"
	::= { siwoisInstanceEntry	25 }

smscSiwoisSmTcpReceived OBJECT-TYPE
		SYNTAX	Unsigned32
		MAX-ACCESS read-only
		STATUS current
		DESCRIPTION
			"Nr. of SME originated SMs via TCP"
	::= { siwoisInstanceEntry	26 }

smscSiwoisSmX25Received OBJECT-TYPE
		SYNTAX	Unsigned32
		MAX-ACCESS read-only
		STATUS current
		DESCRIPTION
			"Nr. of SME originated SMs via X25"
	::= { siwoisInstanceEntry	27 }

smscSiwoisSmTcpRejected OBJECT-TYPE
		SYNTAX	Unsigned32
		MAX-ACCESS read-only
		STATUS current
		DESCRIPTION
			"Tot. nr. of SME orig. SMs via TCP and rejected"
	::= { siwoisInstanceEntry	28 }

smscSiwoisSmX25Rejected OBJECT-TYPE
		SYNTAX	Unsigned32
		MAX-ACCESS read-only
		STATUS current
		DESCRIPTION
			"Tot. nr. of SME orig. SMs via X25 and rejected"
	::= { siwoisInstanceEntry	29 }

smscSiwoisNotifTcpTransmitted OBJECT-TYPE
		SYNTAX	Unsigned32
		MAX-ACCESS read-only
		STATUS current
		DESCRIPTION
			"Nr. of notif. delivery attemps via TCP"
	::= { siwoisInstanceEntry	30 }

smscSiwoisNotifX25Transmitted OBJECT-TYPE
		SYNTAX	Unsigned32
		MAX-ACCESS read-only
		STATUS current
		DESCRIPTION
			"Nr. of notif. delivery attemps via X25"
	::= { siwoisInstanceEntry	31 }

smscSiwoisSmTcpTransmitted OBJECT-TYPE
		SYNTAX	Unsigned32
		MAX-ACCESS read-only
		STATUS current
		DESCRIPTION
			"Nr. of SMs delivery attemps via TCP"
	::= { siwoisInstanceEntry	32 }

smscSiwoisSmX25Transmitted OBJECT-TYPE
		SYNTAX	Unsigned32
		MAX-ACCESS read-only
		STATUS current
		DESCRIPTION
			"Nr. of SMs delivery attemps via X25"
	::= { siwoisInstanceEntry	33 }

smscSiwoisSmTcpFailed OBJECT-TYPE
		SYNTAX	Unsigned32
		MAX-ACCESS read-only
		STATUS current
		DESCRIPTION
			"Nr. of failed SMs delivery attemps via TCP"
	::= { siwoisInstanceEntry	34 }

smscSiwoisSmX25Failed OBJECT-TYPE
		SYNTAX	Unsigned32
		MAX-ACCESS read-only
		STATUS current
		DESCRIPTION
			"Nr. of failed SMs delivery attemps via X25"
	::= { siwoisInstanceEntry	35 }

smscSiwoisNotifTcpFailed OBJECT-TYPE
		SYNTAX	Unsigned32
		MAX-ACCESS read-only
		STATUS current
		DESCRIPTION
			"Nr. of failed notif. delivery attemps via TCP"
	::= { siwoisInstanceEntry	36 }

smscSiwoisNotifX25Failed OBJECT-TYPE
		SYNTAX	Unsigned32
		MAX-ACCESS read-only
		STATUS current
		DESCRIPTION
			"Nr. of failed notif. delivery attemps via X25"
	::= { siwoisInstanceEntry	37 }

smscSiwoisTimeoutErrors OBJECT-TYPE
		SYNTAX	Unsigned32
		MAX-ACCESS read-only
		STATUS current
		DESCRIPTION
			"Tot. nr. of timeouts on IW request"
	::= { siwoisInstanceEntry	38 }

smscSiwoisProtocolErrors OBJECT-TYPE
		SYNTAX	Unsigned32
		MAX-ACCESS read-only
		STATUS current
		DESCRIPTION
			"Tot. nr. of protocol errors"
	::= { siwoisInstanceEntry	39 }

smscSiwoisResourceErrors OBJECT-TYPE
		SYNTAX	Unsigned32
		MAX-ACCESS read-only
		STATUS current
		DESCRIPTION
			"Tot. nr. of resource errors"
	::= { siwoisInstanceEntry	40 }



-- end of SIWOIS description.
-- --------------------------------------


-- --------------------------------------
-- Class SIWCDMA
-- 
smscSiwcdma OBJECT-TYPE
	SYNTAX  SEQUENCE OF SiwcdmaInstanceEntry
	MAX-ACCESS  not-accessible
	STATUS  current
	DESCRIPTION
		"Mapping table for SMSC SIWCDMA entities."
   ::= { smscClassSiw   11  }

siwcdmaInstanceEntry  OBJECT-TYPE
	SYNTAX SiwcdmaInstanceEntry
	MAX-ACCESS  not-accessible
	STATUS  current
	DESCRIPTION
		"An entry (row) in the entityInstanceTable."
	INDEX { IMPLIED smscSiwcdmaName }
   ::= { smscSiwcdma 1 }

SiwcdmaInstanceEntry ::= SEQUENCE {
		smscSiwcdmaName     DisplayString,
		smscSiwcdmaState   INTEGER,
		smscSiwcdmaLastupdate   TimeTicks,
		smscSiwcdmaNode	   DisplayString, 
		smscSiwcdmaSmInvalid	 Unsigned32, 
		smscSiwcdmaMsgReceived	 Unsigned32, 
		smscSiwcdmaMsgRejected	 Unsigned32, 
		smscSiwcdmaMsgTransmitted	 Unsigned32, 
		smscSiwcdmaSmReceived	 Unsigned32, 
		smscSiwcdmaMsgFailed	 Unsigned32, 
		smscSiwcdmaNotifbRequested	 Unsigned32, 
		smscSiwcdmaNotifdRequested	 Unsigned32, 
		smscSiwcdmaNotifndRequested	 Unsigned32, 
		smscSiwcdmaLengthSmInPlmn	 Unsigned32, 
		smscSiwcdmaQelemUsed	 Unsigned32, 
		smscSiwcdmaQelemInProcqueue	 Unsigned32, 
		smscSiwcdmaQelemInExpqueue	 Unsigned32, 
		smscSiwcdmaNrTimersRunning	 Unsigned32, 
		smscSiwcdmaNrSystemTimers	 Unsigned32, 
		smscSiwcdmaImiRecallQelem	 Unsigned32, 
		smscSiwcdmaImiRecallQueues	 Unsigned32, 
		smscSiwcdmaIdiRecallQelem	 Unsigned32, 
		smscSiwcdmaIdiRecallQueues	 Unsigned32, 
		smscSiwcdmaIosRecallQelem	 Unsigned32, 
		smscSiwcdmaIosRecallQueues	 Unsigned32, 
		smscSiwcdmaLogRecallQelem	 Unsigned32, 
		smscSiwcdmaLogRecallQueues	 Unsigned32, 
		smscSiwcdmaTrcreqDiscarded	 Unsigned32, 
		smscSiwcdmaSmsSubmitAccepted	 Unsigned32, 
		smscSiwcdmaSmsSubmitRejected	 Unsigned32, 
		smscSiwcdmaSmsDelackAccepted	 Unsigned32, 
		smscSiwcdmaSmsDelackRejected	 Unsigned32, 
		smscSiwcdmaSmsManackAccepted	 Unsigned32, 
		smscSiwcdmaSmsManackRejected	 Unsigned32, 
		smscSiwcdmaSessionsPending	 Unsigned32, 
		smscSiwcdmaAdtUsedMemory	 Unsigned32, 
		smscSiwcdmaSmResourceFail	 Unsigned32, 
		smscSiwcdmaSmsReadackAccepted	 Unsigned32, 
		smscSiwcdmaSmsReadackRejected	 Unsigned32, 
		smscSiwcdmaSmsCancelAccepted	 Unsigned32, 
		smscSiwcdmaSmsCancelRejected	 Unsigned32
	}

smscSiwcdmaName  OBJECT-TYPE
	SYNTAX  DisplayString
	MAX-ACCESS  read-only
	STATUS   current
	DESCRIPTION
		"Identifies the name of the entity."
   ::= {siwcdmaInstanceEntry 1 }

smscSiwcdmaState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { siwcdmaInstanceEntry 2 }


smscSiwcdmaLastupdate OBJECT-TYPE
		SYNTAX	TimeTicks
		MAX-ACCESS read-only
		STATUS current
		DESCRIPTION
			"Value which reflects the last time the entities fields have been updated"
	::= { siwcdmaInstanceEntry	3 }

smscSiwcdmaNode  OBJECT-TYPE
	SYNTAX  DisplayString
	MAX-ACCESS  read-only
	STATUS   current
	DESCRIPTION
		"Identifies the node the entity is running on."
   ::= {siwcdmaInstanceEntry 4 }

smscSiwcdmaSmInvalid OBJECT-TYPE
		SYNTAX	Unsigned32
		MAX-ACCESS read-only
		STATUS current
		DESCRIPTION
			"Received invalid short messages"
	::= { siwcdmaInstanceEntry	5 }

smscSiwcdmaMsgReceived OBJECT-TYPE
		SYNTAX	Unsigned32
		MAX-ACCESS read-only
		STATUS current
		DESCRIPTION
			"Received messages"
	::= { siwcdmaInstanceEntry	6 }

smscSiwcdmaMsgRejected OBJECT-TYPE
		SYNTAX	Unsigned32
		MAX-ACCESS read-only
		STATUS current
		DESCRIPTION
			"Received messages and rejected"
	::= { siwcdmaInstanceEntry	7 }

smscSiwcdmaMsgTransmitted OBJECT-TYPE
		SYNTAX	Unsigned32
		MAX-ACCESS read-only
		STATUS current
		DESCRIPTION
			"Transmitted messages"
	::= { siwcdmaInstanceEntry	8 }

smscSiwcdmaSmReceived OBJECT-TYPE
		SYNTAX	Unsigned32
		MAX-ACCESS read-only
		STATUS current
		DESCRIPTION
			"Received short messages"
	::= { siwcdmaInstanceEntry	9 }

smscSiwcdmaMsgFailed OBJECT-TYPE
		SYNTAX	Unsigned32
		MAX-ACCESS read-only
		STATUS current
		DESCRIPTION
			"Messages that failed on sending"
	::= { siwcdmaInstanceEntry	10 }

smscSiwcdmaNotifbRequested OBJECT-TYPE
		SYNTAX	Unsigned32
		MAX-ACCESS read-only
		STATUS current
		DESCRIPTION
			"Requested buffered message notifications"
	::= { siwcdmaInstanceEntry	11 }

smscSiwcdmaNotifdRequested OBJECT-TYPE
		SYNTAX	Unsigned32
		MAX-ACCESS read-only
		STATUS current
		DESCRIPTION
			"Requested delivery notifications"
	::= { siwcdmaInstanceEntry	12 }

smscSiwcdmaNotifndRequested OBJECT-TYPE
		SYNTAX	Unsigned32
		MAX-ACCESS read-only
		STATUS current
		DESCRIPTION
			"Requested non-delivery notifications"
	::= { siwcdmaInstanceEntry	13 }

smscSiwcdmaLengthSmInPlmn OBJECT-TYPE
		SYNTAX	Unsigned32
		MAX-ACCESS read-only
		STATUS current
		DESCRIPTION
			"Accumulated length of short messages via PLMN"
	::= { siwcdmaInstanceEntry	14 }

smscSiwcdmaQelemUsed OBJECT-TYPE
		SYNTAX	Unsigned32
		MAX-ACCESS read-only
		STATUS current
		DESCRIPTION
			"Number of elements in internal queues"
	::= { siwcdmaInstanceEntry	15 }

smscSiwcdmaQelemInProcqueue OBJECT-TYPE
		SYNTAX	Unsigned32
		MAX-ACCESS read-only
		STATUS current
		DESCRIPTION
			"Number of elements used in process queue"
	::= { siwcdmaInstanceEntry	16 }

smscSiwcdmaQelemInExpqueue OBJECT-TYPE
		SYNTAX	Unsigned32
		MAX-ACCESS read-only
		STATUS current
		DESCRIPTION
			"Number of elements used in expedited queue"
	::= { siwcdmaInstanceEntry	17 }

smscSiwcdmaNrTimersRunning OBJECT-TYPE
		SYNTAX	Unsigned32
		MAX-ACCESS read-only
		STATUS current
		DESCRIPTION
			"Total number of timers running"
	::= { siwcdmaInstanceEntry	18 }

smscSiwcdmaNrSystemTimers OBJECT-TYPE
		SYNTAX	Unsigned32
		MAX-ACCESS read-only
		STATUS current
		DESCRIPTION
			"Number of system timers running"
	::= { siwcdmaInstanceEntry	19 }

smscSiwcdmaImiRecallQelem OBJECT-TYPE
		SYNTAX	Unsigned32
		MAX-ACCESS read-only
		STATUS current
		DESCRIPTION
			"Number of IMI recall-queue elements used"
	::= { siwcdmaInstanceEntry	20 }

smscSiwcdmaImiRecallQueues OBJECT-TYPE
		SYNTAX	Unsigned32
		MAX-ACCESS read-only
		STATUS current
		DESCRIPTION
			"Number of IMI-recall-queues used"
	::= { siwcdmaInstanceEntry	21 }

smscSiwcdmaIdiRecallQelem OBJECT-TYPE
		SYNTAX	Unsigned32
		MAX-ACCESS read-only
		STATUS current
		DESCRIPTION
			"Number of IDI recall-queue elements used"
	::= { siwcdmaInstanceEntry	22 }

smscSiwcdmaIdiRecallQueues OBJECT-TYPE
		SYNTAX	Unsigned32
		MAX-ACCESS read-only
		STATUS current
		DESCRIPTION
			"Number of IDI recall-queues used"
	::= { siwcdmaInstanceEntry	23 }

smscSiwcdmaIosRecallQelem OBJECT-TYPE
		SYNTAX	Unsigned32
		MAX-ACCESS read-only
		STATUS current
		DESCRIPTION
			"Number of IOS recall-queue elements used"
	::= { siwcdmaInstanceEntry	24 }

smscSiwcdmaIosRecallQueues OBJECT-TYPE
		SYNTAX	Unsigned32
		MAX-ACCESS read-only
		STATUS current
		DESCRIPTION
			"Number of IOS recall-queues used"
	::= { siwcdmaInstanceEntry	25 }

smscSiwcdmaLogRecallQelem OBJECT-TYPE
		SYNTAX	Unsigned32
		MAX-ACCESS read-only
		STATUS current
		DESCRIPTION
			"Number of LOG recall-queue elements used"
	::= { siwcdmaInstanceEntry	26 }

smscSiwcdmaLogRecallQueues OBJECT-TYPE
		SYNTAX	Unsigned32
		MAX-ACCESS read-only
		STATUS current
		DESCRIPTION
			"Number of LOG recall-queues used"
	::= { siwcdmaInstanceEntry	27 }

smscSiwcdmaTrcreqDiscarded OBJECT-TYPE
		SYNTAX	Unsigned32
		MAX-ACCESS read-only
		STATUS current
		DESCRIPTION
			"Number of trace requests discarded"
	::= { siwcdmaInstanceEntry	28 }

smscSiwcdmaSmsSubmitAccepted OBJECT-TYPE
		SYNTAX	Unsigned32
		MAX-ACCESS read-only
		STATUS current
		DESCRIPTION
			"Number of SMS SUBMIT messages accepted"
	::= { siwcdmaInstanceEntry	29 }

smscSiwcdmaSmsSubmitRejected OBJECT-TYPE
		SYNTAX	Unsigned32
		MAX-ACCESS read-only
		STATUS current
		DESCRIPTION
			"Number of SMS SUBMIT messages rejected"
	::= { siwcdmaInstanceEntry	30 }

smscSiwcdmaSmsDelackAccepted OBJECT-TYPE
		SYNTAX	Unsigned32
		MAX-ACCESS read-only
		STATUS current
		DESCRIPTION
			"Number of SMS DELIVERY ACK messages accepted"
	::= { siwcdmaInstanceEntry	31 }

smscSiwcdmaSmsDelackRejected OBJECT-TYPE
		SYNTAX	Unsigned32
		MAX-ACCESS read-only
		STATUS current
		DESCRIPTION
			"Number of SMS DELIVERY ACK messages rejected"
	::= { siwcdmaInstanceEntry	32 }

smscSiwcdmaSmsManackAccepted OBJECT-TYPE
		SYNTAX	Unsigned32
		MAX-ACCESS read-only
		STATUS current
		DESCRIPTION
			"Number of SMS MANUAL ACK messages accepted"
	::= { siwcdmaInstanceEntry	33 }

smscSiwcdmaSmsManackRejected OBJECT-TYPE
		SYNTAX	Unsigned32
		MAX-ACCESS read-only
		STATUS current
		DESCRIPTION
			"Number of SMS MANUAL ACK messages rejected"
	::= { siwcdmaInstanceEntry	34 }

smscSiwcdmaSessionsPending OBJECT-TYPE
		SYNTAX	Unsigned32
		MAX-ACCESS read-only
		STATUS current
		DESCRIPTION
			"Number of sessions (currently) pending"
	::= { siwcdmaInstanceEntry	35 }

smscSiwcdmaAdtUsedMemory OBJECT-TYPE
		SYNTAX	Unsigned32
		MAX-ACCESS read-only
		STATUS current
		DESCRIPTION
			"Memory blocks used by ADT tables of SIWCDMA."
	::= { siwcdmaInstanceEntry	36 }

smscSiwcdmaSmResourceFail OBJECT-TYPE
		SYNTAX	Unsigned32
		MAX-ACCESS read-only
		STATUS current
		DESCRIPTION
			"Number of rejected SM due to resource shortage"
	::= { siwcdmaInstanceEntry	37 }

smscSiwcdmaSmsReadackAccepted OBJECT-TYPE
		SYNTAX	Unsigned32
		MAX-ACCESS read-only
		STATUS current
		DESCRIPTION
			"Number of SMS READ ACK messages accepted"
	::= { siwcdmaInstanceEntry	38 }

smscSiwcdmaSmsReadackRejected OBJECT-TYPE
		SYNTAX	Unsigned32
		MAX-ACCESS read-only
		STATUS current
		DESCRIPTION
			"Number of SMS READ ACK messages rejected"
	::= { siwcdmaInstanceEntry	39 }

smscSiwcdmaSmsCancelAccepted OBJECT-TYPE
		SYNTAX	Unsigned32
		MAX-ACCESS read-only
		STATUS current
		DESCRIPTION
			"Number of SMS CANCELLATION messages accepted"
	::= { siwcdmaInstanceEntry	40 }

smscSiwcdmaSmsCancelRejected OBJECT-TYPE
		SYNTAX	Unsigned32
		MAX-ACCESS read-only
		STATUS current
		DESCRIPTION
			"Number of SMS CANCELLATION messages rejected"
	::= { siwcdmaInstanceEntry	41 }



-- end of SIWCDMA description.
-- --------------------------------------


-- --------------------------------------
-- Class SIWOTA
-- 
smscSiwota OBJECT-TYPE
	SYNTAX  SEQUENCE OF SiwotaInstanceEntry
	MAX-ACCESS  not-accessible
	STATUS  current
	DESCRIPTION
		"Mapping table for SMSC SIWOTA entities."
   ::= { smscClassSiw   12  }

siwotaInstanceEntry  OBJECT-TYPE
	SYNTAX SiwotaInstanceEntry
	MAX-ACCESS  not-accessible
	STATUS  current
	DESCRIPTION
		"An entry (row) in the entityInstanceTable."
	INDEX { IMPLIED smscSiwotaName }
   ::= { smscSiwota 1 }

SiwotaInstanceEntry ::= SEQUENCE {
		smscSiwotaName     DisplayString,
		smscSiwotaState   INTEGER,
		smscSiwotaLastupdate   TimeTicks,
		smscSiwotaNode	   DisplayString, 
		smscSiwotaMsgReceived	 Unsigned32, 
		smscSiwotaMsgRejected	 Unsigned32, 
		smscSiwotaMsgTransmitted	 Unsigned32, 
		smscSiwotaSmReceived	 Unsigned32, 
		smscSiwotaMsgFailed	 Unsigned32, 
		smscSiwotaNotifbRequested	 Unsigned32, 
		smscSiwotaNotifdRequested	 Unsigned32, 
		smscSiwotaNotifndRequested	 Unsigned32, 
		smscSiwotaQelemUsed	 Unsigned32, 
		smscSiwotaQelemInProcqueue	 Unsigned32, 
		smscSiwotaQelemInExpqueue	 Unsigned32, 
		smscSiwotaNrTimersRunning	 Unsigned32, 
		smscSiwotaNrSystemTimers	 Unsigned32, 
		smscSiwotaImiRecallQelem	 Unsigned32, 
		smscSiwotaImiRecallQueues	 Unsigned32, 
		smscSiwotaIdiRecallQelem	 Unsigned32, 
		smscSiwotaIdiRecallQueues	 Unsigned32, 
		smscSiwotaIosRecallQelem	 Unsigned32, 
		smscSiwotaIosRecallQueues	 Unsigned32, 
		smscSiwotaLogRecallQelem	 Unsigned32, 
		smscSiwotaLogRecallQueues	 Unsigned32, 
		smscSiwotaTrcreqDiscarded	 Unsigned32, 
		smscSiwotaOtaTransRcvd	 Unsigned32, 
		smscSiwotaOtaTransAccepted	 Unsigned32, 
		smscSiwotaOtaMsgAttempts	 Unsigned32, 
		smscSiwotaOtaMsgDelivered	 Unsigned32, 
		smscSiwotaOtaMsgRejected	 Unsigned32
	}

smscSiwotaName  OBJECT-TYPE
	SYNTAX  DisplayString
	MAX-ACCESS  read-only
	STATUS   current
	DESCRIPTION
		"Identifies the name of the entity."
   ::= {siwotaInstanceEntry 1 }

smscSiwotaState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { siwotaInstanceEntry 2 }


smscSiwotaLastupdate OBJECT-TYPE
		SYNTAX	TimeTicks
		MAX-ACCESS read-only
		STATUS current
		DESCRIPTION
			"Value which reflects the last time the entities fields have been updated"
	::= { siwotaInstanceEntry	3 }

smscSiwotaNode  OBJECT-TYPE
	SYNTAX  DisplayString
	MAX-ACCESS  read-only
	STATUS   current
	DESCRIPTION
		"Identifies the node the entity is running on."
   ::= {siwotaInstanceEntry 4 }

smscSiwotaMsgReceived OBJECT-TYPE
		SYNTAX	Unsigned32
		MAX-ACCESS read-only
		STATUS current
		DESCRIPTION
			"Received messages"
	::= { siwotaInstanceEntry	5 }

smscSiwotaMsgRejected OBJECT-TYPE
		SYNTAX	Unsigned32
		MAX-ACCESS read-only
		STATUS current
		DESCRIPTION
			"Received messages and rejected"
	::= { siwotaInstanceEntry	6 }

smscSiwotaMsgTransmitted OBJECT-TYPE
		SYNTAX	Unsigned32
		MAX-ACCESS read-only
		STATUS current
		DESCRIPTION
			"Transmitted messages"
	::= { siwotaInstanceEntry	7 }

smscSiwotaSmReceived OBJECT-TYPE
		SYNTAX	Unsigned32
		MAX-ACCESS read-only
		STATUS current
		DESCRIPTION
			"Received short messages"
	::= { siwotaInstanceEntry	8 }

smscSiwotaMsgFailed OBJECT-TYPE
		SYNTAX	Unsigned32
		MAX-ACCESS read-only
		STATUS current
		DESCRIPTION
			"Messages that failed on sending"
	::= { siwotaInstanceEntry	9 }

smscSiwotaNotifbRequested OBJECT-TYPE
		SYNTAX	Unsigned32
		MAX-ACCESS read-only
		STATUS current
		DESCRIPTION
			"Requested buffered message notifications"
	::= { siwotaInstanceEntry	10 }

smscSiwotaNotifdRequested OBJECT-TYPE
		SYNTAX	Unsigned32
		MAX-ACCESS read-only
		STATUS current
		DESCRIPTION
			"Requested delivery notifications"
	::= { siwotaInstanceEntry	11 }

smscSiwotaNotifndRequested OBJECT-TYPE
		SYNTAX	Unsigned32
		MAX-ACCESS read-only
		STATUS current
		DESCRIPTION
			"Requested non-delivery notifications"
	::= { siwotaInstanceEntry	12 }

smscSiwotaQelemUsed OBJECT-TYPE
		SYNTAX	Unsigned32
		MAX-ACCESS read-only
		STATUS current
		DESCRIPTION
			"Number of elements in internal queues"
	::= { siwotaInstanceEntry	13 }

smscSiwotaQelemInProcqueue OBJECT-TYPE
		SYNTAX	Unsigned32
		MAX-ACCESS read-only
		STATUS current
		DESCRIPTION
			"Number of elements used in process queue"
	::= { siwotaInstanceEntry	14 }

smscSiwotaQelemInExpqueue OBJECT-TYPE
		SYNTAX	Unsigned32
		MAX-ACCESS read-only
		STATUS current
		DESCRIPTION
			"Number of elements used in expedited queue"
	::= { siwotaInstanceEntry	15 }

smscSiwotaNrTimersRunning OBJECT-TYPE
		SYNTAX	Unsigned32
		MAX-ACCESS read-only
		STATUS current
		DESCRIPTION
			"Total number of timers running"
	::= { siwotaInstanceEntry	16 }

smscSiwotaNrSystemTimers OBJECT-TYPE
		SYNTAX	Unsigned32
		MAX-ACCESS read-only
		STATUS current
		DESCRIPTION
			"Number of system timers running"
	::= { siwotaInstanceEntry	17 }

smscSiwotaImiRecallQelem OBJECT-TYPE
		SYNTAX	Unsigned32
		MAX-ACCESS read-only
		STATUS current
		DESCRIPTION
			"Number of IMI recall-queue elements used"
	::= { siwotaInstanceEntry	18 }

smscSiwotaImiRecallQueues OBJECT-TYPE
		SYNTAX	Unsigned32
		MAX-ACCESS read-only
		STATUS current
		DESCRIPTION
			"Number of IMI-recall-queues used"
	::= { siwotaInstanceEntry	19 }

smscSiwotaIdiRecallQelem OBJECT-TYPE
		SYNTAX	Unsigned32
		MAX-ACCESS read-only
		STATUS current
		DESCRIPTION
			"Number of IDI recall-queue elements used"
	::= { siwotaInstanceEntry	20 }

smscSiwotaIdiRecallQueues OBJECT-TYPE
		SYNTAX	Unsigned32
		MAX-ACCESS read-only
		STATUS current
		DESCRIPTION
			"Number of IDI recall-queues used"
	::= { siwotaInstanceEntry	21 }

smscSiwotaIosRecallQelem OBJECT-TYPE
		SYNTAX	Unsigned32
		MAX-ACCESS read-only
		STATUS current
		DESCRIPTION
			"Number of IOS recall-queue elements used"
	::= { siwotaInstanceEntry	22 }

smscSiwotaIosRecallQueues OBJECT-TYPE
		SYNTAX	Unsigned32
		MAX-ACCESS read-only
		STATUS current
		DESCRIPTION
			"Number of IOS recall-queues used"
	::= { siwotaInstanceEntry	23 }

smscSiwotaLogRecallQelem OBJECT-TYPE
		SYNTAX	Unsigned32
		MAX-ACCESS read-only
		STATUS current
		DESCRIPTION
			"Number of LOG recall-queue elements used"
	::= { siwotaInstanceEntry	24 }

smscSiwotaLogRecallQueues OBJECT-TYPE
		SYNTAX	Unsigned32
		MAX-ACCESS read-only
		STATUS current
		DESCRIPTION
			"Number of LOG recall-queues used"
	::= { siwotaInstanceEntry	25 }

smscSiwotaTrcreqDiscarded OBJECT-TYPE
		SYNTAX	Unsigned32
		MAX-ACCESS read-only
		STATUS current
		DESCRIPTION
			"Number of trace requests discarded"
	::= { siwotaInstanceEntry	26 }

smscSiwotaOtaTransRcvd OBJECT-TYPE
		SYNTAX	Unsigned32
		MAX-ACCESS read-only
		STATUS current
		DESCRIPTION
			"Total number of transactions received"
	::= { siwotaInstanceEntry	27 }

smscSiwotaOtaTransAccepted OBJECT-TYPE
		SYNTAX	Unsigned32
		MAX-ACCESS read-only
		STATUS current
		DESCRIPTION
			"Total number of transactions accepted"
	::= { siwotaInstanceEntry	28 }

smscSiwotaOtaMsgAttempts OBJECT-TYPE
		SYNTAX	Unsigned32
		MAX-ACCESS read-only
		STATUS current
		DESCRIPTION
			"OTA download message delivery attemps"
	::= { siwotaInstanceEntry	29 }

smscSiwotaOtaMsgDelivered OBJECT-TYPE
		SYNTAX	Unsigned32
		MAX-ACCESS read-only
		STATUS current
		DESCRIPTION
			"OTA download messages succesfully delivered"
	::= { siwotaInstanceEntry	30 }

smscSiwotaOtaMsgRejected OBJECT-TYPE
		SYNTAX	Unsigned32
		MAX-ACCESS read-only
		STATUS current
		DESCRIPTION
			"OTA download messages that failed"
	::= { siwotaInstanceEntry	31 }



-- end of SIWOTA description.
-- --------------------------------------


-- --------------------------------------
-- Class SIWTDMA
-- 
smscSiwtdma OBJECT-TYPE
	SYNTAX  SEQUENCE OF SiwtdmaInstanceEntry
	MAX-ACCESS  not-accessible
	STATUS  current
	DESCRIPTION
		"Mapping table for SMSC SIWTDMA entities."
   ::= { smscClassSiw   13  }

siwtdmaInstanceEntry  OBJECT-TYPE
	SYNTAX SiwtdmaInstanceEntry
	MAX-ACCESS  not-accessible
	STATUS  current
	DESCRIPTION
		"An entry (row) in the entityInstanceTable."
	INDEX { IMPLIED smscSiwtdmaName }
   ::= { smscSiwtdma 1 }

SiwtdmaInstanceEntry ::= SEQUENCE {
		smscSiwtdmaName     DisplayString,
		smscSiwtdmaState   INTEGER,
		smscSiwtdmaLastupdate   TimeTicks,
		smscSiwtdmaNode	   DisplayString, 
		smscSiwtdmaSmInvalid	 Unsigned32, 
		smscSiwtdmaMsgReceived	 Unsigned32, 
		smscSiwtdmaMsgRejected	 Unsigned32, 
		smscSiwtdmaMsgTransmitted	 Unsigned32, 
		smscSiwtdmaSmReceived	 Unsigned32, 
		smscSiwtdmaMsgFailed	 Unsigned32, 
		smscSiwtdmaNotifbRequested	 Unsigned32, 
		smscSiwtdmaNotifdRequested	 Unsigned32, 
		smscSiwtdmaNotifndRequested	 Unsigned32, 
		smscSiwtdmaLengthSmInPlmn	 Unsigned32, 
		smscSiwtdmaQelemUsed	 Unsigned32, 
		smscSiwtdmaQelemInProcqueue	 Unsigned32, 
		smscSiwtdmaQelemInExpqueue	 Unsigned32, 
		smscSiwtdmaNrTimersRunning	 Unsigned32, 
		smscSiwtdmaNrSystemTimers	 Unsigned32, 
		smscSiwtdmaImiRecallQelem	 Unsigned32, 
		smscSiwtdmaImiRecallQueues	 Unsigned32, 
		smscSiwtdmaIdiRecallQelem	 Unsigned32, 
		smscSiwtdmaIdiRecallQueues	 Unsigned32, 
		smscSiwtdmaIosRecallQelem	 Unsigned32, 
		smscSiwtdmaIosRecallQueues	 Unsigned32, 
		smscSiwtdmaLogRecallQelem	 Unsigned32, 
		smscSiwtdmaLogRecallQueues	 Unsigned32, 
		smscSiwtdmaTrcreqDiscarded	 Unsigned32, 
		smscSiwtdmaSmsSubmitAccepted	 Unsigned32, 
		smscSiwtdmaSmsSubmitRejected	 Unsigned32, 
		smscSiwtdmaSmsDelackAccepted	 Unsigned32, 
		smscSiwtdmaSmsDelackRejected	 Unsigned32, 
		smscSiwtdmaSmsManackAccepted	 Unsigned32, 
		smscSiwtdmaSmsManackRejected	 Unsigned32, 
		smscSiwtdmaSessionsPending	 Unsigned32, 
		smscSiwtdmaAdtUsedMemory	 Unsigned32, 
		smscSiwtdmaSmResourceFail	 Unsigned32
	}

smscSiwtdmaName  OBJECT-TYPE
	SYNTAX  DisplayString
	MAX-ACCESS  read-only
	STATUS   current
	DESCRIPTION
		"Identifies the name of the entity."
   ::= {siwtdmaInstanceEntry 1 }

smscSiwtdmaState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { siwtdmaInstanceEntry 2 }


smscSiwtdmaLastupdate OBJECT-TYPE
		SYNTAX	TimeTicks
		MAX-ACCESS read-only
		STATUS current
		DESCRIPTION
			"Value which reflects the last time the entities fields have been updated"
	::= { siwtdmaInstanceEntry	3 }

smscSiwtdmaNode  OBJECT-TYPE
	SYNTAX  DisplayString
	MAX-ACCESS  read-only
	STATUS   current
	DESCRIPTION
		"Identifies the node the entity is running on."
   ::= {siwtdmaInstanceEntry 4 }

smscSiwtdmaSmInvalid OBJECT-TYPE
		SYNTAX	Unsigned32
		MAX-ACCESS read-only
		STATUS current
		DESCRIPTION
			"Received invalid short messages"
	::= { siwtdmaInstanceEntry	5 }

smscSiwtdmaMsgReceived OBJECT-TYPE
		SYNTAX	Unsigned32
		MAX-ACCESS read-only
		STATUS current
		DESCRIPTION
			"Received messages"
	::= { siwtdmaInstanceEntry	6 }

smscSiwtdmaMsgRejected OBJECT-TYPE
		SYNTAX	Unsigned32
		MAX-ACCESS read-only
		STATUS current
		DESCRIPTION
			"Received messages and rejected"
	::= { siwtdmaInstanceEntry	7 }

smscSiwtdmaMsgTransmitted OBJECT-TYPE
		SYNTAX	Unsigned32
		MAX-ACCESS read-only
		STATUS current
		DESCRIPTION
			"Transmitted messages"
	::= { siwtdmaInstanceEntry	8 }

smscSiwtdmaSmReceived OBJECT-TYPE
		SYNTAX	Unsigned32
		MAX-ACCESS read-only
		STATUS current
		DESCRIPTION
			"Received short messages"
	::= { siwtdmaInstanceEntry	9 }

smscSiwtdmaMsgFailed OBJECT-TYPE
		SYNTAX	Unsigned32
		MAX-ACCESS read-only
		STATUS current
		DESCRIPTION
			"Messages that failed on sending"
	::= { siwtdmaInstanceEntry	10 }

smscSiwtdmaNotifbRequested OBJECT-TYPE
		SYNTAX	Unsigned32
		MAX-ACCESS read-only
		STATUS current
		DESCRIPTION
			"Requested buffered message notifications"
	::= { siwtdmaInstanceEntry	11 }

smscSiwtdmaNotifdRequested OBJECT-TYPE
		SYNTAX	Unsigned32
		MAX-ACCESS read-only
		STATUS current
		DESCRIPTION
			"Requested delivery notifications"
	::= { siwtdmaInstanceEntry	12 }

smscSiwtdmaNotifndRequested OBJECT-TYPE
		SYNTAX	Unsigned32
		MAX-ACCESS read-only
		STATUS current
		DESCRIPTION
			"Requested non-delivery notifications"
	::= { siwtdmaInstanceEntry	13 }

smscSiwtdmaLengthSmInPlmn OBJECT-TYPE
		SYNTAX	Unsigned32
		MAX-ACCESS read-only
		STATUS current
		DESCRIPTION
			"Accumulated length of short messages via PLMN"
	::= { siwtdmaInstanceEntry	14 }

smscSiwtdmaQelemUsed OBJECT-TYPE
		SYNTAX	Unsigned32
		MAX-ACCESS read-only
		STATUS current
		DESCRIPTION
			"Number of elements in internal queues"
	::= { siwtdmaInstanceEntry	15 }

smscSiwtdmaQelemInProcqueue OBJECT-TYPE
		SYNTAX	Unsigned32
		MAX-ACCESS read-only
		STATUS current
		DESCRIPTION
			"Number of elements used in process queue"
	::= { siwtdmaInstanceEntry	16 }

smscSiwtdmaQelemInExpqueue OBJECT-TYPE
		SYNTAX	Unsigned32
		MAX-ACCESS read-only
		STATUS current
		DESCRIPTION
			"Number of elements used in expedited queue"
	::= { siwtdmaInstanceEntry	17 }

smscSiwtdmaNrTimersRunning OBJECT-TYPE
		SYNTAX	Unsigned32
		MAX-ACCESS read-only
		STATUS current
		DESCRIPTION
			"Total number of timers running"
	::= { siwtdmaInstanceEntry	18 }

smscSiwtdmaNrSystemTimers OBJECT-TYPE
		SYNTAX	Unsigned32
		MAX-ACCESS read-only
		STATUS current
		DESCRIPTION
			"Number of system timers running"
	::= { siwtdmaInstanceEntry	19 }

smscSiwtdmaImiRecallQelem OBJECT-TYPE
		SYNTAX	Unsigned32
		MAX-ACCESS read-only
		STATUS current
		DESCRIPTION
			"Number of IMI recall-queue elements used"
	::= { siwtdmaInstanceEntry	20 }

smscSiwtdmaImiRecallQueues OBJECT-TYPE
		SYNTAX	Unsigned32
		MAX-ACCESS read-only
		STATUS current
		DESCRIPTION
			"Number of IMI-recall-queues used"
	::= { siwtdmaInstanceEntry	21 }

smscSiwtdmaIdiRecallQelem OBJECT-TYPE
		SYNTAX	Unsigned32
		MAX-ACCESS read-only
		STATUS current
		DESCRIPTION
			"Number of IDI recall-queue elements used"
	::= { siwtdmaInstanceEntry	22 }

smscSiwtdmaIdiRecallQueues OBJECT-TYPE
		SYNTAX	Unsigned32
		MAX-ACCESS read-only
		STATUS current
		DESCRIPTION
			"Number of IDI recall-queues used"
	::= { siwtdmaInstanceEntry	23 }

smscSiwtdmaIosRecallQelem OBJECT-TYPE
		SYNTAX	Unsigned32
		MAX-ACCESS read-only
		STATUS current
		DESCRIPTION
			"Number of IOS recall-queue elements used"
	::= { siwtdmaInstanceEntry	24 }

smscSiwtdmaIosRecallQueues OBJECT-TYPE
		SYNTAX	Unsigned32
		MAX-ACCESS read-only
		STATUS current
		DESCRIPTION
			"Number of IOS recall-queues used"
	::= { siwtdmaInstanceEntry	25 }

smscSiwtdmaLogRecallQelem OBJECT-TYPE
		SYNTAX	Unsigned32
		MAX-ACCESS read-only
		STATUS current
		DESCRIPTION
			"Number of LOG recall-queue elements used"
	::= { siwtdmaInstanceEntry	26 }

smscSiwtdmaLogRecallQueues OBJECT-TYPE
		SYNTAX	Unsigned32
		MAX-ACCESS read-only
		STATUS current
		DESCRIPTION
			"Number of LOG recall-queues used"
	::= { siwtdmaInstanceEntry	27 }

smscSiwtdmaTrcreqDiscarded OBJECT-TYPE
		SYNTAX	Unsigned32
		MAX-ACCESS read-only
		STATUS current
		DESCRIPTION
			"Number of trace requests discarded"
	::= { siwtdmaInstanceEntry	28 }

smscSiwtdmaSmsSubmitAccepted OBJECT-TYPE
		SYNTAX	Unsigned32
		MAX-ACCESS read-only
		STATUS current
		DESCRIPTION
			"Number of SMS SUBMIT messages accepted"
	::= { siwtdmaInstanceEntry	29 }

smscSiwtdmaSmsSubmitRejected OBJECT-TYPE
		SYNTAX	Unsigned32
		MAX-ACCESS read-only
		STATUS current
		DESCRIPTION
			"Number of SMS SUBMIT messages rejected"
	::= { siwtdmaInstanceEntry	30 }

smscSiwtdmaSmsDelackAccepted OBJECT-TYPE
		SYNTAX	Unsigned32
		MAX-ACCESS read-only
		STATUS current
		DESCRIPTION
			"SMS DELIVERY ACK messages accepted"
	::= { siwtdmaInstanceEntry	31 }

smscSiwtdmaSmsDelackRejected OBJECT-TYPE
		SYNTAX	Unsigned32
		MAX-ACCESS read-only
		STATUS current
		DESCRIPTION
			"SMS DELIVERY ACK messages rejected"
	::= { siwtdmaInstanceEntry	32 }

smscSiwtdmaSmsManackAccepted OBJECT-TYPE
		SYNTAX	Unsigned32
		MAX-ACCESS read-only
		STATUS current
		DESCRIPTION
			"SMS MANUAL ACK messages accepted"
	::= { siwtdmaInstanceEntry	33 }

smscSiwtdmaSmsManackRejected OBJECT-TYPE
		SYNTAX	Unsigned32
		MAX-ACCESS read-only
		STATUS current
		DESCRIPTION
			"SMS MANUAL ACK messages rejected"
	::= { siwtdmaInstanceEntry	34 }

smscSiwtdmaSessionsPending OBJECT-TYPE
		SYNTAX	Unsigned32
		MAX-ACCESS read-only
		STATUS current
		DESCRIPTION
			"Number of sessions (currently) pending"
	::= { siwtdmaInstanceEntry	35 }

smscSiwtdmaAdtUsedMemory OBJECT-TYPE
		SYNTAX	Unsigned32
		MAX-ACCESS read-only
		STATUS current
		DESCRIPTION
			"Memory blocks used by ADT tables of SIWTDMA."
	::= { siwtdmaInstanceEntry	36 }

smscSiwtdmaSmResourceFail OBJECT-TYPE
		SYNTAX	Unsigned32
		MAX-ACCESS read-only
		STATUS current
		DESCRIPTION
			"Number of rejected SM due to resource shortage"
	::= { siwtdmaInstanceEntry	37 }



-- end of SIWTDMA description.
-- --------------------------------------


-- --------------------------------------
-- Class DIWMENU
-- 
smscDiwmenu OBJECT-TYPE
	SYNTAX  SEQUENCE OF DiwmenuInstanceEntry
	MAX-ACCESS  not-accessible
	STATUS  current
	DESCRIPTION
		"Mapping table for SMSC DIWMENU entities."
   ::= { smscClassDiw   1  }

diwmenuInstanceEntry  OBJECT-TYPE
	SYNTAX DiwmenuInstanceEntry
	MAX-ACCESS  not-accessible
	STATUS  current
	DESCRIPTION
		"An entry (row) in the entityInstanceTable."
	INDEX { IMPLIED smscDiwmenuName }
   ::= { smscDiwmenu 1 }

DiwmenuInstanceEntry ::= SEQUENCE {
		smscDiwmenuName     DisplayString,
		smscDiwmenuState   INTEGER,
		smscDiwmenuLastupdate   TimeTicks,
		smscDiwmenuNode	   DisplayString, 
		smscDiwmenuMsgReceived	 Unsigned32, 
		smscDiwmenuMsgRejected	 Unsigned32, 
		smscDiwmenuMsgTransmitted	 Unsigned32, 
		smscDiwmenuMsgFailed	 Unsigned32, 
		smscDiwmenuNotifPstnFailed	 Unsigned32, 
		smscDiwmenuSessRefPstn	 Unsigned32, 
		smscDiwmenuSmPstnFailed	 Unsigned32, 
		smscDiwmenuSmVpFailed	 Unsigned32, 
		smscDiwmenuNotifVpFailed	 Unsigned32, 
		smscDiwmenuNotifPstnTransmitted	 Unsigned32, 
		smscDiwmenuSmPstnTransmitted	 Unsigned32, 
		smscDiwmenuLengthSmOutPstn	 Unsigned32, 
		smscDiwmenuQelemUsed	 Unsigned32, 
		smscDiwmenuQelemInProcqueue	 Unsigned32, 
		smscDiwmenuQelemInExpqueue	 Unsigned32, 
		smscDiwmenuNrTimersRunning	 Unsigned32, 
		smscDiwmenuNrSystemTimers	 Unsigned32, 
		smscDiwmenuImiRecallQelem	 Unsigned32, 
		smscDiwmenuImiRecallQueues	 Unsigned32, 
		smscDiwmenuIdiRecallQelem	 Unsigned32, 
		smscDiwmenuIdiRecallQueues	 Unsigned32, 
		smscDiwmenuIosRecallQelem	 Unsigned32, 
		smscDiwmenuIosRecallQueues	 Unsigned32, 
		smscDiwmenuLogRecallQelem	 Unsigned32, 
		smscDiwmenuLogRecallQueues	 Unsigned32, 
		smscDiwmenuTrcreqDiscarded	 Unsigned32
	}

smscDiwmenuName  OBJECT-TYPE
	SYNTAX  DisplayString
	MAX-ACCESS  read-only
	STATUS   current
	DESCRIPTION
		"Identifies the name of the entity."
   ::= {diwmenuInstanceEntry 1 }

smscDiwmenuState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { diwmenuInstanceEntry 2 }


smscDiwmenuLastupdate OBJECT-TYPE
		SYNTAX	TimeTicks
		MAX-ACCESS read-only
		STATUS current
		DESCRIPTION
			"Value which reflects the last time the entities fields have been updated"
	::= { diwmenuInstanceEntry	3 }

smscDiwmenuNode  OBJECT-TYPE
	SYNTAX  DisplayString
	MAX-ACCESS  read-only
	STATUS   current
	DESCRIPTION
		"Identifies the node the entity is running on."
   ::= {diwmenuInstanceEntry 4 }

smscDiwmenuMsgReceived OBJECT-TYPE
		SYNTAX	Unsigned32
		MAX-ACCESS read-only
		STATUS current
		DESCRIPTION
			"Received messages"
	::= { diwmenuInstanceEntry	5 }

smscDiwmenuMsgRejected OBJECT-TYPE
		SYNTAX	Unsigned32
		MAX-ACCESS read-only
		STATUS current
		DESCRIPTION
			"Received messages and rejected"
	::= { diwmenuInstanceEntry	6 }

smscDiwmenuMsgTransmitted OBJECT-TYPE
		SYNTAX	Unsigned32
		MAX-ACCESS read-only
		STATUS current
		DESCRIPTION
			"Transmitted messages"
	::= { diwmenuInstanceEntry	7 }

smscDiwmenuMsgFailed OBJECT-TYPE
		SYNTAX	Unsigned32
		MAX-ACCESS read-only
		STATUS current
		DESCRIPTION
			"Messages that failed on sending"
	::= { diwmenuInstanceEntry	8 }

smscDiwmenuNotifPstnFailed OBJECT-TYPE
		SYNTAX	Unsigned32
		MAX-ACCESS read-only
		STATUS current
		DESCRIPTION
			"Submitted notifications for PSTN that failed"
	::= { diwmenuInstanceEntry	9 }

smscDiwmenuSessRefPstn OBJECT-TYPE
		SYNTAX	Unsigned32
		MAX-ACCESS read-only
		STATUS current
		DESCRIPTION
			"Refused sessions via PSTN"
	::= { diwmenuInstanceEntry	10 }

smscDiwmenuSmPstnFailed OBJECT-TYPE
		SYNTAX	Unsigned32
		MAX-ACCESS read-only
		STATUS current
		DESCRIPTION
			"Short messages submitted to PSTN that failed"
	::= { diwmenuInstanceEntry	11 }

smscDiwmenuSmVpFailed OBJECT-TYPE
		SYNTAX	Unsigned32
		MAX-ACCESS read-only
		STATUS current
		DESCRIPTION
			"Failed short messages submitted and validity period exceeded"
	::= { diwmenuInstanceEntry	12 }

smscDiwmenuNotifVpFailed OBJECT-TYPE
		SYNTAX	Unsigned32
		MAX-ACCESS read-only
		STATUS current
		DESCRIPTION
			"Failed notifications with validity period exceeded"
	::= { diwmenuInstanceEntry	13 }

smscDiwmenuNotifPstnTransmitted OBJECT-TYPE
		SYNTAX	Unsigned32
		MAX-ACCESS read-only
		STATUS current
		DESCRIPTION
			"Transmitted notifications to PSTN"
	::= { diwmenuInstanceEntry	14 }

smscDiwmenuSmPstnTransmitted OBJECT-TYPE
		SYNTAX	Unsigned32
		MAX-ACCESS read-only
		STATUS current
		DESCRIPTION
			"Transmitted short messages to PSTN"
	::= { diwmenuInstanceEntry	15 }

smscDiwmenuLengthSmOutPstn OBJECT-TYPE
		SYNTAX	Unsigned32
		MAX-ACCESS read-only
		STATUS current
		DESCRIPTION
			"Accumulated length of short messages to PSTN"
	::= { diwmenuInstanceEntry	16 }

smscDiwmenuQelemUsed OBJECT-TYPE
		SYNTAX	Unsigned32
		MAX-ACCESS read-only
		STATUS current
		DESCRIPTION
			"Number of elements in internal queues"
	::= { diwmenuInstanceEntry	17 }

smscDiwmenuQelemInProcqueue OBJECT-TYPE
		SYNTAX	Unsigned32
		MAX-ACCESS read-only
		STATUS current
		DESCRIPTION
			"Number of elements used in process queue"
	::= { diwmenuInstanceEntry	18 }

smscDiwmenuQelemInExpqueue OBJECT-TYPE
		SYNTAX	Unsigned32
		MAX-ACCESS read-only
		STATUS current
		DESCRIPTION
			"Number of elements used in expedited queue"
	::= { diwmenuInstanceEntry	19 }

smscDiwmenuNrTimersRunning OBJECT-TYPE
		SYNTAX	Unsigned32
		MAX-ACCESS read-only
		STATUS current
		DESCRIPTION
			"Total number of timers running"
	::= { diwmenuInstanceEntry	20 }

smscDiwmenuNrSystemTimers OBJECT-TYPE
		SYNTAX	Unsigned32
		MAX-ACCESS read-only
		STATUS current
		DESCRIPTION
			"Number of system timers running"
	::= { diwmenuInstanceEntry	21 }

smscDiwmenuImiRecallQelem OBJECT-TYPE
		SYNTAX	Unsigned32
		MAX-ACCESS read-only
		STATUS current
		DESCRIPTION
			"Number of IMI recall-queue elements used"
	::= { diwmenuInstanceEntry	22 }

smscDiwmenuImiRecallQueues OBJECT-TYPE
		SYNTAX	Unsigned32
		MAX-ACCESS read-only
		STATUS current
		DESCRIPTION
			"Number of IMI-recall-queues used"
	::= { diwmenuInstanceEntry	23 }

smscDiwmenuIdiRecallQelem OBJECT-TYPE
		SYNTAX	Unsigned32
		MAX-ACCESS read-only
		STATUS current
		DESCRIPTION
			"Number of IDI recall-queue elements used"
	::= { diwmenuInstanceEntry	24 }

smscDiwmenuIdiRecallQueues OBJECT-TYPE
		SYNTAX	Unsigned32
		MAX-ACCESS read-only
		STATUS current
		DESCRIPTION
			"Number of IDI recall-queues used"
	::= { diwmenuInstanceEntry	25 }

smscDiwmenuIosRecallQelem OBJECT-TYPE
		SYNTAX	Unsigned32
		MAX-ACCESS read-only
		STATUS current
		DESCRIPTION
			"Number of IOS recall-queue elements used"
	::= { diwmenuInstanceEntry	26 }

smscDiwmenuIosRecallQueues OBJECT-TYPE
		SYNTAX	Unsigned32
		MAX-ACCESS read-only
		STATUS current
		DESCRIPTION
			"Number of IOS recall-queues used"
	::= { diwmenuInstanceEntry	27 }

smscDiwmenuLogRecallQelem OBJECT-TYPE
		SYNTAX	Unsigned32
		MAX-ACCESS read-only
		STATUS current
		DESCRIPTION
			"Number of LOG recall-queue elements used"
	::= { diwmenuInstanceEntry	28 }

smscDiwmenuLogRecallQueues OBJECT-TYPE
		SYNTAX	Unsigned32
		MAX-ACCESS read-only
		STATUS current
		DESCRIPTION
			"Number of LOG recall-queues used"
	::= { diwmenuInstanceEntry	29 }

smscDiwmenuTrcreqDiscarded OBJECT-TYPE
		SYNTAX	Unsigned32
		MAX-ACCESS read-only
		STATUS current
		DESCRIPTION
			"Number of trace requests discarded"
	::= { diwmenuInstanceEntry	30 }



-- end of DIWMENU description.
-- --------------------------------------


-- --------------------------------------
-- Class DIWPC
-- 
smscDiwpc OBJECT-TYPE
	SYNTAX  SEQUENCE OF DiwpcInstanceEntry
	MAX-ACCESS  not-accessible
	STATUS  current
	DESCRIPTION
		"Mapping table for SMSC DIWPC entities."
   ::= { smscClassDiw   2  }

diwpcInstanceEntry  OBJECT-TYPE
	SYNTAX DiwpcInstanceEntry
	MAX-ACCESS  not-accessible
	STATUS  current
	DESCRIPTION
		"An entry (row) in the entityInstanceTable."
	INDEX { IMPLIED smscDiwpcName }
   ::= { smscDiwpc 1 }

DiwpcInstanceEntry ::= SEQUENCE {
		smscDiwpcName     DisplayString,
		smscDiwpcState   INTEGER,
		smscDiwpcLastupdate   TimeTicks,
		smscDiwpcNode	   DisplayString, 
		smscDiwpcMsgReceived	 Unsigned32, 
		smscDiwpcMsgRejected	 Unsigned32, 
		smscDiwpcMsgTransmitted	 Unsigned32, 
		smscDiwpcMsgFailed	 Unsigned32, 
		smscDiwpcNotifPstnFailed	 Unsigned32, 
		smscDiwpcNotifX25Failed	 Unsigned32, 
		smscDiwpcSessRefPstn	 Unsigned32, 
		smscDiwpcSessRefX25	 Unsigned32, 
		smscDiwpcSmPstnFailed	 Unsigned32, 
		smscDiwpcSmVpFailed	 Unsigned32, 
		smscDiwpcNotifVpFailed	 Unsigned32, 
		smscDiwpcNotifPstnTransmitted	 Unsigned32, 
		smscDiwpcSmPstnTransmitted	 Unsigned32, 
		smscDiwpcLengthSmOutPstn	 Unsigned32, 
		smscDiwpcSmX25Failed	 Unsigned32, 
		smscDiwpcNotifX25Transmitted	 Unsigned32, 
		smscDiwpcSmX25Transmitted	 Unsigned32, 
		smscDiwpcLengthSmOutX25	 Unsigned32, 
		smscDiwpcQelemUsed	 Unsigned32, 
		smscDiwpcQelemInProcqueue	 Unsigned32, 
		smscDiwpcQelemInExpqueue	 Unsigned32, 
		smscDiwpcNrTimersRunning	 Unsigned32, 
		smscDiwpcNrSystemTimers	 Unsigned32, 
		smscDiwpcImiRecallQelem	 Unsigned32, 
		smscDiwpcImiRecallQueues	 Unsigned32, 
		smscDiwpcIdiRecallQelem	 Unsigned32, 
		smscDiwpcIdiRecallQueues	 Unsigned32, 
		smscDiwpcIosRecallQelem	 Unsigned32, 
		smscDiwpcIosRecallQueues	 Unsigned32, 
		smscDiwpcLogRecallQelem	 Unsigned32, 
		smscDiwpcLogRecallQueues	 Unsigned32, 
		smscDiwpcTrcreqDiscarded	 Unsigned32
	}

smscDiwpcName  OBJECT-TYPE
	SYNTAX  DisplayString
	MAX-ACCESS  read-only
	STATUS   current
	DESCRIPTION
		"Identifies the name of the entity."
   ::= {diwpcInstanceEntry 1 }

smscDiwpcState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { diwpcInstanceEntry 2 }


smscDiwpcLastupdate OBJECT-TYPE
		SYNTAX	TimeTicks
		MAX-ACCESS read-only
		STATUS current
		DESCRIPTION
			"Value which reflects the last time the entities fields have been updated"
	::= { diwpcInstanceEntry	3 }

smscDiwpcNode  OBJECT-TYPE
	SYNTAX  DisplayString
	MAX-ACCESS  read-only
	STATUS   current
	DESCRIPTION
		"Identifies the node the entity is running on."
   ::= {diwpcInstanceEntry 4 }

smscDiwpcMsgReceived OBJECT-TYPE
		SYNTAX	Unsigned32
		MAX-ACCESS read-only
		STATUS current
		DESCRIPTION
			"Received messages"
	::= { diwpcInstanceEntry	5 }

smscDiwpcMsgRejected OBJECT-TYPE
		SYNTAX	Unsigned32
		MAX-ACCESS read-only
		STATUS current
		DESCRIPTION
			"Received messages and rejected"
	::= { diwpcInstanceEntry	6 }

smscDiwpcMsgTransmitted OBJECT-TYPE
		SYNTAX	Unsigned32
		MAX-ACCESS read-only
		STATUS current
		DESCRIPTION
			"Transmitted messages"
	::= { diwpcInstanceEntry	7 }

smscDiwpcMsgFailed OBJECT-TYPE
		SYNTAX	Unsigned32
		MAX-ACCESS read-only
		STATUS current
		DESCRIPTION
			"Messages that failed on sending"
	::= { diwpcInstanceEntry	8 }

smscDiwpcNotifPstnFailed OBJECT-TYPE
		SYNTAX	Unsigned32
		MAX-ACCESS read-only
		STATUS current
		DESCRIPTION
			"Submitted notifications for PSTN that failed"
	::= { diwpcInstanceEntry	9 }

smscDiwpcNotifX25Failed OBJECT-TYPE
		SYNTAX	Unsigned32
		MAX-ACCESS read-only
		STATUS current
		DESCRIPTION
			"Submitted notifications for X25 that failed"
	::= { diwpcInstanceEntry	10 }

smscDiwpcSessRefPstn OBJECT-TYPE
		SYNTAX	Unsigned32
		MAX-ACCESS read-only
		STATUS current
		DESCRIPTION
			"Refused sessions via PSTN"
	::= { diwpcInstanceEntry	11 }

smscDiwpcSessRefX25 OBJECT-TYPE
		SYNTAX	Unsigned32
		MAX-ACCESS read-only
		STATUS current
		DESCRIPTION
			"Refused sessions via X25"
	::= { diwpcInstanceEntry	12 }

smscDiwpcSmPstnFailed OBJECT-TYPE
		SYNTAX	Unsigned32
		MAX-ACCESS read-only
		STATUS current
		DESCRIPTION
			"Short messages submitted to PSTN that failed"
	::= { diwpcInstanceEntry	13 }

smscDiwpcSmVpFailed OBJECT-TYPE
		SYNTAX	Unsigned32
		MAX-ACCESS read-only
		STATUS current
		DESCRIPTION
			"Failed short messages submitted and validity period exceeded"
	::= { diwpcInstanceEntry	14 }

smscDiwpcNotifVpFailed OBJECT-TYPE
		SYNTAX	Unsigned32
		MAX-ACCESS read-only
		STATUS current
		DESCRIPTION
			"Failed notifications with validity period exceeded"
	::= { diwpcInstanceEntry	15 }

smscDiwpcNotifPstnTransmitted OBJECT-TYPE
		SYNTAX	Unsigned32
		MAX-ACCESS read-only
		STATUS current
		DESCRIPTION
			"Transmitted notifications to PSTN"
	::= { diwpcInstanceEntry	16 }

smscDiwpcSmPstnTransmitted OBJECT-TYPE
		SYNTAX	Unsigned32
		MAX-ACCESS read-only
		STATUS current
		DESCRIPTION
			"Transmitted short messages to PSTN"
	::= { diwpcInstanceEntry	17 }

smscDiwpcLengthSmOutPstn OBJECT-TYPE
		SYNTAX	Unsigned32
		MAX-ACCESS read-only
		STATUS current
		DESCRIPTION
			"Accumulated length of short messages to PSTN"
	::= { diwpcInstanceEntry	18 }

smscDiwpcSmX25Failed OBJECT-TYPE
		SYNTAX	Unsigned32
		MAX-ACCESS read-only
		STATUS current
		DESCRIPTION
			"Short messages submitted to X25 that failed"
	::= { diwpcInstanceEntry	19 }

smscDiwpcNotifX25Transmitted OBJECT-TYPE
		SYNTAX	Unsigned32
		MAX-ACCESS read-only
		STATUS current
		DESCRIPTION
			"Transmitted notifications to X25"
	::= { diwpcInstanceEntry	20 }

smscDiwpcSmX25Transmitted OBJECT-TYPE
		SYNTAX	Unsigned32
		MAX-ACCESS read-only
		STATUS current
		DESCRIPTION
			"Transmitted short messages to X25"
	::= { diwpcInstanceEntry	21 }

smscDiwpcLengthSmOutX25 OBJECT-TYPE
		SYNTAX	Unsigned32
		MAX-ACCESS read-only
		STATUS current
		DESCRIPTION
			"Accumulated length of short messages to X25"
	::= { diwpcInstanceEntry	22 }

smscDiwpcQelemUsed OBJECT-TYPE
		SYNTAX	Unsigned32
		MAX-ACCESS read-only
		STATUS current
		DESCRIPTION
			"Number of elements in internal queues"
	::= { diwpcInstanceEntry	23 }

smscDiwpcQelemInProcqueue OBJECT-TYPE
		SYNTAX	Unsigned32
		MAX-ACCESS read-only
		STATUS current
		DESCRIPTION
			"Number of elements used in process queue"
	::= { diwpcInstanceEntry	24 }

smscDiwpcQelemInExpqueue OBJECT-TYPE
		SYNTAX	Unsigned32
		MAX-ACCESS read-only
		STATUS current
		DESCRIPTION
			"Number of elements used in expedited queue"
	::= { diwpcInstanceEntry	25 }

smscDiwpcNrTimersRunning OBJECT-TYPE
		SYNTAX	Unsigned32
		MAX-ACCESS read-only
		STATUS current
		DESCRIPTION
			"Total number of timers running"
	::= { diwpcInstanceEntry	26 }

smscDiwpcNrSystemTimers OBJECT-TYPE
		SYNTAX	Unsigned32
		MAX-ACCESS read-only
		STATUS current
		DESCRIPTION
			"Number of system timers running"
	::= { diwpcInstanceEntry	27 }

smscDiwpcImiRecallQelem OBJECT-TYPE
		SYNTAX	Unsigned32
		MAX-ACCESS read-only
		STATUS current
		DESCRIPTION
			"Number of IMI recall-queue elements used"
	::= { diwpcInstanceEntry	28 }

smscDiwpcImiRecallQueues OBJECT-TYPE
		SYNTAX	Unsigned32
		MAX-ACCESS read-only
		STATUS current
		DESCRIPTION
			"Number of IMI-recall-queues used"
	::= { diwpcInstanceEntry	29 }

smscDiwpcIdiRecallQelem OBJECT-TYPE
		SYNTAX	Unsigned32
		MAX-ACCESS read-only
		STATUS current
		DESCRIPTION
			"Number of IDI recall-queue elements used"
	::= { diwpcInstanceEntry	30 }

smscDiwpcIdiRecallQueues OBJECT-TYPE
		SYNTAX	Unsigned32
		MAX-ACCESS read-only
		STATUS current
		DESCRIPTION
			"Number of IDI recall-queues used"
	::= { diwpcInstanceEntry	31 }

smscDiwpcIosRecallQelem OBJECT-TYPE
		SYNTAX	Unsigned32
		MAX-ACCESS read-only
		STATUS current
		DESCRIPTION
			"Number of IOS recall-queue elements used"
	::= { diwpcInstanceEntry	32 }

smscDiwpcIosRecallQueues OBJECT-TYPE
		SYNTAX	Unsigned32
		MAX-ACCESS read-only
		STATUS current
		DESCRIPTION
			"Number of IOS recall-queues used"
	::= { diwpcInstanceEntry	33 }

smscDiwpcLogRecallQelem OBJECT-TYPE
		SYNTAX	Unsigned32
		MAX-ACCESS read-only
		STATUS current
		DESCRIPTION
			"Number of LOG recall-queue elements used"
	::= { diwpcInstanceEntry	34 }

smscDiwpcLogRecallQueues OBJECT-TYPE
		SYNTAX	Unsigned32
		MAX-ACCESS read-only
		STATUS current
		DESCRIPTION
			"Number of LOG recall-queues used"
	::= { diwpcInstanceEntry	35 }

smscDiwpcTrcreqDiscarded OBJECT-TYPE
		SYNTAX	Unsigned32
		MAX-ACCESS read-only
		STATUS current
		DESCRIPTION
			"Number of trace requests discarded"
	::= { diwpcInstanceEntry	36 }



-- end of DIWPC description.
-- --------------------------------------


-- --------------------------------------
-- Class DIWPLMN
-- 
smscDiwplmn OBJECT-TYPE
	SYNTAX  SEQUENCE OF DiwplmnInstanceEntry
	MAX-ACCESS  not-accessible
	STATUS  current
	DESCRIPTION
		"Mapping table for SMSC DIWPLMN entities."
   ::= { smscClassDiw   3  }

diwplmnInstanceEntry  OBJECT-TYPE
	SYNTAX DiwplmnInstanceEntry
	MAX-ACCESS  not-accessible
	STATUS  current
	DESCRIPTION
		"An entry (row) in the entityInstanceTable."
	INDEX { IMPLIED smscDiwplmnName }
   ::= { smscDiwplmn 1 }

DiwplmnInstanceEntry ::= SEQUENCE {
		smscDiwplmnName     DisplayString,
		smscDiwplmnState   INTEGER,
		smscDiwplmnLastupdate   TimeTicks,
		smscDiwplmnNode	   DisplayString, 
		smscDiwplmnMsgReceived	 Unsigned32, 
		smscDiwplmnMsgRejected	 Unsigned32, 
		smscDiwplmnMsgTransmitted	 Unsigned32, 
		smscDiwplmnNotifFailed	 Unsigned32, 
		smscDiwplmnNotifTransmitted	 Unsigned32, 
		smscDiwplmnSmFailed	 Unsigned32, 
		smscDiwplmnSmTransmitted	 Unsigned32, 
		smscDiwplmnMsgFailed	 Unsigned32, 
		smscDiwplmnSmVpFailed	 Unsigned32, 
		smscDiwplmnNotifVpFailed	 Unsigned32, 
		smscDiwplmnLengthSmOutPlmn	 Unsigned32, 
		smscDiwplmnQelemUsed	 Unsigned32, 
		smscDiwplmnQelemInProcqueue	 Unsigned32, 
		smscDiwplmnQelemInExpqueue	 Unsigned32, 
		smscDiwplmnNrTimersRunning	 Unsigned32, 
		smscDiwplmnNrSystemTimers	 Unsigned32, 
		smscDiwplmnImiRecallQelem	 Unsigned32, 
		smscDiwplmnImiRecallQueues	 Unsigned32, 
		smscDiwplmnIdiRecallQelem	 Unsigned32, 
		smscDiwplmnIdiRecallQueues	 Unsigned32, 
		smscDiwplmnIosRecallQelem	 Unsigned32, 
		smscDiwplmnIosRecallQueues	 Unsigned32, 
		smscDiwplmnLogRecallQelem	 Unsigned32, 
		smscDiwplmnLogRecallQueues	 Unsigned32, 
		smscDiwplmnTrcreqDiscarded	 Unsigned32, 
		smscDiwplmnSessionsPending	 Unsigned32
	}

smscDiwplmnName  OBJECT-TYPE
	SYNTAX  DisplayString
	MAX-ACCESS  read-only
	STATUS   current
	DESCRIPTION
		"Identifies the name of the entity."
   ::= {diwplmnInstanceEntry 1 }

smscDiwplmnState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { diwplmnInstanceEntry 2 }


smscDiwplmnLastupdate OBJECT-TYPE
		SYNTAX	TimeTicks
		MAX-ACCESS read-only
		STATUS current
		DESCRIPTION
			"Value which reflects the last time the entities fields have been updated"
	::= { diwplmnInstanceEntry	3 }

smscDiwplmnNode  OBJECT-TYPE
	SYNTAX  DisplayString
	MAX-ACCESS  read-only
	STATUS   current
	DESCRIPTION
		"Identifies the node the entity is running on."
   ::= {diwplmnInstanceEntry 4 }

smscDiwplmnMsgReceived OBJECT-TYPE
		SYNTAX	Unsigned32
		MAX-ACCESS read-only
		STATUS current
		DESCRIPTION
			"Received messages"
	::= { diwplmnInstanceEntry	5 }

smscDiwplmnMsgRejected OBJECT-TYPE
		SYNTAX	Unsigned32
		MAX-ACCESS read-only
		STATUS current
		DESCRIPTION
			"Received messages and rejected"
	::= { diwplmnInstanceEntry	6 }

smscDiwplmnMsgTransmitted OBJECT-TYPE
		SYNTAX	Unsigned32
		MAX-ACCESS read-only
		STATUS current
		DESCRIPTION
			"Transmitted messages"
	::= { diwplmnInstanceEntry	7 }

smscDiwplmnNotifFailed OBJECT-TYPE
		SYNTAX	Unsigned32
		MAX-ACCESS read-only
		STATUS current
		DESCRIPTION
			"Notifications submitted and failed"
	::= { diwplmnInstanceEntry	8 }

smscDiwplmnNotifTransmitted OBJECT-TYPE
		SYNTAX	Unsigned32
		MAX-ACCESS read-only
		STATUS current
		DESCRIPTION
			"Transmitted notifications"
	::= { diwplmnInstanceEntry	9 }

smscDiwplmnSmFailed OBJECT-TYPE
		SYNTAX	Unsigned32
		MAX-ACCESS read-only
		STATUS current
		DESCRIPTION
			"Short messages submitted and failed"
	::= { diwplmnInstanceEntry	10 }

smscDiwplmnSmTransmitted OBJECT-TYPE
		SYNTAX	Unsigned32
		MAX-ACCESS read-only
		STATUS current
		DESCRIPTION
			"Transmitted short messages"
	::= { diwplmnInstanceEntry	11 }

smscDiwplmnMsgFailed OBJECT-TYPE
		SYNTAX	Unsigned32
		MAX-ACCESS read-only
		STATUS current
		DESCRIPTION
			"Messages that failed on sending"
	::= { diwplmnInstanceEntry	12 }

smscDiwplmnSmVpFailed OBJECT-TYPE
		SYNTAX	Unsigned32
		MAX-ACCESS read-only
		STATUS current
		DESCRIPTION
			"Failed short messages submitted and validity period exceeded"
	::= { diwplmnInstanceEntry	13 }

smscDiwplmnNotifVpFailed OBJECT-TYPE
		SYNTAX	Unsigned32
		MAX-ACCESS read-only
		STATUS current
		DESCRIPTION
			"Failed notifications with validity period exceeded"
	::= { diwplmnInstanceEntry	14 }

smscDiwplmnLengthSmOutPlmn OBJECT-TYPE
		SYNTAX	Unsigned32
		MAX-ACCESS read-only
		STATUS current
		DESCRIPTION
			"Accumulated length of short messages to PLMN"
	::= { diwplmnInstanceEntry	15 }

smscDiwplmnQelemUsed OBJECT-TYPE
		SYNTAX	Unsigned32
		MAX-ACCESS read-only
		STATUS current
		DESCRIPTION
			"Number of elements in internal queues"
	::= { diwplmnInstanceEntry	16 }

smscDiwplmnQelemInProcqueue OBJECT-TYPE
		SYNTAX	Unsigned32
		MAX-ACCESS read-only
		STATUS current
		DESCRIPTION
			"Number of elements used in process queue"
	::= { diwplmnInstanceEntry	17 }

smscDiwplmnQelemInExpqueue OBJECT-TYPE
		SYNTAX	Unsigned32
		MAX-ACCESS read-only
		STATUS current
		DESCRIPTION
			"Number of elements used in expedited queue"
	::= { diwplmnInstanceEntry	18 }

smscDiwplmnNrTimersRunning OBJECT-TYPE
		SYNTAX	Unsigned32
		MAX-ACCESS read-only
		STATUS current
		DESCRIPTION
			"Total number of timers running"
	::= { diwplmnInstanceEntry	19 }

smscDiwplmnNrSystemTimers OBJECT-TYPE
		SYNTAX	Unsigned32
		MAX-ACCESS read-only
		STATUS current
		DESCRIPTION
			"Number of system timers running"
	::= { diwplmnInstanceEntry	20 }

smscDiwplmnImiRecallQelem OBJECT-TYPE
		SYNTAX	Unsigned32
		MAX-ACCESS read-only
		STATUS current
		DESCRIPTION
			"Number of IMI recall-queue elements used"
	::= { diwplmnInstanceEntry	21 }

smscDiwplmnImiRecallQueues OBJECT-TYPE
		SYNTAX	Unsigned32
		MAX-ACCESS read-only
		STATUS current
		DESCRIPTION
			"Number of IMI-recall-queues used"
	::= { diwplmnInstanceEntry	22 }

smscDiwplmnIdiRecallQelem OBJECT-TYPE
		SYNTAX	Unsigned32
		MAX-ACCESS read-only
		STATUS current
		DESCRIPTION
			"Number of IDI recall-queue elements used"
	::= { diwplmnInstanceEntry	23 }

smscDiwplmnIdiRecallQueues OBJECT-TYPE
		SYNTAX	Unsigned32
		MAX-ACCESS read-only
		STATUS current
		DESCRIPTION
			"Number of IDI recall-queues used"
	::= { diwplmnInstanceEntry	24 }

smscDiwplmnIosRecallQelem OBJECT-TYPE
		SYNTAX	Unsigned32
		MAX-ACCESS read-only
		STATUS current
		DESCRIPTION
			"Number of IOS recall-queue elements used"
	::= { diwplmnInstanceEntry	25 }

smscDiwplmnIosRecallQueues OBJECT-TYPE
		SYNTAX	Unsigned32
		MAX-ACCESS read-only
		STATUS current
		DESCRIPTION
			"Number of IOS recall-queues used"
	::= { diwplmnInstanceEntry	26 }

smscDiwplmnLogRecallQelem OBJECT-TYPE
		SYNTAX	Unsigned32
		MAX-ACCESS read-only
		STATUS current
		DESCRIPTION
			"Number of LOG recall-queue elements used"
	::= { diwplmnInstanceEntry	27 }

smscDiwplmnLogRecallQueues OBJECT-TYPE
		SYNTAX	Unsigned32
		MAX-ACCESS read-only
		STATUS current
		DESCRIPTION
			"Number of LOG recall-queues used"
	::= { diwplmnInstanceEntry	28 }

smscDiwplmnTrcreqDiscarded OBJECT-TYPE
		SYNTAX	Unsigned32
		MAX-ACCESS read-only
		STATUS current
		DESCRIPTION
			"Number of trace requests discarded"
	::= { diwplmnInstanceEntry	29 }

smscDiwplmnSessionsPending OBJECT-TYPE
		SYNTAX	Unsigned32
		MAX-ACCESS read-only
		STATUS current
		DESCRIPTION
			"Number of sessions (currently) pending"
	::= { diwplmnInstanceEntry	30 }



-- end of DIWPLMN description.
-- --------------------------------------


-- --------------------------------------
-- Class DIWFAX
-- 
smscDiwfax OBJECT-TYPE
	SYNTAX  SEQUENCE OF DiwfaxInstanceEntry
	MAX-ACCESS  not-accessible
	STATUS  current
	DESCRIPTION
		"Mapping table for SMSC DIWFAX entities."
   ::= { smscClassDiw   4  }

diwfaxInstanceEntry  OBJECT-TYPE
	SYNTAX DiwfaxInstanceEntry
	MAX-ACCESS  not-accessible
	STATUS  current
	DESCRIPTION
		"An entry (row) in the entityInstanceTable."
	INDEX { IMPLIED smscDiwfaxName }
   ::= { smscDiwfax 1 }

DiwfaxInstanceEntry ::= SEQUENCE {
		smscDiwfaxName     DisplayString,
		smscDiwfaxState   INTEGER,
		smscDiwfaxLastupdate   TimeTicks,
		smscDiwfaxNode	   DisplayString, 
		smscDiwfaxMsgReceived	 Unsigned32, 
		smscDiwfaxMsgRejected	 Unsigned32, 
		smscDiwfaxMsgTransmitted	 Unsigned32, 
		smscDiwfaxNotifFailed	 Unsigned32, 
		smscDiwfaxNotifTransmitted	 Unsigned32, 
		smscDiwfaxSmFailed	 Unsigned32, 
		smscDiwfaxSmTransmitted	 Unsigned32, 
		smscDiwfaxMsgFailed	 Unsigned32, 
		smscDiwfaxQelemUsed	 Unsigned32, 
		smscDiwfaxQelemInProcqueue	 Unsigned32, 
		smscDiwfaxQelemInExpqueue	 Unsigned32, 
		smscDiwfaxNrTimersRunning	 Unsigned32, 
		smscDiwfaxNrSystemTimers	 Unsigned32, 
		smscDiwfaxImiRecallQelem	 Unsigned32, 
		smscDiwfaxImiRecallQueues	 Unsigned32, 
		smscDiwfaxIdiRecallQelem	 Unsigned32, 
		smscDiwfaxIdiRecallQueues	 Unsigned32, 
		smscDiwfaxIosRecallQelem	 Unsigned32, 
		smscDiwfaxIosRecallQueues	 Unsigned32, 
		smscDiwfaxLogRecallQelem	 Unsigned32, 
		smscDiwfaxLogRecallQueues	 Unsigned32, 
		smscDiwfaxTrcreqDiscarded	 Unsigned32
	}

smscDiwfaxName  OBJECT-TYPE
	SYNTAX  DisplayString
	MAX-ACCESS  read-only
	STATUS   current
	DESCRIPTION
		"Identifies the name of the entity."
   ::= {diwfaxInstanceEntry 1 }

smscDiwfaxState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { diwfaxInstanceEntry 2 }


smscDiwfaxLastupdate OBJECT-TYPE
		SYNTAX	TimeTicks
		MAX-ACCESS read-only
		STATUS current
		DESCRIPTION
			"Value which reflects the last time the entities fields have been updated"
	::= { diwfaxInstanceEntry	3 }

smscDiwfaxNode  OBJECT-TYPE
	SYNTAX  DisplayString
	MAX-ACCESS  read-only
	STATUS   current
	DESCRIPTION
		"Identifies the node the entity is running on."
   ::= {diwfaxInstanceEntry 4 }

smscDiwfaxMsgReceived OBJECT-TYPE
		SYNTAX	Unsigned32
		MAX-ACCESS read-only
		STATUS current
		DESCRIPTION
			"Received messages"
	::= { diwfaxInstanceEntry	5 }

smscDiwfaxMsgRejected OBJECT-TYPE
		SYNTAX	Unsigned32
		MAX-ACCESS read-only
		STATUS current
		DESCRIPTION
			"Received messages and rejected"
	::= { diwfaxInstanceEntry	6 }

smscDiwfaxMsgTransmitted OBJECT-TYPE
		SYNTAX	Unsigned32
		MAX-ACCESS read-only
		STATUS current
		DESCRIPTION
			"Transmitted messages"
	::= { diwfaxInstanceEntry	7 }

smscDiwfaxNotifFailed OBJECT-TYPE
		SYNTAX	Unsigned32
		MAX-ACCESS read-only
		STATUS current
		DESCRIPTION
			"Notifications submitted and failed"
	::= { diwfaxInstanceEntry	8 }

smscDiwfaxNotifTransmitted OBJECT-TYPE
		SYNTAX	Unsigned32
		MAX-ACCESS read-only
		STATUS current
		DESCRIPTION
			"Transmitted notifications"
	::= { diwfaxInstanceEntry	9 }

smscDiwfaxSmFailed OBJECT-TYPE
		SYNTAX	Unsigned32
		MAX-ACCESS read-only
		STATUS current
		DESCRIPTION
			"Short messages submitted and failed"
	::= { diwfaxInstanceEntry	10 }

smscDiwfaxSmTransmitted OBJECT-TYPE
		SYNTAX	Unsigned32
		MAX-ACCESS read-only
		STATUS current
		DESCRIPTION
			"Transmitted short messages"
	::= { diwfaxInstanceEntry	11 }

smscDiwfaxMsgFailed OBJECT-TYPE
		SYNTAX	Unsigned32
		MAX-ACCESS read-only
		STATUS current
		DESCRIPTION
			"Messages that failed on sending"
	::= { diwfaxInstanceEntry	12 }

smscDiwfaxQelemUsed OBJECT-TYPE
		SYNTAX	Unsigned32
		MAX-ACCESS read-only
		STATUS current
		DESCRIPTION
			"Number of elements in internal queues"
	::= { diwfaxInstanceEntry	13 }

smscDiwfaxQelemInProcqueue OBJECT-TYPE
		SYNTAX	Unsigned32
		MAX-ACCESS read-only
		STATUS current
		DESCRIPTION
			"Number of elements used in process queue"
	::= { diwfaxInstanceEntry	14 }

smscDiwfaxQelemInExpqueue OBJECT-TYPE
		SYNTAX	Unsigned32
		MAX-ACCESS read-only
		STATUS current
		DESCRIPTION
			"Number of elements used in expedited queue"
	::= { diwfaxInstanceEntry	15 }

smscDiwfaxNrTimersRunning OBJECT-TYPE
		SYNTAX	Unsigned32
		MAX-ACCESS read-only
		STATUS current
		DESCRIPTION
			"Total number of timers running"
	::= { diwfaxInstanceEntry	16 }

smscDiwfaxNrSystemTimers OBJECT-TYPE
		SYNTAX	Unsigned32
		MAX-ACCESS read-only
		STATUS current
		DESCRIPTION
			"Number of system timers running"
	::= { diwfaxInstanceEntry	17 }

smscDiwfaxImiRecallQelem OBJECT-TYPE
		SYNTAX	Unsigned32
		MAX-ACCESS read-only
		STATUS current
		DESCRIPTION
			"Number of IMI recall-queue elements used"
	::= { diwfaxInstanceEntry	18 }

smscDiwfaxImiRecallQueues OBJECT-TYPE
		SYNTAX	Unsigned32
		MAX-ACCESS read-only
		STATUS current
		DESCRIPTION
			"Number of IMI-recall-queues used"
	::= { diwfaxInstanceEntry	19 }

smscDiwfaxIdiRecallQelem OBJECT-TYPE
		SYNTAX	Unsigned32
		MAX-ACCESS read-only
		STATUS current
		DESCRIPTION
			"Number of IDI recall-queue elements used"
	::= { diwfaxInstanceEntry	20 }

smscDiwfaxIdiRecallQueues OBJECT-TYPE
		SYNTAX	Unsigned32
		MAX-ACCESS read-only
		STATUS current
		DESCRIPTION
			"Number of IDI recall-queues used"
	::= { diwfaxInstanceEntry	21 }

smscDiwfaxIosRecallQelem OBJECT-TYPE
		SYNTAX	Unsigned32
		MAX-ACCESS read-only
		STATUS current
		DESCRIPTION
			"Number of IOS recall-queue elements used"
	::= { diwfaxInstanceEntry	22 }

smscDiwfaxIosRecallQueues OBJECT-TYPE
		SYNTAX	Unsigned32
		MAX-ACCESS read-only
		STATUS current
		DESCRIPTION
			"Number of IOS recall-queues used"
	::= { diwfaxInstanceEntry	23 }

smscDiwfaxLogRecallQelem OBJECT-TYPE
		SYNTAX	Unsigned32
		MAX-ACCESS read-only
		STATUS current
		DESCRIPTION
			"Number of LOG recall-queue elements used"
	::= { diwfaxInstanceEntry	24 }

smscDiwfaxLogRecallQueues OBJECT-TYPE
		SYNTAX	Unsigned32
		MAX-ACCESS read-only
		STATUS current
		DESCRIPTION
			"Number of LOG recall-queues used"
	::= { diwfaxInstanceEntry	25 }

smscDiwfaxTrcreqDiscarded OBJECT-TYPE
		SYNTAX	Unsigned32
		MAX-ACCESS read-only
		STATUS current
		DESCRIPTION
			"Number of trace requests discarded"
	::= { diwfaxInstanceEntry	26 }



-- end of DIWFAX description.
-- --------------------------------------


-- --------------------------------------
-- Class DIWERMES
-- 
smscDiwermes OBJECT-TYPE
	SYNTAX  SEQUENCE OF DiwermesInstanceEntry
	MAX-ACCESS  not-accessible
	STATUS  current
	DESCRIPTION
		"Mapping table for SMSC DIWERMES entities."
   ::= { smscClassDiw   5  }

diwermesInstanceEntry  OBJECT-TYPE
	SYNTAX DiwermesInstanceEntry
	MAX-ACCESS  not-accessible
	STATUS  current
	DESCRIPTION
		"An entry (row) in the entityInstanceTable."
	INDEX { IMPLIED smscDiwermesName }
   ::= { smscDiwermes 1 }

DiwermesInstanceEntry ::= SEQUENCE {
		smscDiwermesName     DisplayString,
		smscDiwermesState   INTEGER,
		smscDiwermesLastupdate   TimeTicks,
		smscDiwermesNode	   DisplayString, 
		smscDiwermesMsgReceived	 Unsigned32, 
		smscDiwermesMsgRejected	 Unsigned32, 
		smscDiwermesMsgTransmitted	 Unsigned32, 
		smscDiwermesNotifFailed	 Unsigned32, 
		smscDiwermesNotifTransmitted	 Unsigned32, 
		smscDiwermesSmFailed	 Unsigned32, 
		smscDiwermesSmTransmitted	 Unsigned32, 
		smscDiwermesMsgFailed	 Unsigned32, 
		smscDiwermesQelemUsed	 Unsigned32, 
		smscDiwermesQelemInProcqueue	 Unsigned32, 
		smscDiwermesQelemInExpqueue	 Unsigned32, 
		smscDiwermesNrTimersRunning	 Unsigned32, 
		smscDiwermesNrSystemTimers	 Unsigned32, 
		smscDiwermesImiRecallQelem	 Unsigned32, 
		smscDiwermesImiRecallQueues	 Unsigned32, 
		smscDiwermesIdiRecallQelem	 Unsigned32, 
		smscDiwermesIdiRecallQueues	 Unsigned32, 
		smscDiwermesIosRecallQelem	 Unsigned32, 
		smscDiwermesIosRecallQueues	 Unsigned32, 
		smscDiwermesLogRecallQelem	 Unsigned32, 
		smscDiwermesLogRecallQueues	 Unsigned32, 
		smscDiwermesTrcreqDiscarded	 Unsigned32
	}

smscDiwermesName  OBJECT-TYPE
	SYNTAX  DisplayString
	MAX-ACCESS  read-only
	STATUS   current
	DESCRIPTION
		"Identifies the name of the entity."
   ::= {diwermesInstanceEntry 1 }

smscDiwermesState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { diwermesInstanceEntry 2 }


smscDiwermesLastupdate OBJECT-TYPE
		SYNTAX	TimeTicks
		MAX-ACCESS read-only
		STATUS current
		DESCRIPTION
			"Value which reflects the last time the entities fields have been updated"
	::= { diwermesInstanceEntry	3 }

smscDiwermesNode  OBJECT-TYPE
	SYNTAX  DisplayString
	MAX-ACCESS  read-only
	STATUS   current
	DESCRIPTION
		"Identifies the node the entity is running on."
   ::= {diwermesInstanceEntry 4 }

smscDiwermesMsgReceived OBJECT-TYPE
		SYNTAX	Unsigned32
		MAX-ACCESS read-only
		STATUS current
		DESCRIPTION
			"Received messages"
	::= { diwermesInstanceEntry	5 }

smscDiwermesMsgRejected OBJECT-TYPE
		SYNTAX	Unsigned32
		MAX-ACCESS read-only
		STATUS current
		DESCRIPTION
			"Received messages and rejected"
	::= { diwermesInstanceEntry	6 }

smscDiwermesMsgTransmitted OBJECT-TYPE
		SYNTAX	Unsigned32
		MAX-ACCESS read-only
		STATUS current
		DESCRIPTION
			"Transmitted messages"
	::= { diwermesInstanceEntry	7 }

smscDiwermesNotifFailed OBJECT-TYPE
		SYNTAX	Unsigned32
		MAX-ACCESS read-only
		STATUS current
		DESCRIPTION
			"Notifications submitted and failed"
	::= { diwermesInstanceEntry	8 }

smscDiwermesNotifTransmitted OBJECT-TYPE
		SYNTAX	Unsigned32
		MAX-ACCESS read-only
		STATUS current
		DESCRIPTION
			"Transmitted notifications"
	::= { diwermesInstanceEntry	9 }

smscDiwermesSmFailed OBJECT-TYPE
		SYNTAX	Unsigned32
		MAX-ACCESS read-only
		STATUS current
		DESCRIPTION
			"Short messages submitted and failed"
	::= { diwermesInstanceEntry	10 }

smscDiwermesSmTransmitted OBJECT-TYPE
		SYNTAX	Unsigned32
		MAX-ACCESS read-only
		STATUS current
		DESCRIPTION
			"Transmitted short messages"
	::= { diwermesInstanceEntry	11 }

smscDiwermesMsgFailed OBJECT-TYPE
		SYNTAX	Unsigned32
		MAX-ACCESS read-only
		STATUS current
		DESCRIPTION
			"Messages that failed on sending"
	::= { diwermesInstanceEntry	12 }

smscDiwermesQelemUsed OBJECT-TYPE
		SYNTAX	Unsigned32
		MAX-ACCESS read-only
		STATUS current
		DESCRIPTION
			"Number of elements in internal queues"
	::= { diwermesInstanceEntry	13 }

smscDiwermesQelemInProcqueue OBJECT-TYPE
		SYNTAX	Unsigned32
		MAX-ACCESS read-only
		STATUS current
		DESCRIPTION
			"Number of elements used in process queue"
	::= { diwermesInstanceEntry	14 }

smscDiwermesQelemInExpqueue OBJECT-TYPE
		SYNTAX	Unsigned32
		MAX-ACCESS read-only
		STATUS current
		DESCRIPTION
			"Number of elements used in expedited queue"
	::= { diwermesInstanceEntry	15 }

smscDiwermesNrTimersRunning OBJECT-TYPE
		SYNTAX	Unsigned32
		MAX-ACCESS read-only
		STATUS current
		DESCRIPTION
			"Total number of timers running"
	::= { diwermesInstanceEntry	16 }

smscDiwermesNrSystemTimers OBJECT-TYPE
		SYNTAX	Unsigned32
		MAX-ACCESS read-only
		STATUS current
		DESCRIPTION
			"Number of system timers running"
	::= { diwermesInstanceEntry	17 }

smscDiwermesImiRecallQelem OBJECT-TYPE
		SYNTAX	Unsigned32
		MAX-ACCESS read-only
		STATUS current
		DESCRIPTION
			"Number of IMI recall-queue elements used"
	::= { diwermesInstanceEntry	18 }

smscDiwermesImiRecallQueues OBJECT-TYPE
		SYNTAX	Unsigned32
		MAX-ACCESS read-only
		STATUS current
		DESCRIPTION
			"Number of IMI-recall-queues used"
	::= { diwermesInstanceEntry	19 }

smscDiwermesIdiRecallQelem OBJECT-TYPE
		SYNTAX	Unsigned32
		MAX-ACCESS read-only
		STATUS current
		DESCRIPTION
			"Number of IDI recall-queue elements used"
	::= { diwermesInstanceEntry	20 }

smscDiwermesIdiRecallQueues OBJECT-TYPE
		SYNTAX	Unsigned32
		MAX-ACCESS read-only
		STATUS current
		DESCRIPTION
			"Number of IDI recall-queues used"
	::= { diwermesInstanceEntry	21 }

smscDiwermesIosRecallQelem OBJECT-TYPE
		SYNTAX	Unsigned32
		MAX-ACCESS read-only
		STATUS current
		DESCRIPTION
			"Number of IOS recall-queue elements used"
	::= { diwermesInstanceEntry	22 }

smscDiwermesIosRecallQueues OBJECT-TYPE
		SYNTAX	Unsigned32
		MAX-ACCESS read-only
		STATUS current
		DESCRIPTION
			"Number of IOS recall-queues used"
	::= { diwermesInstanceEntry	23 }

smscDiwermesLogRecallQelem OBJECT-TYPE
		SYNTAX	Unsigned32
		MAX-ACCESS read-only
		STATUS current
		DESCRIPTION
			"Number of LOG recall-queue elements used"
	::= { diwermesInstanceEntry	24 }

smscDiwermesLogRecallQueues OBJECT-TYPE
		SYNTAX	Unsigned32
		MAX-ACCESS read-only
		STATUS current
		DESCRIPTION
			"Number of LOG recall-queues used"
	::= { diwermesInstanceEntry	25 }

smscDiwermesTrcreqDiscarded OBJECT-TYPE
		SYNTAX	Unsigned32
		MAX-ACCESS read-only
		STATUS current
		DESCRIPTION
			"Number of trace requests discarded"
	::= { diwermesInstanceEntry	26 }



-- end of DIWERMES description.
-- --------------------------------------


-- --------------------------------------
-- Class DIWTAP
-- 
smscDiwtap OBJECT-TYPE
	SYNTAX  SEQUENCE OF DiwtapInstanceEntry
	MAX-ACCESS  not-accessible
	STATUS  current
	DESCRIPTION
		"Mapping table for SMSC DIWTAP entities."
   ::= { smscClassDiw   6  }

diwtapInstanceEntry  OBJECT-TYPE
	SYNTAX DiwtapInstanceEntry
	MAX-ACCESS  not-accessible
	STATUS  current
	DESCRIPTION
		"An entry (row) in the entityInstanceTable."
	INDEX { IMPLIED smscDiwtapName }
   ::= { smscDiwtap 1 }

DiwtapInstanceEntry ::= SEQUENCE {
		smscDiwtapName     DisplayString,
		smscDiwtapState   INTEGER,
		smscDiwtapLastupdate   TimeTicks,
		smscDiwtapNode	   DisplayString, 
		smscDiwtapMsgReceived	 Unsigned32, 
		smscDiwtapMsgRejected	 Unsigned32, 
		smscDiwtapMsgTransmitted	 Unsigned32, 
		smscDiwtapMsgFailed	 Unsigned32, 
		smscDiwtapNotifPstnFailed	 Unsigned32, 
		smscDiwtapNotifX25Failed	 Unsigned32, 
		smscDiwtapNotifTcpFailed	 Unsigned32, 
		smscDiwtapSessRefPstn	 Unsigned32, 
		smscDiwtapSessRefX25	 Unsigned32, 
		smscDiwtapSessRefTcp	 Unsigned32, 
		smscDiwtapSmPstnFailed	 Unsigned32, 
		smscDiwtapSmVpFailed	 Unsigned32, 
		smscDiwtapNotifVpFailed	 Unsigned32, 
		smscDiwtapNotifPstnTransmitted	 Unsigned32, 
		smscDiwtapSmPstnTransmitted	 Unsigned32, 
		smscDiwtapLengthSmOutPstn	 Unsigned32, 
		smscDiwtapSmX25Failed	 Unsigned32, 
		smscDiwtapNotifX25Transmitted	 Unsigned32, 
		smscDiwtapSmX25Transmitted	 Unsigned32, 
		smscDiwtapLengthSmOutX25	 Unsigned32, 
		smscDiwtapSmTcpFailed	 Unsigned32, 
		smscDiwtapNotifTcpTransmitted	 Unsigned32, 
		smscDiwtapSmTcpTransmitted	 Unsigned32, 
		smscDiwtapLengthSmOutTcp	 Unsigned32, 
		smscDiwtapQelemUsed	 Unsigned32, 
		smscDiwtapQelemInProcqueue	 Unsigned32, 
		smscDiwtapQelemInExpqueue	 Unsigned32, 
		smscDiwtapNrTimersRunning	 Unsigned32, 
		smscDiwtapNrSystemTimers	 Unsigned32, 
		smscDiwtapImiRecallQelem	 Unsigned32, 
		smscDiwtapImiRecallQueues	 Unsigned32, 
		smscDiwtapIdiRecallQelem	 Unsigned32, 
		smscDiwtapIdiRecallQueues	 Unsigned32, 
		smscDiwtapIosRecallQelem	 Unsigned32, 
		smscDiwtapIosRecallQueues	 Unsigned32, 
		smscDiwtapLogRecallQelem	 Unsigned32, 
		smscDiwtapLogRecallQueues	 Unsigned32, 
		smscDiwtapTrcreqDiscarded	 Unsigned32, 
		smscDiwtapQueuedMsgs	 Unsigned32
	}

smscDiwtapName  OBJECT-TYPE
	SYNTAX  DisplayString
	MAX-ACCESS  read-only
	STATUS   current
	DESCRIPTION
		"Identifies the name of the entity."
   ::= {diwtapInstanceEntry 1 }

smscDiwtapState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { diwtapInstanceEntry 2 }


smscDiwtapLastupdate OBJECT-TYPE
		SYNTAX	TimeTicks
		MAX-ACCESS read-only
		STATUS current
		DESCRIPTION
			"Value which reflects the last time the entities fields have been updated"
	::= { diwtapInstanceEntry	3 }

smscDiwtapNode  OBJECT-TYPE
	SYNTAX  DisplayString
	MAX-ACCESS  read-only
	STATUS   current
	DESCRIPTION
		"Identifies the node the entity is running on."
   ::= {diwtapInstanceEntry 4 }

smscDiwtapMsgReceived OBJECT-TYPE
		SYNTAX	Unsigned32
		MAX-ACCESS read-only
		STATUS current
		DESCRIPTION
			"Received messages"
	::= { diwtapInstanceEntry	5 }

smscDiwtapMsgRejected OBJECT-TYPE
		SYNTAX	Unsigned32
		MAX-ACCESS read-only
		STATUS current
		DESCRIPTION
			"Received messages and rejected"
	::= { diwtapInstanceEntry	6 }

smscDiwtapMsgTransmitted OBJECT-TYPE
		SYNTAX	Unsigned32
		MAX-ACCESS read-only
		STATUS current
		DESCRIPTION
			"Transmitted messages"
	::= { diwtapInstanceEntry	7 }

smscDiwtapMsgFailed OBJECT-TYPE
		SYNTAX	Unsigned32
		MAX-ACCESS read-only
		STATUS current
		DESCRIPTION
			"Messages that failed on sending"
	::= { diwtapInstanceEntry	8 }

smscDiwtapNotifPstnFailed OBJECT-TYPE
		SYNTAX	Unsigned32
		MAX-ACCESS read-only
		STATUS current
		DESCRIPTION
			"Submitted notifications for PSTN that failed"
	::= { diwtapInstanceEntry	9 }

smscDiwtapNotifX25Failed OBJECT-TYPE
		SYNTAX	Unsigned32
		MAX-ACCESS read-only
		STATUS current
		DESCRIPTION
			"Submitted notifications for X25 that failed"
	::= { diwtapInstanceEntry	10 }

smscDiwtapNotifTcpFailed OBJECT-TYPE
		SYNTAX	Unsigned32
		MAX-ACCESS read-only
		STATUS current
		DESCRIPTION
			"Submitted notifications for TCP that failed"
	::= { diwtapInstanceEntry	11 }

smscDiwtapSessRefPstn OBJECT-TYPE
		SYNTAX	Unsigned32
		MAX-ACCESS read-only
		STATUS current
		DESCRIPTION
			"Refused sessions via PSTN"
	::= { diwtapInstanceEntry	12 }

smscDiwtapSessRefX25 OBJECT-TYPE
		SYNTAX	Unsigned32
		MAX-ACCESS read-only
		STATUS current
		DESCRIPTION
			"Refused sessions via X25"
	::= { diwtapInstanceEntry	13 }

smscDiwtapSessRefTcp OBJECT-TYPE
		SYNTAX	Unsigned32
		MAX-ACCESS read-only
		STATUS current
		DESCRIPTION
			"Refused sessions via TCP"
	::= { diwtapInstanceEntry	14 }

smscDiwtapSmPstnFailed OBJECT-TYPE
		SYNTAX	Unsigned32
		MAX-ACCESS read-only
		STATUS current
		DESCRIPTION
			"Short messages submitted to PSTN that failed"
	::= { diwtapInstanceEntry	15 }

smscDiwtapSmVpFailed OBJECT-TYPE
		SYNTAX	Unsigned32
		MAX-ACCESS read-only
		STATUS current
		DESCRIPTION
			"Failed short messages submitted and validity period exceeded"
	::= { diwtapInstanceEntry	16 }

smscDiwtapNotifVpFailed OBJECT-TYPE
		SYNTAX	Unsigned32
		MAX-ACCESS read-only
		STATUS current
		DESCRIPTION
			"Failed notifications with validity period exceeded"
	::= { diwtapInstanceEntry	17 }

smscDiwtapNotifPstnTransmitted OBJECT-TYPE
		SYNTAX	Unsigned32
		MAX-ACCESS read-only
		STATUS current
		DESCRIPTION
			"Transmitted notifications to PSTN"
	::= { diwtapInstanceEntry	18 }

smscDiwtapSmPstnTransmitted OBJECT-TYPE
		SYNTAX	Unsigned32
		MAX-ACCESS read-only
		STATUS current
		DESCRIPTION
			"Transmitted short messages to PSTN"
	::= { diwtapInstanceEntry	19 }

smscDiwtapLengthSmOutPstn OBJECT-TYPE
		SYNTAX	Unsigned32
		MAX-ACCESS read-only
		STATUS current
		DESCRIPTION
			"Accumulated length of short messages to PSTN"
	::= { diwtapInstanceEntry	20 }

smscDiwtapSmX25Failed OBJECT-TYPE
		SYNTAX	Unsigned32
		MAX-ACCESS read-only
		STATUS current
		DESCRIPTION
			"Short messages submitted to X25 that failed"
	::= { diwtapInstanceEntry	21 }

smscDiwtapNotifX25Transmitted OBJECT-TYPE
		SYNTAX	Unsigned32
		MAX-ACCESS read-only
		STATUS current
		DESCRIPTION
			"Transmitted notifications to X25"
	::= { diwtapInstanceEntry	22 }

smscDiwtapSmX25Transmitted OBJECT-TYPE
		SYNTAX	Unsigned32
		MAX-ACCESS read-only
		STATUS current
		DESCRIPTION
			"Transmitted short messages to X25"
	::= { diwtapInstanceEntry	23 }

smscDiwtapLengthSmOutX25 OBJECT-TYPE
		SYNTAX	Unsigned32
		MAX-ACCESS read-only
		STATUS current
		DESCRIPTION
			"Accumulated length of short messages to X25"
	::= { diwtapInstanceEntry	24 }

smscDiwtapSmTcpFailed OBJECT-TYPE
		SYNTAX	Unsigned32
		MAX-ACCESS read-only
		STATUS current
		DESCRIPTION
			"Short messages submitted to TCP that failed"
	::= { diwtapInstanceEntry	25 }

smscDiwtapNotifTcpTransmitted OBJECT-TYPE
		SYNTAX	Unsigned32
		MAX-ACCESS read-only
		STATUS current
		DESCRIPTION
			"Transmitted notifications to TCP"
	::= { diwtapInstanceEntry	26 }

smscDiwtapSmTcpTransmitted OBJECT-TYPE
		SYNTAX	Unsigned32
		MAX-ACCESS read-only
		STATUS current
		DESCRIPTION
			"Transmitted short messages to TCP"
	::= { diwtapInstanceEntry	27 }

smscDiwtapLengthSmOutTcp OBJECT-TYPE
		SYNTAX	Unsigned32
		MAX-ACCESS read-only
		STATUS current
		DESCRIPTION
			"Accumulated length of short messages to TCP"
	::= { diwtapInstanceEntry	28 }

smscDiwtapQelemUsed OBJECT-TYPE
		SYNTAX	Unsigned32
		MAX-ACCESS read-only
		STATUS current
		DESCRIPTION
			"Number of elements in internal queues"
	::= { diwtapInstanceEntry	29 }

smscDiwtapQelemInProcqueue OBJECT-TYPE
		SYNTAX	Unsigned32
		MAX-ACCESS read-only
		STATUS current
		DESCRIPTION
			"Number of elements used in process queue"
	::= { diwtapInstanceEntry	30 }

smscDiwtapQelemInExpqueue OBJECT-TYPE
		SYNTAX	Unsigned32
		MAX-ACCESS read-only
		STATUS current
		DESCRIPTION
			"Number of elements used in expedited queue"
	::= { diwtapInstanceEntry	31 }

smscDiwtapNrTimersRunning OBJECT-TYPE
		SYNTAX	Unsigned32
		MAX-ACCESS read-only
		STATUS current
		DESCRIPTION
			"Total number of timers running"
	::= { diwtapInstanceEntry	32 }

smscDiwtapNrSystemTimers OBJECT-TYPE
		SYNTAX	Unsigned32
		MAX-ACCESS read-only
		STATUS current
		DESCRIPTION
			"Number of system timers running"
	::= { diwtapInstanceEntry	33 }

smscDiwtapImiRecallQelem OBJECT-TYPE
		SYNTAX	Unsigned32
		MAX-ACCESS read-only
		STATUS current
		DESCRIPTION
			"Number of IMI recall-queue elements used"
	::= { diwtapInstanceEntry	34 }

smscDiwtapImiRecallQueues OBJECT-TYPE
		SYNTAX	Unsigned32
		MAX-ACCESS read-only
		STATUS current
		DESCRIPTION
			"Number of IMI-recall-queues used"
	::= { diwtapInstanceEntry	35 }

smscDiwtapIdiRecallQelem OBJECT-TYPE
		SYNTAX	Unsigned32
		MAX-ACCESS read-only
		STATUS current
		DESCRIPTION
			"Number of IDI recall-queue elements used"
	::= { diwtapInstanceEntry	36 }

smscDiwtapIdiRecallQueues OBJECT-TYPE
		SYNTAX	Unsigned32
		MAX-ACCESS read-only
		STATUS current
		DESCRIPTION
			"Number of IDI recall-queues used"
	::= { diwtapInstanceEntry	37 }

smscDiwtapIosRecallQelem OBJECT-TYPE
		SYNTAX	Unsigned32
		MAX-ACCESS read-only
		STATUS current
		DESCRIPTION
			"Number of IOS recall-queue elements used"
	::= { diwtapInstanceEntry	38 }

smscDiwtapIosRecallQueues OBJECT-TYPE
		SYNTAX	Unsigned32
		MAX-ACCESS read-only
		STATUS current
		DESCRIPTION
			"Number of IOS recall-queues used"
	::= { diwtapInstanceEntry	39 }

smscDiwtapLogRecallQelem OBJECT-TYPE
		SYNTAX	Unsigned32
		MAX-ACCESS read-only
		STATUS current
		DESCRIPTION
			"Number of LOG recall-queue elements used"
	::= { diwtapInstanceEntry	40 }

smscDiwtapLogRecallQueues OBJECT-TYPE
		SYNTAX	Unsigned32
		MAX-ACCESS read-only
		STATUS current
		DESCRIPTION
			"Number of LOG recall-queues used"
	::= { diwtapInstanceEntry	41 }

smscDiwtapTrcreqDiscarded OBJECT-TYPE
		SYNTAX	Unsigned32
		MAX-ACCESS read-only
		STATUS current
		DESCRIPTION
			"Number of trace requests discarded"
	::= { diwtapInstanceEntry	42 }

smscDiwtapQueuedMsgs OBJECT-TYPE
		SYNTAX	Unsigned32
		MAX-ACCESS read-only
		STATUS current
		DESCRIPTION
			"Number of messages queued"
	::= { diwtapInstanceEntry	43 }



-- end of DIWTAP description.
-- --------------------------------------


-- --------------------------------------
-- Class DIWOIS
-- 
smscDiwois OBJECT-TYPE
	SYNTAX  SEQUENCE OF DiwoisInstanceEntry
	MAX-ACCESS  not-accessible
	STATUS  current
	DESCRIPTION
		"Mapping table for SMSC DIWOIS entities."
   ::= { smscClassDiw   7  }

diwoisInstanceEntry  OBJECT-TYPE
	SYNTAX DiwoisInstanceEntry
	MAX-ACCESS  not-accessible
	STATUS  current
	DESCRIPTION
		"An entry (row) in the entityInstanceTable."
	INDEX { IMPLIED smscDiwoisName }
   ::= { smscDiwois 1 }

DiwoisInstanceEntry ::= SEQUENCE {
		smscDiwoisName     DisplayString,
		smscDiwoisState   INTEGER,
		smscDiwoisLastupdate   TimeTicks,
		smscDiwoisNode	   DisplayString, 
		smscDiwoisMsgReceived	 Unsigned32, 
		smscDiwoisMsgRejected	 Unsigned32, 
		smscDiwoisMsgTransmitted	 Unsigned32, 
		smscDiwoisMsgFailed	 Unsigned32, 
		smscDiwoisSessionsPending	 Unsigned32, 
		smscDiwoisQelemUsed	 Unsigned32, 
		smscDiwoisQelemInProcqueue	 Unsigned32, 
		smscDiwoisQelemInExpqueue	 Unsigned32, 
		smscDiwoisNrTimersRunning	 Unsigned32, 
		smscDiwoisNrSystemTimers	 Unsigned32, 
		smscDiwoisImiRecallQelem	 Unsigned32, 
		smscDiwoisImiRecallQueues	 Unsigned32, 
		smscDiwoisIdiRecallQelem	 Unsigned32, 
		smscDiwoisIdiRecallQueues	 Unsigned32, 
		smscDiwoisIosRecallQelem	 Unsigned32, 
		smscDiwoisIosRecallQueues	 Unsigned32, 
		smscDiwoisLogRecallQelem	 Unsigned32, 
		smscDiwoisLogRecallQueues	 Unsigned32, 
		smscDiwoisTrcreqDiscarded	 Unsigned32, 
		smscDiwoisNotifTcpTransmitted	 Unsigned32, 
		smscDiwoisNotifX25Transmitted	 Unsigned32, 
		smscDiwoisSmTcpTransmitted	 Unsigned32, 
		smscDiwoisSmX25Transmitted	 Unsigned32, 
		smscDiwoisSmTcpFailed	 Unsigned32, 
		smscDiwoisSmX25Failed	 Unsigned32, 
		smscDiwoisNotifTcpFailed	 Unsigned32, 
		smscDiwoisNotifX25Failed	 Unsigned32, 
		smscDiwoisTimeoutErrors	 Unsigned32, 
		smscDiwoisProtocolErrors	 Unsigned32, 
		smscDiwoisResourceErrors	 Unsigned32
	}

smscDiwoisName  OBJECT-TYPE
	SYNTAX  DisplayString
	MAX-ACCESS  read-only
	STATUS   current
	DESCRIPTION
		"Identifies the name of the entity."
   ::= {diwoisInstanceEntry 1 }

smscDiwoisState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { diwoisInstanceEntry 2 }


smscDiwoisLastupdate OBJECT-TYPE
		SYNTAX	TimeTicks
		MAX-ACCESS read-only
		STATUS current
		DESCRIPTION
			"Value which reflects the last time the entities fields have been updated"
	::= { diwoisInstanceEntry	3 }

smscDiwoisNode  OBJECT-TYPE
	SYNTAX  DisplayString
	MAX-ACCESS  read-only
	STATUS   current
	DESCRIPTION
		"Identifies the node the entity is running on."
   ::= {diwoisInstanceEntry 4 }

smscDiwoisMsgReceived OBJECT-TYPE
		SYNTAX	Unsigned32
		MAX-ACCESS read-only
		STATUS current
		DESCRIPTION
			"Received messages"
	::= { diwoisInstanceEntry	5 }

smscDiwoisMsgRejected OBJECT-TYPE
		SYNTAX	Unsigned32
		MAX-ACCESS read-only
		STATUS current
		DESCRIPTION
			"Received messages and rejected"
	::= { diwoisInstanceEntry	6 }

smscDiwoisMsgTransmitted OBJECT-TYPE
		SYNTAX	Unsigned32
		MAX-ACCESS read-only
		STATUS current
		DESCRIPTION
			"Transmitted messages"
	::= { diwoisInstanceEntry	7 }

smscDiwoisMsgFailed OBJECT-TYPE
		SYNTAX	Unsigned32
		MAX-ACCESS read-only
		STATUS current
		DESCRIPTION
			"Messages that failed on sending"
	::= { diwoisInstanceEntry	8 }

smscDiwoisSessionsPending OBJECT-TYPE
		SYNTAX	Unsigned32
		MAX-ACCESS read-only
		STATUS current
		DESCRIPTION
			"Number of sessions (currently) pending"
	::= { diwoisInstanceEntry	9 }

smscDiwoisQelemUsed OBJECT-TYPE
		SYNTAX	Unsigned32
		MAX-ACCESS read-only
		STATUS current
		DESCRIPTION
			"Number of elements in internal queues"
	::= { diwoisInstanceEntry	10 }

smscDiwoisQelemInProcqueue OBJECT-TYPE
		SYNTAX	Unsigned32
		MAX-ACCESS read-only
		STATUS current
		DESCRIPTION
			"Number of elements used in process queue"
	::= { diwoisInstanceEntry	11 }

smscDiwoisQelemInExpqueue OBJECT-TYPE
		SYNTAX	Unsigned32
		MAX-ACCESS read-only
		STATUS current
		DESCRIPTION
			"Number of elements used in expedited queue"
	::= { diwoisInstanceEntry	12 }

smscDiwoisNrTimersRunning OBJECT-TYPE
		SYNTAX	Unsigned32
		MAX-ACCESS read-only
		STATUS current
		DESCRIPTION
			"Total number of timers running"
	::= { diwoisInstanceEntry	13 }

smscDiwoisNrSystemTimers OBJECT-TYPE
		SYNTAX	Unsigned32
		MAX-ACCESS read-only
		STATUS current
		DESCRIPTION
			"Number of system timers running"
	::= { diwoisInstanceEntry	14 }

smscDiwoisImiRecallQelem OBJECT-TYPE
		SYNTAX	Unsigned32
		MAX-ACCESS read-only
		STATUS current
		DESCRIPTION
			"Number of IMI recall-queue elements used"
	::= { diwoisInstanceEntry	15 }

smscDiwoisImiRecallQueues OBJECT-TYPE
		SYNTAX	Unsigned32
		MAX-ACCESS read-only
		STATUS current
		DESCRIPTION
			"Number of IMI-recall-queues used"
	::= { diwoisInstanceEntry	16 }

smscDiwoisIdiRecallQelem OBJECT-TYPE
		SYNTAX	Unsigned32
		MAX-ACCESS read-only
		STATUS current
		DESCRIPTION
			"Number of IDI recall-queue elements used"
	::= { diwoisInstanceEntry	17 }

smscDiwoisIdiRecallQueues OBJECT-TYPE
		SYNTAX	Unsigned32
		MAX-ACCESS read-only
		STATUS current
		DESCRIPTION
			"Number of IDI recall-queues used"
	::= { diwoisInstanceEntry	18 }

smscDiwoisIosRecallQelem OBJECT-TYPE
		SYNTAX	Unsigned32
		MAX-ACCESS read-only
		STATUS current
		DESCRIPTION
			"Number of IOS recall-queue elements used"
	::= { diwoisInstanceEntry	19 }

smscDiwoisIosRecallQueues OBJECT-TYPE
		SYNTAX	Unsigned32
		MAX-ACCESS read-only
		STATUS current
		DESCRIPTION
			"Number of IOS recall-queues used"
	::= { diwoisInstanceEntry	20 }

smscDiwoisLogRecallQelem OBJECT-TYPE
		SYNTAX	Unsigned32
		MAX-ACCESS read-only
		STATUS current
		DESCRIPTION
			"Number of LOG recall-queue elements used"
	::= { diwoisInstanceEntry	21 }

smscDiwoisLogRecallQueues OBJECT-TYPE
		SYNTAX	Unsigned32
		MAX-ACCESS read-only
		STATUS current
		DESCRIPTION
			"Number of LOG recall-queues used"
	::= { diwoisInstanceEntry	22 }

smscDiwoisTrcreqDiscarded OBJECT-TYPE
		SYNTAX	Unsigned32
		MAX-ACCESS read-only
		STATUS current
		DESCRIPTION
			"Number of trace requests discarded"
	::= { diwoisInstanceEntry	23 }

smscDiwoisNotifTcpTransmitted OBJECT-TYPE
		SYNTAX	Unsigned32
		MAX-ACCESS read-only
		STATUS current
		DESCRIPTION
			"Nr. of notif. delivery attemps via TCP"
	::= { diwoisInstanceEntry	24 }

smscDiwoisNotifX25Transmitted OBJECT-TYPE
		SYNTAX	Unsigned32
		MAX-ACCESS read-only
		STATUS current
		DESCRIPTION
			"Nr. of notif. delivery attemps via X25"
	::= { diwoisInstanceEntry	25 }

smscDiwoisSmTcpTransmitted OBJECT-TYPE
		SYNTAX	Unsigned32
		MAX-ACCESS read-only
		STATUS current
		DESCRIPTION
			"Nr. of SMs delivery attemps via TCP"
	::= { diwoisInstanceEntry	26 }

smscDiwoisSmX25Transmitted OBJECT-TYPE
		SYNTAX	Unsigned32
		MAX-ACCESS read-only
		STATUS current
		DESCRIPTION
			"Nr. of SMs delivery attemps via X25"
	::= { diwoisInstanceEntry	27 }

smscDiwoisSmTcpFailed OBJECT-TYPE
		SYNTAX	Unsigned32
		MAX-ACCESS read-only
		STATUS current
		DESCRIPTION
			"Nr. of failed SMs delivery attemps via TCP"
	::= { diwoisInstanceEntry	28 }

smscDiwoisSmX25Failed OBJECT-TYPE
		SYNTAX	Unsigned32
		MAX-ACCESS read-only
		STATUS current
		DESCRIPTION
			"Nr. of failed SMs delivery attemps via X25"
	::= { diwoisInstanceEntry	29 }

smscDiwoisNotifTcpFailed OBJECT-TYPE
		SYNTAX	Unsigned32
		MAX-ACCESS read-only
		STATUS current
		DESCRIPTION
			"Nr. of failed notif. delivery attemps via TCP"
	::= { diwoisInstanceEntry	30 }

smscDiwoisNotifX25Failed OBJECT-TYPE
		SYNTAX	Unsigned32
		MAX-ACCESS read-only
		STATUS current
		DESCRIPTION
			"Nr. of failed notif. delivery attemps via X25"
	::= { diwoisInstanceEntry	31 }

smscDiwoisTimeoutErrors OBJECT-TYPE
		SYNTAX	Unsigned32
		MAX-ACCESS read-only
		STATUS current
		DESCRIPTION
			"Tot. nr. of timeouts on IW request"
	::= { diwoisInstanceEntry	32 }

smscDiwoisProtocolErrors OBJECT-TYPE
		SYNTAX	Unsigned32
		MAX-ACCESS read-only
		STATUS current
		DESCRIPTION
			"Tot. nr. of protocol errors"
	::= { diwoisInstanceEntry	33 }

smscDiwoisResourceErrors OBJECT-TYPE
		SYNTAX	Unsigned32
		MAX-ACCESS read-only
		STATUS current
		DESCRIPTION
			"Tot. nr. of resource errors"
	::= { diwoisInstanceEntry	34 }



-- end of DIWOIS description.
-- --------------------------------------


-- --------------------------------------
-- Class DIWCDMA
-- 
smscDiwcdma OBJECT-TYPE
	SYNTAX  SEQUENCE OF DiwcdmaInstanceEntry
	MAX-ACCESS  not-accessible
	STATUS  current
	DESCRIPTION
		"Mapping table for SMSC DIWCDMA entities."
   ::= { smscClassDiw   8  }

diwcdmaInstanceEntry  OBJECT-TYPE
	SYNTAX DiwcdmaInstanceEntry
	MAX-ACCESS  not-accessible
	STATUS  current
	DESCRIPTION
		"An entry (row) in the entityInstanceTable."
	INDEX { IMPLIED smscDiwcdmaName }
   ::= { smscDiwcdma 1 }

DiwcdmaInstanceEntry ::= SEQUENCE {
		smscDiwcdmaName     DisplayString,
		smscDiwcdmaState   INTEGER,
		smscDiwcdmaLastupdate   TimeTicks,
		smscDiwcdmaNode	   DisplayString, 
		smscDiwcdmaMsgReceived	 Unsigned32, 
		smscDiwcdmaMsgRejected	 Unsigned32, 
		smscDiwcdmaMsgTransmitted	 Unsigned32, 
		smscDiwcdmaNotifFailed	 Unsigned32, 
		smscDiwcdmaNotifTransmitted	 Unsigned32, 
		smscDiwcdmaSmFailed	 Unsigned32, 
		smscDiwcdmaSmTransmitted	 Unsigned32, 
		smscDiwcdmaMsgFailed	 Unsigned32, 
		smscDiwcdmaSmVpFailed	 Unsigned32, 
		smscDiwcdmaNotifVpFailed	 Unsigned32, 
		smscDiwcdmaLengthSmOutPlmn	 Unsigned32, 
		smscDiwcdmaQelemUsed	 Unsigned32, 
		smscDiwcdmaQelemInProcqueue	 Unsigned32, 
		smscDiwcdmaQelemInExpqueue	 Unsigned32, 
		smscDiwcdmaNrTimersRunning	 Unsigned32, 
		smscDiwcdmaNrSystemTimers	 Unsigned32, 
		smscDiwcdmaImiRecallQelem	 Unsigned32, 
		smscDiwcdmaImiRecallQueues	 Unsigned32, 
		smscDiwcdmaIdiRecallQelem	 Unsigned32, 
		smscDiwcdmaIdiRecallQueues	 Unsigned32, 
		smscDiwcdmaIosRecallQelem	 Unsigned32, 
		smscDiwcdmaIosRecallQueues	 Unsigned32, 
		smscDiwcdmaLogRecallQelem	 Unsigned32, 
		smscDiwcdmaLogRecallQueues	 Unsigned32, 
		smscDiwcdmaTrcreqDiscarded	 Unsigned32, 
		smscDiwcdmaSmsDeliverOk	 Unsigned32, 
		smscDiwcdmaSmsDeliverFail	 Unsigned32, 
		smscDiwcdmaSmsDelackOk	 Unsigned32, 
		smscDiwcdmaSmsDelackFail	 Unsigned32, 
		smscDiwcdmaSmsManackOk	 Unsigned32, 
		smscDiwcdmaSmsManackFail	 Unsigned32, 
		smscDiwcdmaSessionsPending	 Unsigned32, 
		smscDiwcdmaWemtFailUnsuppTsid	 Unsigned32, 
		smscDiwcdmaSmsReadackOk	 Unsigned32, 
		smscDiwcdmaSmsReadackFail	 Unsigned32
	}

smscDiwcdmaName  OBJECT-TYPE
	SYNTAX  DisplayString
	MAX-ACCESS  read-only
	STATUS   current
	DESCRIPTION
		"Identifies the name of the entity."
   ::= {diwcdmaInstanceEntry 1 }

smscDiwcdmaState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { diwcdmaInstanceEntry 2 }


smscDiwcdmaLastupdate OBJECT-TYPE
		SYNTAX	TimeTicks
		MAX-ACCESS read-only
		STATUS current
		DESCRIPTION
			"Value which reflects the last time the entities fields have been updated"
	::= { diwcdmaInstanceEntry	3 }

smscDiwcdmaNode  OBJECT-TYPE
	SYNTAX  DisplayString
	MAX-ACCESS  read-only
	STATUS   current
	DESCRIPTION
		"Identifies the node the entity is running on."
   ::= {diwcdmaInstanceEntry 4 }

smscDiwcdmaMsgReceived OBJECT-TYPE
		SYNTAX	Unsigned32
		MAX-ACCESS read-only
		STATUS current
		DESCRIPTION
			"Received messages"
	::= { diwcdmaInstanceEntry	5 }

smscDiwcdmaMsgRejected OBJECT-TYPE
		SYNTAX	Unsigned32
		MAX-ACCESS read-only
		STATUS current
		DESCRIPTION
			"Received messages and rejected"
	::= { diwcdmaInstanceEntry	6 }

smscDiwcdmaMsgTransmitted OBJECT-TYPE
		SYNTAX	Unsigned32
		MAX-ACCESS read-only
		STATUS current
		DESCRIPTION
			"Transmitted messages"
	::= { diwcdmaInstanceEntry	7 }

smscDiwcdmaNotifFailed OBJECT-TYPE
		SYNTAX	Unsigned32
		MAX-ACCESS read-only
		STATUS current
		DESCRIPTION
			"Notifications submitted and failed"
	::= { diwcdmaInstanceEntry	8 }

smscDiwcdmaNotifTransmitted OBJECT-TYPE
		SYNTAX	Unsigned32
		MAX-ACCESS read-only
		STATUS current
		DESCRIPTION
			"Transmitted notifications"
	::= { diwcdmaInstanceEntry	9 }

smscDiwcdmaSmFailed OBJECT-TYPE
		SYNTAX	Unsigned32
		MAX-ACCESS read-only
		STATUS current
		DESCRIPTION
			"Short messages submitted and failed"
	::= { diwcdmaInstanceEntry	10 }

smscDiwcdmaSmTransmitted OBJECT-TYPE
		SYNTAX	Unsigned32
		MAX-ACCESS read-only
		STATUS current
		DESCRIPTION
			"Transmitted short messages"
	::= { diwcdmaInstanceEntry	11 }

smscDiwcdmaMsgFailed OBJECT-TYPE
		SYNTAX	Unsigned32
		MAX-ACCESS read-only
		STATUS current
		DESCRIPTION
			"Messages that failed on sending"
	::= { diwcdmaInstanceEntry	12 }

smscDiwcdmaSmVpFailed OBJECT-TYPE
		SYNTAX	Unsigned32
		MAX-ACCESS read-only
		STATUS current
		DESCRIPTION
			"Failed short messages submitted and validity period exceeded"
	::= { diwcdmaInstanceEntry	13 }

smscDiwcdmaNotifVpFailed OBJECT-TYPE
		SYNTAX	Unsigned32
		MAX-ACCESS read-only
		STATUS current
		DESCRIPTION
			"Failed notifications with validity period exceeded"
	::= { diwcdmaInstanceEntry	14 }

smscDiwcdmaLengthSmOutPlmn OBJECT-TYPE
		SYNTAX	Unsigned32
		MAX-ACCESS read-only
		STATUS current
		DESCRIPTION
			"Accumulated length of short messages to PLMN"
	::= { diwcdmaInstanceEntry	15 }

smscDiwcdmaQelemUsed OBJECT-TYPE
		SYNTAX	Unsigned32
		MAX-ACCESS read-only
		STATUS current
		DESCRIPTION
			"Number of elements in internal queues"
	::= { diwcdmaInstanceEntry	16 }

smscDiwcdmaQelemInProcqueue OBJECT-TYPE
		SYNTAX	Unsigned32
		MAX-ACCESS read-only
		STATUS current
		DESCRIPTION
			"Number of elements used in process queue"
	::= { diwcdmaInstanceEntry	17 }

smscDiwcdmaQelemInExpqueue OBJECT-TYPE
		SYNTAX	Unsigned32
		MAX-ACCESS read-only
		STATUS current
		DESCRIPTION
			"Number of elements used in expedited queue"
	::= { diwcdmaInstanceEntry	18 }

smscDiwcdmaNrTimersRunning OBJECT-TYPE
		SYNTAX	Unsigned32
		MAX-ACCESS read-only
		STATUS current
		DESCRIPTION
			"Total number of timers running"
	::= { diwcdmaInstanceEntry	19 }

smscDiwcdmaNrSystemTimers OBJECT-TYPE
		SYNTAX	Unsigned32
		MAX-ACCESS read-only
		STATUS current
		DESCRIPTION
			"Number of system timers running"
	::= { diwcdmaInstanceEntry	20 }

smscDiwcdmaImiRecallQelem OBJECT-TYPE
		SYNTAX	Unsigned32
		MAX-ACCESS read-only
		STATUS current
		DESCRIPTION
			"Number of IMI recall-queue elements used"
	::= { diwcdmaInstanceEntry	21 }

smscDiwcdmaImiRecallQueues OBJECT-TYPE
		SYNTAX	Unsigned32
		MAX-ACCESS read-only
		STATUS current
		DESCRIPTION
			"Number of IMI-recall-queues used"
	::= { diwcdmaInstanceEntry	22 }

smscDiwcdmaIdiRecallQelem OBJECT-TYPE
		SYNTAX	Unsigned32
		MAX-ACCESS read-only
		STATUS current
		DESCRIPTION
			"Number of IDI recall-queue elements used"
	::= { diwcdmaInstanceEntry	23 }

smscDiwcdmaIdiRecallQueues OBJECT-TYPE
		SYNTAX	Unsigned32
		MAX-ACCESS read-only
		STATUS current
		DESCRIPTION
			"Number of IDI recall-queues used"
	::= { diwcdmaInstanceEntry	24 }

smscDiwcdmaIosRecallQelem OBJECT-TYPE
		SYNTAX	Unsigned32
		MAX-ACCESS read-only
		STATUS current
		DESCRIPTION
			"Number of IOS recall-queue elements used"
	::= { diwcdmaInstanceEntry	25 }

smscDiwcdmaIosRecallQueues OBJECT-TYPE
		SYNTAX	Unsigned32
		MAX-ACCESS read-only
		STATUS current
		DESCRIPTION
			"Number of IOS recall-queues used"
	::= { diwcdmaInstanceEntry	26 }

smscDiwcdmaLogRecallQelem OBJECT-TYPE
		SYNTAX	Unsigned32
		MAX-ACCESS read-only
		STATUS current
		DESCRIPTION
			"Number of LOG recall-queue elements used"
	::= { diwcdmaInstanceEntry	27 }

smscDiwcdmaLogRecallQueues OBJECT-TYPE
		SYNTAX	Unsigned32
		MAX-ACCESS read-only
		STATUS current
		DESCRIPTION
			"Number of LOG recall-queues used"
	::= { diwcdmaInstanceEntry	28 }

smscDiwcdmaTrcreqDiscarded OBJECT-TYPE
		SYNTAX	Unsigned32
		MAX-ACCESS read-only
		STATUS current
		DESCRIPTION
			"Number of trace requests discarded"
	::= { diwcdmaInstanceEntry	29 }

smscDiwcdmaSmsDeliverOk OBJECT-TYPE
		SYNTAX	Unsigned32
		MAX-ACCESS read-only
		STATUS current
		DESCRIPTION
			"Number of SMS DELIVER messages succesfullydelivered"
	::= { diwcdmaInstanceEntry	30 }

smscDiwcdmaSmsDeliverFail OBJECT-TYPE
		SYNTAX	Unsigned32
		MAX-ACCESS read-only
		STATUS current
		DESCRIPTION
			"Number of SMS DELIVER messages that failed"
	::= { diwcdmaInstanceEntry	31 }

smscDiwcdmaSmsDelackOk OBJECT-TYPE
		SYNTAX	Unsigned32
		MAX-ACCESS read-only
		STATUS current
		DESCRIPTION
			"Number of SMS DELIVERY ACK messages succesfullydelivered"
	::= { diwcdmaInstanceEntry	32 }

smscDiwcdmaSmsDelackFail OBJECT-TYPE
		SYNTAX	Unsigned32
		MAX-ACCESS read-only
		STATUS current
		DESCRIPTION
			"Number of SMS DELIVERY ACK messages that failed"
	::= { diwcdmaInstanceEntry	33 }

smscDiwcdmaSmsManackOk OBJECT-TYPE
		SYNTAX	Unsigned32
		MAX-ACCESS read-only
		STATUS current
		DESCRIPTION
			"Number of SMS MANUAL ACK messages succesfullydelivered"
	::= { diwcdmaInstanceEntry	34 }

smscDiwcdmaSmsManackFail OBJECT-TYPE
		SYNTAX	Unsigned32
		MAX-ACCESS read-only
		STATUS current
		DESCRIPTION
			"Number of SMS MANUAL ACK messages that failed"
	::= { diwcdmaInstanceEntry	35 }

smscDiwcdmaSessionsPending OBJECT-TYPE
		SYNTAX	Unsigned32
		MAX-ACCESS read-only
		STATUS current
		DESCRIPTION
			"Number of sessions (currently) pending"
	::= { diwcdmaInstanceEntry	36 }

smscDiwcdmaWemtFailUnsuppTsid OBJECT-TYPE
		SYNTAX	Unsigned32
		MAX-ACCESS read-only
		STATUS current
		DESCRIPTION
			"Number of failed messages with unsupported WEMT"
	::= { diwcdmaInstanceEntry	37 }

smscDiwcdmaSmsReadackOk OBJECT-TYPE
		SYNTAX	Unsigned32
		MAX-ACCESS read-only
		STATUS current
		DESCRIPTION
			"Number of SMS READ ACK messages succesfullydelivered"
	::= { diwcdmaInstanceEntry	38 }

smscDiwcdmaSmsReadackFail OBJECT-TYPE
		SYNTAX	Unsigned32
		MAX-ACCESS read-only
		STATUS current
		DESCRIPTION
			"Number of SMS READ ACK messages that failed"
	::= { diwcdmaInstanceEntry	39 }



-- end of DIWCDMA description.
-- --------------------------------------


-- --------------------------------------
-- Class DIWSMTP
-- 
smscDiwsmtp OBJECT-TYPE
	SYNTAX  SEQUENCE OF DiwsmtpInstanceEntry
	MAX-ACCESS  not-accessible
	STATUS  current
	DESCRIPTION
		"Mapping table for SMSC DIWSMTP entities."
   ::= { smscClassDiw   9  }

diwsmtpInstanceEntry  OBJECT-TYPE
	SYNTAX DiwsmtpInstanceEntry
	MAX-ACCESS  not-accessible
	STATUS  current
	DESCRIPTION
		"An entry (row) in the entityInstanceTable."
	INDEX { IMPLIED smscDiwsmtpName }
   ::= { smscDiwsmtp 1 }

DiwsmtpInstanceEntry ::= SEQUENCE {
		smscDiwsmtpName     DisplayString,
		smscDiwsmtpState   INTEGER,
		smscDiwsmtpLastupdate   TimeTicks,
		smscDiwsmtpNode	   DisplayString, 
		smscDiwsmtpMsgReceived	 Unsigned32, 
		smscDiwsmtpMsgRejected	 Unsigned32, 
		smscDiwsmtpMsgTransmitted	 Unsigned32, 
		smscDiwsmtpMsgFailed	 Unsigned32, 
		smscDiwsmtpQelemUsed	 Unsigned32, 
		smscDiwsmtpQelemInProcqueue	 Unsigned32, 
		smscDiwsmtpQelemInExpqueue	 Unsigned32, 
		smscDiwsmtpNrTimersRunning	 Unsigned32, 
		smscDiwsmtpNrSystemTimers	 Unsigned32, 
		smscDiwsmtpImiRecallQelem	 Unsigned32, 
		smscDiwsmtpImiRecallQueues	 Unsigned32, 
		smscDiwsmtpIdiRecallQelem	 Unsigned32, 
		smscDiwsmtpIdiRecallQueues	 Unsigned32, 
		smscDiwsmtpIosRecallQelem	 Unsigned32, 
		smscDiwsmtpIosRecallQueues	 Unsigned32, 
		smscDiwsmtpLogRecallQelem	 Unsigned32, 
		smscDiwsmtpLogRecallQueues	 Unsigned32, 
		smscDiwsmtpTrcreqDiscarded	 Unsigned32, 
		smscDiwsmtpNrSessionTimeout	 Unsigned32, 
		smscDiwsmtpNrInitialTimeout	 Unsigned32, 
		smscDiwsmtpNrMailTimeout	 Unsigned32, 
		smscDiwsmtpNrRcptTimeout	 Unsigned32, 
		smscDiwsmtpNrDataInitTimeout	 Unsigned32, 
		smscDiwsmtpNrDataTerminTimeout	 Unsigned32, 
		smscDiwsmtpSmTransmitted	 Unsigned32, 
		smscDiwsmtpSmFailed	 Unsigned32, 
		smscDiwsmtpSessPending	 Unsigned32
	}

smscDiwsmtpName  OBJECT-TYPE
	SYNTAX  DisplayString
	MAX-ACCESS  read-only
	STATUS   current
	DESCRIPTION
		"Identifies the name of the entity."
   ::= {diwsmtpInstanceEntry 1 }

smscDiwsmtpState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { diwsmtpInstanceEntry 2 }


smscDiwsmtpLastupdate OBJECT-TYPE
		SYNTAX	TimeTicks
		MAX-ACCESS read-only
		STATUS current
		DESCRIPTION
			"Value which reflects the last time the entities fields have been updated"
	::= { diwsmtpInstanceEntry	3 }

smscDiwsmtpNode  OBJECT-TYPE
	SYNTAX  DisplayString
	MAX-ACCESS  read-only
	STATUS   current
	DESCRIPTION
		"Identifies the node the entity is running on."
   ::= {diwsmtpInstanceEntry 4 }

smscDiwsmtpMsgReceived OBJECT-TYPE
		SYNTAX	Unsigned32
		MAX-ACCESS read-only
		STATUS current
		DESCRIPTION
			"Received messages"
	::= { diwsmtpInstanceEntry	5 }

smscDiwsmtpMsgRejected OBJECT-TYPE
		SYNTAX	Unsigned32
		MAX-ACCESS read-only
		STATUS current
		DESCRIPTION
			"Received messages and rejected"
	::= { diwsmtpInstanceEntry	6 }

smscDiwsmtpMsgTransmitted OBJECT-TYPE
		SYNTAX	Unsigned32
		MAX-ACCESS read-only
		STATUS current
		DESCRIPTION
			"Transmitted messages"
	::= { diwsmtpInstanceEntry	7 }

smscDiwsmtpMsgFailed OBJECT-TYPE
		SYNTAX	Unsigned32
		MAX-ACCESS read-only
		STATUS current
		DESCRIPTION
			"Messages that failed on sending"
	::= { diwsmtpInstanceEntry	8 }

smscDiwsmtpQelemUsed OBJECT-TYPE
		SYNTAX	Unsigned32
		MAX-ACCESS read-only
		STATUS current
		DESCRIPTION
			"Number of elements in internal queues"
	::= { diwsmtpInstanceEntry	9 }

smscDiwsmtpQelemInProcqueue OBJECT-TYPE
		SYNTAX	Unsigned32
		MAX-ACCESS read-only
		STATUS current
		DESCRIPTION
			"Number of elements used in process queue"
	::= { diwsmtpInstanceEntry	10 }

smscDiwsmtpQelemInExpqueue OBJECT-TYPE
		SYNTAX	Unsigned32
		MAX-ACCESS read-only
		STATUS current
		DESCRIPTION
			"Number of elements used in expedited queue"
	::= { diwsmtpInstanceEntry	11 }

smscDiwsmtpNrTimersRunning OBJECT-TYPE
		SYNTAX	Unsigned32
		MAX-ACCESS read-only
		STATUS current
		DESCRIPTION
			"Total number of timers running"
	::= { diwsmtpInstanceEntry	12 }

smscDiwsmtpNrSystemTimers OBJECT-TYPE
		SYNTAX	Unsigned32
		MAX-ACCESS read-only
		STATUS current
		DESCRIPTION
			"Number of system timers running"
	::= { diwsmtpInstanceEntry	13 }

smscDiwsmtpImiRecallQelem OBJECT-TYPE
		SYNTAX	Unsigned32
		MAX-ACCESS read-only
		STATUS current
		DESCRIPTION
			"Number of IMI recall-queue elements used"
	::= { diwsmtpInstanceEntry	14 }

smscDiwsmtpImiRecallQueues OBJECT-TYPE
		SYNTAX	Unsigned32
		MAX-ACCESS read-only
		STATUS current
		DESCRIPTION
			"Number of IMI-recall-queues used"
	::= { diwsmtpInstanceEntry	15 }

smscDiwsmtpIdiRecallQelem OBJECT-TYPE
		SYNTAX	Unsigned32
		MAX-ACCESS read-only
		STATUS current
		DESCRIPTION
			"Number of IDI recall-queue elements used"
	::= { diwsmtpInstanceEntry	16 }

smscDiwsmtpIdiRecallQueues OBJECT-TYPE
		SYNTAX	Unsigned32
		MAX-ACCESS read-only
		STATUS current
		DESCRIPTION
			"Number of IDI recall-queues used"
	::= { diwsmtpInstanceEntry	17 }

smscDiwsmtpIosRecallQelem OBJECT-TYPE
		SYNTAX	Unsigned32
		MAX-ACCESS read-only
		STATUS current
		DESCRIPTION
			"Number of IOS recall-queue elements used"
	::= { diwsmtpInstanceEntry	18 }

smscDiwsmtpIosRecallQueues OBJECT-TYPE
		SYNTAX	Unsigned32
		MAX-ACCESS read-only
		STATUS current
		DESCRIPTION
			"Number of IOS recall-queues used"
	::= { diwsmtpInstanceEntry	19 }

smscDiwsmtpLogRecallQelem OBJECT-TYPE
		SYNTAX	Unsigned32
		MAX-ACCESS read-only
		STATUS current
		DESCRIPTION
			"Number of LOG recall-queue elements used"
	::= { diwsmtpInstanceEntry	20 }

smscDiwsmtpLogRecallQueues OBJECT-TYPE
		SYNTAX	Unsigned32
		MAX-ACCESS read-only
		STATUS current
		DESCRIPTION
			"Number of LOG recall-queues used"
	::= { diwsmtpInstanceEntry	21 }

smscDiwsmtpTrcreqDiscarded OBJECT-TYPE
		SYNTAX	Unsigned32
		MAX-ACCESS read-only
		STATUS current
		DESCRIPTION
			"Number of trace requests discarded"
	::= { diwsmtpInstanceEntry	22 }

smscDiwsmtpNrSessionTimeout OBJECT-TYPE
		SYNTAX	Unsigned32
		MAX-ACCESS read-only
		STATUS current
		DESCRIPTION
			"SMTP Number of session timeouts"
	::= { diwsmtpInstanceEntry	23 }

smscDiwsmtpNrInitialTimeout OBJECT-TYPE
		SYNTAX	Unsigned32
		MAX-ACCESS read-only
		STATUS current
		DESCRIPTION
			"SMTP Number of initial timeouts"
	::= { diwsmtpInstanceEntry	24 }

smscDiwsmtpNrMailTimeout OBJECT-TYPE
		SYNTAX	Unsigned32
		MAX-ACCESS read-only
		STATUS current
		DESCRIPTION
			"SMTP Number of MAIL timeouts"
	::= { diwsmtpInstanceEntry	25 }

smscDiwsmtpNrRcptTimeout OBJECT-TYPE
		SYNTAX	Unsigned32
		MAX-ACCESS read-only
		STATUS current
		DESCRIPTION
			"SMTP Number of RCPT timeouts"
	::= { diwsmtpInstanceEntry	26 }

smscDiwsmtpNrDataInitTimeout OBJECT-TYPE
		SYNTAX	Unsigned32
		MAX-ACCESS read-only
		STATUS current
		DESCRIPTION
			"SMTP Number of DATA Initiation timeouts"
	::= { diwsmtpInstanceEntry	27 }

smscDiwsmtpNrDataTerminTimeout OBJECT-TYPE
		SYNTAX	Unsigned32
		MAX-ACCESS read-only
		STATUS current
		DESCRIPTION
			"SMTP Number of DATA Termination timeouts"
	::= { diwsmtpInstanceEntry	28 }

smscDiwsmtpSmTransmitted OBJECT-TYPE
		SYNTAX	Unsigned32
		MAX-ACCESS read-only
		STATUS current
		DESCRIPTION
			"Number of delivery attempts"
	::= { diwsmtpInstanceEntry	29 }

smscDiwsmtpSmFailed OBJECT-TYPE
		SYNTAX	Unsigned32
		MAX-ACCESS read-only
		STATUS current
		DESCRIPTION
			"Number of failed delivery attempts"
	::= { diwsmtpInstanceEntry	30 }

smscDiwsmtpSessPending OBJECT-TYPE
		SYNTAX	Unsigned32
		MAX-ACCESS read-only
		STATUS current
		DESCRIPTION
			"Number of sessions (currently) pending"
	::= { diwsmtpInstanceEntry	31 }



-- end of DIWSMTP description.
-- --------------------------------------


-- --------------------------------------
-- Class DIWTDMA
-- 
smscDiwtdma OBJECT-TYPE
	SYNTAX  SEQUENCE OF DiwtdmaInstanceEntry
	MAX-ACCESS  not-accessible
	STATUS  current
	DESCRIPTION
		"Mapping table for SMSC DIWTDMA entities."
   ::= { smscClassDiw   10  }

diwtdmaInstanceEntry  OBJECT-TYPE
	SYNTAX DiwtdmaInstanceEntry
	MAX-ACCESS  not-accessible
	STATUS  current
	DESCRIPTION
		"An entry (row) in the entityInstanceTable."
	INDEX { IMPLIED smscDiwtdmaName }
   ::= { smscDiwtdma 1 }

DiwtdmaInstanceEntry ::= SEQUENCE {
		smscDiwtdmaName     DisplayString,
		smscDiwtdmaState   INTEGER,
		smscDiwtdmaLastupdate   TimeTicks,
		smscDiwtdmaNode	   DisplayString, 
		smscDiwtdmaMsgReceived	 Unsigned32, 
		smscDiwtdmaMsgRejected	 Unsigned32, 
		smscDiwtdmaMsgTransmitted	 Unsigned32, 
		smscDiwtdmaNotifFailed	 Unsigned32, 
		smscDiwtdmaNotifTransmitted	 Unsigned32, 
		smscDiwtdmaSmFailed	 Unsigned32, 
		smscDiwtdmaSmTransmitted	 Unsigned32, 
		smscDiwtdmaMsgFailed	 Unsigned32, 
		smscDiwtdmaSmVpFailed	 Unsigned32, 
		smscDiwtdmaNotifVpFailed	 Unsigned32, 
		smscDiwtdmaLengthSmOutPlmn	 Unsigned32, 
		smscDiwtdmaQelemUsed	 Unsigned32, 
		smscDiwtdmaQelemInProcqueue	 Unsigned32, 
		smscDiwtdmaQelemInExpqueue	 Unsigned32, 
		smscDiwtdmaNrTimersRunning	 Unsigned32, 
		smscDiwtdmaNrSystemTimers	 Unsigned32, 
		smscDiwtdmaImiRecallQelem	 Unsigned32, 
		smscDiwtdmaImiRecallQueues	 Unsigned32, 
		smscDiwtdmaIdiRecallQelem	 Unsigned32, 
		smscDiwtdmaIdiRecallQueues	 Unsigned32, 
		smscDiwtdmaIosRecallQelem	 Unsigned32, 
		smscDiwtdmaIosRecallQueues	 Unsigned32, 
		smscDiwtdmaLogRecallQelem	 Unsigned32, 
		smscDiwtdmaLogRecallQueues	 Unsigned32, 
		smscDiwtdmaTrcreqDiscarded	 Unsigned32, 
		smscDiwtdmaSmsDeliverOk	 Unsigned32, 
		smscDiwtdmaSmsDeliverFail	 Unsigned32, 
		smscDiwtdmaSmsDelackOk	 Unsigned32, 
		smscDiwtdmaSmsDelackFail	 Unsigned32, 
		smscDiwtdmaSmsManackOk	 Unsigned32, 
		smscDiwtdmaSmsManackFail	 Unsigned32, 
		smscDiwtdmaSessionsPending	 Unsigned32
	}

smscDiwtdmaName  OBJECT-TYPE
	SYNTAX  DisplayString
	MAX-ACCESS  read-only
	STATUS   current
	DESCRIPTION
		"Identifies the name of the entity."
   ::= {diwtdmaInstanceEntry 1 }

smscDiwtdmaState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { diwtdmaInstanceEntry 2 }


smscDiwtdmaLastupdate OBJECT-TYPE
		SYNTAX	TimeTicks
		MAX-ACCESS read-only
		STATUS current
		DESCRIPTION
			"Value which reflects the last time the entities fields have been updated"
	::= { diwtdmaInstanceEntry	3 }

smscDiwtdmaNode  OBJECT-TYPE
	SYNTAX  DisplayString
	MAX-ACCESS  read-only
	STATUS   current
	DESCRIPTION
		"Identifies the node the entity is running on."
   ::= {diwtdmaInstanceEntry 4 }

smscDiwtdmaMsgReceived OBJECT-TYPE
		SYNTAX	Unsigned32
		MAX-ACCESS read-only
		STATUS current
		DESCRIPTION
			"Received messages"
	::= { diwtdmaInstanceEntry	5 }

smscDiwtdmaMsgRejected OBJECT-TYPE
		SYNTAX	Unsigned32
		MAX-ACCESS read-only
		STATUS current
		DESCRIPTION
			"Received messages and rejected"
	::= { diwtdmaInstanceEntry	6 }

smscDiwtdmaMsgTransmitted OBJECT-TYPE
		SYNTAX	Unsigned32
		MAX-ACCESS read-only
		STATUS current
		DESCRIPTION
			"Transmitted messages"
	::= { diwtdmaInstanceEntry	7 }

smscDiwtdmaNotifFailed OBJECT-TYPE
		SYNTAX	Unsigned32
		MAX-ACCESS read-only
		STATUS current
		DESCRIPTION
			"Notifications submitted and failed"
	::= { diwtdmaInstanceEntry	8 }

smscDiwtdmaNotifTransmitted OBJECT-TYPE
		SYNTAX	Unsigned32
		MAX-ACCESS read-only
		STATUS current
		DESCRIPTION
			"Transmitted notifications"
	::= { diwtdmaInstanceEntry	9 }

smscDiwtdmaSmFailed OBJECT-TYPE
		SYNTAX	Unsigned32
		MAX-ACCESS read-only
		STATUS current
		DESCRIPTION
			"Short messages submitted and failed"
	::= { diwtdmaInstanceEntry	10 }

smscDiwtdmaSmTransmitted OBJECT-TYPE
		SYNTAX	Unsigned32
		MAX-ACCESS read-only
		STATUS current
		DESCRIPTION
			"Transmitted short messages"
	::= { diwtdmaInstanceEntry	11 }

smscDiwtdmaMsgFailed OBJECT-TYPE
		SYNTAX	Unsigned32
		MAX-ACCESS read-only
		STATUS current
		DESCRIPTION
			"Messages that failed on sending"
	::= { diwtdmaInstanceEntry	12 }

smscDiwtdmaSmVpFailed OBJECT-TYPE
		SYNTAX	Unsigned32
		MAX-ACCESS read-only
		STATUS current
		DESCRIPTION
			"Failed short messages submitted and validity period exceeded"
	::= { diwtdmaInstanceEntry	13 }

smscDiwtdmaNotifVpFailed OBJECT-TYPE
		SYNTAX	Unsigned32
		MAX-ACCESS read-only
		STATUS current
		DESCRIPTION
			"Failed notifications with validity period exceeded"
	::= { diwtdmaInstanceEntry	14 }

smscDiwtdmaLengthSmOutPlmn OBJECT-TYPE
		SYNTAX	Unsigned32
		MAX-ACCESS read-only
		STATUS current
		DESCRIPTION
			"Accumulated length of short messages to PLMN"
	::= { diwtdmaInstanceEntry	15 }

smscDiwtdmaQelemUsed OBJECT-TYPE
		SYNTAX	Unsigned32
		MAX-ACCESS read-only
		STATUS current
		DESCRIPTION
			"Number of elements in internal queues"
	::= { diwtdmaInstanceEntry	16 }

smscDiwtdmaQelemInProcqueue OBJECT-TYPE
		SYNTAX	Unsigned32
		MAX-ACCESS read-only
		STATUS current
		DESCRIPTION
			"Number of elements used in process queue"
	::= { diwtdmaInstanceEntry	17 }

smscDiwtdmaQelemInExpqueue OBJECT-TYPE
		SYNTAX	Unsigned32
		MAX-ACCESS read-only
		STATUS current
		DESCRIPTION
			"Number of elements used in expedited queue"
	::= { diwtdmaInstanceEntry	18 }

smscDiwtdmaNrTimersRunning OBJECT-TYPE
		SYNTAX	Unsigned32
		MAX-ACCESS read-only
		STATUS current
		DESCRIPTION
			"Total number of timers running"
	::= { diwtdmaInstanceEntry	19 }

smscDiwtdmaNrSystemTimers OBJECT-TYPE
		SYNTAX	Unsigned32
		MAX-ACCESS read-only
		STATUS current
		DESCRIPTION
			"Number of system timers running"
	::= { diwtdmaInstanceEntry	20 }

smscDiwtdmaImiRecallQelem OBJECT-TYPE
		SYNTAX	Unsigned32
		MAX-ACCESS read-only
		STATUS current
		DESCRIPTION
			"Number of IMI recall-queue elements used"
	::= { diwtdmaInstanceEntry	21 }

smscDiwtdmaImiRecallQueues OBJECT-TYPE
		SYNTAX	Unsigned32
		MAX-ACCESS read-only
		STATUS current
		DESCRIPTION
			"Number of IMI-recall-queues used"
	::= { diwtdmaInstanceEntry	22 }

smscDiwtdmaIdiRecallQelem OBJECT-TYPE
		SYNTAX	Unsigned32
		MAX-ACCESS read-only
		STATUS current
		DESCRIPTION
			"Number of IDI recall-queue elements used"
	::= { diwtdmaInstanceEntry	23 }

smscDiwtdmaIdiRecallQueues OBJECT-TYPE
		SYNTAX	Unsigned32
		MAX-ACCESS read-only
		STATUS current
		DESCRIPTION
			"Number of IDI recall-queues used"
	::= { diwtdmaInstanceEntry	24 }

smscDiwtdmaIosRecallQelem OBJECT-TYPE
		SYNTAX	Unsigned32
		MAX-ACCESS read-only
		STATUS current
		DESCRIPTION
			"Number of IOS recall-queue elements used"
	::= { diwtdmaInstanceEntry	25 }

smscDiwtdmaIosRecallQueues OBJECT-TYPE
		SYNTAX	Unsigned32
		MAX-ACCESS read-only
		STATUS current
		DESCRIPTION
			"Number of IOS recall-queues used"
	::= { diwtdmaInstanceEntry	26 }

smscDiwtdmaLogRecallQelem OBJECT-TYPE
		SYNTAX	Unsigned32
		MAX-ACCESS read-only
		STATUS current
		DESCRIPTION
			"Number of LOG recall-queue elements used"
	::= { diwtdmaInstanceEntry	27 }

smscDiwtdmaLogRecallQueues OBJECT-TYPE
		SYNTAX	Unsigned32
		MAX-ACCESS read-only
		STATUS current
		DESCRIPTION
			"Number of LOG recall-queues used"
	::= { diwtdmaInstanceEntry	28 }

smscDiwtdmaTrcreqDiscarded OBJECT-TYPE
		SYNTAX	Unsigned32
		MAX-ACCESS read-only
		STATUS current
		DESCRIPTION
			"Number of trace requests discarded"
	::= { diwtdmaInstanceEntry	29 }

smscDiwtdmaSmsDeliverOk OBJECT-TYPE
		SYNTAX	Unsigned32
		MAX-ACCESS read-only
		STATUS current
		DESCRIPTION
			"SMS DELIVER messages succesfullydelivered"
	::= { diwtdmaInstanceEntry	30 }

smscDiwtdmaSmsDeliverFail OBJECT-TYPE
		SYNTAX	Unsigned32
		MAX-ACCESS read-only
		STATUS current
		DESCRIPTION
			"SMS DELIVER messages that failed"
	::= { diwtdmaInstanceEntry	31 }

smscDiwtdmaSmsDelackOk OBJECT-TYPE
		SYNTAX	Unsigned32
		MAX-ACCESS read-only
		STATUS current
		DESCRIPTION
			"SMS DELIVERY ACK messages succesfullydelivered"
	::= { diwtdmaInstanceEntry	32 }

smscDiwtdmaSmsDelackFail OBJECT-TYPE
		SYNTAX	Unsigned32
		MAX-ACCESS read-only
		STATUS current
		DESCRIPTION
			"SMS DELIVERY ACK messages that failed"
	::= { diwtdmaInstanceEntry	33 }

smscDiwtdmaSmsManackOk OBJECT-TYPE
		SYNTAX	Unsigned32
		MAX-ACCESS read-only
		STATUS current
		DESCRIPTION
			"SMS MANUAL ACK messages succesfullydelivered"
	::= { diwtdmaInstanceEntry	34 }

smscDiwtdmaSmsManackFail OBJECT-TYPE
		SYNTAX	Unsigned32
		MAX-ACCESS read-only
		STATUS current
		DESCRIPTION
			"SMS MANUAL ACK messages that failed"
	::= { diwtdmaInstanceEntry	35 }

smscDiwtdmaSessionsPending OBJECT-TYPE
		SYNTAX	Unsigned32
		MAX-ACCESS read-only
		STATUS current
		DESCRIPTION
			"Number of sessions (currently) pending"
	::= { diwtdmaInstanceEntry	36 }



-- end of DIWTDMA description.
-- --------------------------------------


-- --------------------------------------
-- Class ENUM
-- 
smscEnum OBJECT-TYPE
	SYNTAX  SEQUENCE OF EnumInstanceEntry
	MAX-ACCESS  not-accessible
	STATUS  current
	DESCRIPTION
		"Mapping table for SMSC ENUM entities."
   ::= { smscClassDiw   11  }

enumInstanceEntry  OBJECT-TYPE
	SYNTAX EnumInstanceEntry
	MAX-ACCESS  not-accessible
	STATUS  current
	DESCRIPTION
		"An entry (row) in the entityInstanceTable."
	INDEX { IMPLIED smscEnumName }
   ::= { smscEnum 1 }

EnumInstanceEntry ::= SEQUENCE {
		smscEnumName     DisplayString,
		smscEnumState   INTEGER,
		smscEnumLastupdate   TimeTicks,
		smscEnumNode	   DisplayString, 
		smscEnumMsgReceived	 Unsigned32, 
		smscEnumMsgRejected	 Unsigned32, 
		smscEnumMsgTransmitted	 Unsigned32, 
		smscEnumMsgFailed	 Unsigned32, 
		smscEnumQelemUsed	 Unsigned32, 
		smscEnumQelemInProcqueue	 Unsigned32, 
		smscEnumQelemInExpqueue	 Unsigned32, 
		smscEnumNrTimersRunning	 Unsigned32, 
		smscEnumNrSystemTimers	 Unsigned32, 
		smscEnumImiRecallQelem	 Unsigned32, 
		smscEnumImiRecallQueues	 Unsigned32, 
		smscEnumIdiRecallQelem	 Unsigned32, 
		smscEnumIdiRecallQueues	 Unsigned32, 
		smscEnumIosRecallQelem	 Unsigned32, 
		smscEnumIosRecallQueues	 Unsigned32, 
		smscEnumLogRecallQelem	 Unsigned32, 
		smscEnumLogRecallQueues	 Unsigned32, 
		smscEnumTrcreqDiscarded	 Unsigned32, 
		smscEnumSentQueriesS	 Unsigned32, 
		smscEnumPendingQueriesS	 Unsigned32, 
		smscEnumReceivedResponsesS	 Unsigned32, 
		smscEnumContextFree	 Unsigned32, 
		smscEnumContextInUse	 Unsigned32, 
		smscEnumContextMaxUsed	 Unsigned32, 
		smscEnumContextNoMem	 Unsigned32, 
		smscEnumCacheLookups	 Unsigned32, 
		smscEnumCacheMisses	 Unsigned32, 
		smscEnumCacheStores	 Unsigned32, 
		smscEnumCacheOverwrites	 Unsigned32, 
		smscEnumSentQueries	 Unsigned32, 
		smscEnumPendingQueries	 Unsigned32, 
		smscEnumRetriedQueries	 Unsigned32, 
		smscEnumTimedoutQueries	 Unsigned32, 
		smscEnumFailedQueries	 Unsigned32, 
		smscEnumReceivedResponses	 Unsigned32, 
		smscEnumSentUdpS	 Unsigned32, 
		smscEnumReceivedUdpS	 Unsigned32, 
		smscEnumSentUdp	 Unsigned32, 
		smscEnumReceivedUdp	 Unsigned32, 
		smscEnumTerminatedQueries	 Unsigned32
	}

smscEnumName  OBJECT-TYPE
	SYNTAX  DisplayString
	MAX-ACCESS  read-only
	STATUS   current
	DESCRIPTION
		"Identifies the name of the entity."
   ::= {enumInstanceEntry 1 }

smscEnumState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { enumInstanceEntry 2 }


smscEnumLastupdate OBJECT-TYPE
		SYNTAX	TimeTicks
		MAX-ACCESS read-only
		STATUS current
		DESCRIPTION
			"Value which reflects the last time the entities fields have been updated"
	::= { enumInstanceEntry	3 }

smscEnumNode  OBJECT-TYPE
	SYNTAX  DisplayString
	MAX-ACCESS  read-only
	STATUS   current
	DESCRIPTION
		"Identifies the node the entity is running on."
   ::= {enumInstanceEntry 4 }

smscEnumMsgReceived OBJECT-TYPE
		SYNTAX	Unsigned32
		MAX-ACCESS read-only
		STATUS current
		DESCRIPTION
			"Received messages"
	::= { enumInstanceEntry	5 }

smscEnumMsgRejected OBJECT-TYPE
		SYNTAX	Unsigned32
		MAX-ACCESS read-only
		STATUS current
		DESCRIPTION
			"Received messages and rejected"
	::= { enumInstanceEntry	6 }

smscEnumMsgTransmitted OBJECT-TYPE
		SYNTAX	Unsigned32
		MAX-ACCESS read-only
		STATUS current
		DESCRIPTION
			"Transmitted messages"
	::= { enumInstanceEntry	7 }

smscEnumMsgFailed OBJECT-TYPE
		SYNTAX	Unsigned32
		MAX-ACCESS read-only
		STATUS current
		DESCRIPTION
			"Messages that failed on sending"
	::= { enumInstanceEntry	8 }

smscEnumQelemUsed OBJECT-TYPE
		SYNTAX	Unsigned32
		MAX-ACCESS read-only
		STATUS current
		DESCRIPTION
			"Number of elements in internal queues"
	::= { enumInstanceEntry	9 }

smscEnumQelemInProcqueue OBJECT-TYPE
		SYNTAX	Unsigned32
		MAX-ACCESS read-only
		STATUS current
		DESCRIPTION
			"Number of elements used in process queue"
	::= { enumInstanceEntry	10 }

smscEnumQelemInExpqueue OBJECT-TYPE
		SYNTAX	Unsigned32
		MAX-ACCESS read-only
		STATUS current
		DESCRIPTION
			"Number of elements used in expedited queue"
	::= { enumInstanceEntry	11 }

smscEnumNrTimersRunning OBJECT-TYPE
		SYNTAX	Unsigned32
		MAX-ACCESS read-only
		STATUS current
		DESCRIPTION
			"Total number of timers running"
	::= { enumInstanceEntry	12 }

smscEnumNrSystemTimers OBJECT-TYPE
		SYNTAX	Unsigned32
		MAX-ACCESS read-only
		STATUS current
		DESCRIPTION
			"Number of system timers running"
	::= { enumInstanceEntry	13 }

smscEnumImiRecallQelem OBJECT-TYPE
		SYNTAX	Unsigned32
		MAX-ACCESS read-only
		STATUS current
		DESCRIPTION
			"Number of IMI recall-queue elements used"
	::= { enumInstanceEntry	14 }

smscEnumImiRecallQueues OBJECT-TYPE
		SYNTAX	Unsigned32
		MAX-ACCESS read-only
		STATUS current
		DESCRIPTION
			"Number of IMI-recall-queues used"
	::= { enumInstanceEntry	15 }

smscEnumIdiRecallQelem OBJECT-TYPE
		SYNTAX	Unsigned32
		MAX-ACCESS read-only
		STATUS current
		DESCRIPTION
			"Number of IDI recall-queue elements used"
	::= { enumInstanceEntry	16 }

smscEnumIdiRecallQueues OBJECT-TYPE
		SYNTAX	Unsigned32
		MAX-ACCESS read-only
		STATUS current
		DESCRIPTION
			"Number of IDI recall-queues used"
	::= { enumInstanceEntry	17 }

smscEnumIosRecallQelem OBJECT-TYPE
		SYNTAX	Unsigned32
		MAX-ACCESS read-only
		STATUS current
		DESCRIPTION
			"Number of IOS recall-queue elements used"
	::= { enumInstanceEntry	18 }

smscEnumIosRecallQueues OBJECT-TYPE
		SYNTAX	Unsigned32
		MAX-ACCESS read-only
		STATUS current
		DESCRIPTION
			"Number of IOS recall-queues used"
	::= { enumInstanceEntry	19 }

smscEnumLogRecallQelem OBJECT-TYPE
		SYNTAX	Unsigned32
		MAX-ACCESS read-only
		STATUS current
		DESCRIPTION
			"Number of LOG recall-queue elements used"
	::= { enumInstanceEntry	20 }

smscEnumLogRecallQueues OBJECT-TYPE
		SYNTAX	Unsigned32
		MAX-ACCESS read-only
		STATUS current
		DESCRIPTION
			"Number of LOG recall-queues used"
	::= { enumInstanceEntry	21 }

smscEnumTrcreqDiscarded OBJECT-TYPE
		SYNTAX	Unsigned32
		MAX-ACCESS read-only
		STATUS current
		DESCRIPTION
			"Number of trace requests discarded"
	::= { enumInstanceEntry	22 }

smscEnumSentQueriesS OBJECT-TYPE
		SYNTAX	Unsigned32
		MAX-ACCESS read-only
		STATUS current
		DESCRIPTION
			"Number of sent DNS queries (statistical)"
	::= { enumInstanceEntry	23 }

smscEnumPendingQueriesS OBJECT-TYPE
		SYNTAX	Unsigned32
		MAX-ACCESS read-only
		STATUS current
		DESCRIPTION
			"Number of pending DNS queries (statistical)"
	::= { enumInstanceEntry	24 }

smscEnumReceivedResponsesS OBJECT-TYPE
		SYNTAX	Unsigned32
		MAX-ACCESS read-only
		STATUS current
		DESCRIPTION
			"Number of received DNS responses (statistical)"
	::= { enumInstanceEntry	25 }

smscEnumContextFree OBJECT-TYPE
		SYNTAX	Unsigned32
		MAX-ACCESS read-only
		STATUS current
		DESCRIPTION
			"Number of Free Contexts"
	::= { enumInstanceEntry	26 }

smscEnumContextInUse OBJECT-TYPE
		SYNTAX	Unsigned32
		MAX-ACCESS read-only
		STATUS current
		DESCRIPTION
			"Number of Busy Contexts"
	::= { enumInstanceEntry	27 }

smscEnumContextMaxUsed OBJECT-TYPE
		SYNTAX	Unsigned32
		MAX-ACCESS read-only
		STATUS current
		DESCRIPTION
			"Highest peak of Busy Contexts"
	::= { enumInstanceEntry	28 }

smscEnumContextNoMem OBJECT-TYPE
		SYNTAX	Unsigned32
		MAX-ACCESS read-only
		STATUS current
		DESCRIPTION
			"Number of times no Free Contexts available"
	::= { enumInstanceEntry	29 }

smscEnumCacheLookups OBJECT-TYPE
		SYNTAX	Unsigned32
		MAX-ACCESS read-only
		STATUS current
		DESCRIPTION
			"Number of DNS Query Cache lookups"
	::= { enumInstanceEntry	30 }

smscEnumCacheMisses OBJECT-TYPE
		SYNTAX	Unsigned32
		MAX-ACCESS read-only
		STATUS current
		DESCRIPTION
			"Number of DNS Query Cache lookups with no result"
	::= { enumInstanceEntry	31 }

smscEnumCacheStores OBJECT-TYPE
		SYNTAX	Unsigned32
		MAX-ACCESS read-only
		STATUS current
		DESCRIPTION
			"Number of times item stored in DNS Query Cache"
	::= { enumInstanceEntry	32 }

smscEnumCacheOverwrites OBJECT-TYPE
		SYNTAX	Unsigned32
		MAX-ACCESS read-only
		STATUS current
		DESCRIPTION
			"Nr. of times item overwritten in DNS Query Cache"
	::= { enumInstanceEntry	33 }

smscEnumSentQueries OBJECT-TYPE
		SYNTAX	Unsigned32
		MAX-ACCESS read-only
		STATUS current
		DESCRIPTION
			"Number of sent DNS Queries"
	::= { enumInstanceEntry	34 }

smscEnumPendingQueries OBJECT-TYPE
		SYNTAX	Unsigned32
		MAX-ACCESS read-only
		STATUS current
		DESCRIPTION
			"Number of pending DNS Queries"
	::= { enumInstanceEntry	35 }

smscEnumRetriedQueries OBJECT-TYPE
		SYNTAX	Unsigned32
		MAX-ACCESS read-only
		STATUS current
		DESCRIPTION
			"Number of DNS Queries with one or more retries"
	::= { enumInstanceEntry	36 }

smscEnumTimedoutQueries OBJECT-TYPE
		SYNTAX	Unsigned32
		MAX-ACCESS read-only
		STATUS current
		DESCRIPTION
			"Number of DNS Queries failed due to timeout"
	::= { enumInstanceEntry	37 }

smscEnumFailedQueries OBJECT-TYPE
		SYNTAX	Unsigned32
		MAX-ACCESS read-only
		STATUS current
		DESCRIPTION
			"Number of DNS Queries failed due to other reasons"
	::= { enumInstanceEntry	38 }

smscEnumReceivedResponses OBJECT-TYPE
		SYNTAX	Unsigned32
		MAX-ACCESS read-only
		STATUS current
		DESCRIPTION
			"Number of received DNS Responses"
	::= { enumInstanceEntry	39 }

smscEnumSentUdpS OBJECT-TYPE
		SYNTAX	Unsigned32
		MAX-ACCESS read-only
		STATUS current
		DESCRIPTION
			"Number of sent UDP packets (statistical)"
	::= { enumInstanceEntry	40 }

smscEnumReceivedUdpS OBJECT-TYPE
		SYNTAX	Unsigned32
		MAX-ACCESS read-only
		STATUS current
		DESCRIPTION
			"Number of received UDP packets (statistical)"
	::= { enumInstanceEntry	41 }

smscEnumSentUdp OBJECT-TYPE
		SYNTAX	Unsigned32
		MAX-ACCESS read-only
		STATUS current
		DESCRIPTION
			"Number of sent UDP packets"
	::= { enumInstanceEntry	42 }

smscEnumReceivedUdp OBJECT-TYPE
		SYNTAX	Unsigned32
		MAX-ACCESS read-only
		STATUS current
		DESCRIPTION
			"Number of received UDP packets"
	::= { enumInstanceEntry	43 }

smscEnumTerminatedQueries OBJECT-TYPE
		SYNTAX	Unsigned32
		MAX-ACCESS read-only
		STATUS current
		DESCRIPTION
			"Number of terminated DNS queries"
	::= { enumInstanceEntry	44 }



-- end of ENUM description.
-- --------------------------------------


-- --------------------------------------
-- Class X25
-- 
smscX25 OBJECT-TYPE
	SYNTAX  SEQUENCE OF X25InstanceEntry
	MAX-ACCESS  not-accessible
	STATUS  current
	DESCRIPTION
		"Mapping table for SMSC X25 entities."
   ::= { smscClassServer   1  }

x25InstanceEntry  OBJECT-TYPE
	SYNTAX X25InstanceEntry
	MAX-ACCESS  not-accessible
	STATUS  current
	DESCRIPTION
		"An entry (row) in the entityInstanceTable."
	INDEX { IMPLIED smscX25Name }
   ::= { smscX25 1 }

X25InstanceEntry ::= SEQUENCE {
		smscX25Name     DisplayString,
		smscX25State   INTEGER,
		smscX25Lastupdate   TimeTicks,
		smscX25Node	   DisplayString, 
		smscX25MsgReceived	 Unsigned32, 
		smscX25MsgRejected	 Unsigned32, 
		smscX25MsgTransmitted	 Unsigned32, 
		smscX25MsgFailed	 Unsigned32, 
		smscX25ConTot	 Unsigned32, 
		smscX25ConIn	 Unsigned32, 
		smscX25ConInAcc	 Unsigned32, 
		smscX25ConOut	 Unsigned32, 
		smscX25ConOutAcc	 Unsigned32, 
		smscX25ConOutBusy	 Unsigned32, 
		smscX25ConOutNoAnswer	 Unsigned32, 
		smscX25ConOutOtherFail	 Unsigned32, 
		smscX25ConTimeCumulative	 Unsigned32, 
		smscX25QelemUsed	 Unsigned32, 
		smscX25QelemInProcqueue	 Unsigned32, 
		smscX25QelemInExpqueue	 Unsigned32, 
		smscX25NrTimersRunning	 Unsigned32, 
		smscX25NrSystemTimers	 Unsigned32, 
		smscX25ImiRecallQelem	 Unsigned32, 
		smscX25ImiRecallQueues	 Unsigned32, 
		smscX25IdiRecallQelem	 Unsigned32, 
		smscX25IdiRecallQueues	 Unsigned32, 
		smscX25IosRecallQelem	 Unsigned32, 
		smscX25IosRecallQueues	 Unsigned32, 
		smscX25LogRecallQelem	 Unsigned32, 
		smscX25LogRecallQueues	 Unsigned32, 
		smscX25TrcreqDiscarded	 Unsigned32
	}

smscX25Name  OBJECT-TYPE
	SYNTAX  DisplayString
	MAX-ACCESS  read-only
	STATUS   current
	DESCRIPTION
		"Identifies the name of the entity."
   ::= {x25InstanceEntry 1 }

smscX25State  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { x25InstanceEntry 2 }


smscX25Lastupdate OBJECT-TYPE
		SYNTAX	TimeTicks
		MAX-ACCESS read-only
		STATUS current
		DESCRIPTION
			"Value which reflects the last time the entities fields have been updated"
	::= { x25InstanceEntry	3 }

smscX25Node  OBJECT-TYPE
	SYNTAX  DisplayString
	MAX-ACCESS  read-only
	STATUS   current
	DESCRIPTION
		"Identifies the node the entity is running on."
   ::= {x25InstanceEntry 4 }

smscX25MsgReceived OBJECT-TYPE
		SYNTAX	Unsigned32
		MAX-ACCESS read-only
		STATUS current
		DESCRIPTION
			"Received messages"
	::= { x25InstanceEntry	5 }

smscX25MsgRejected OBJECT-TYPE
		SYNTAX	Unsigned32
		MAX-ACCESS read-only
		STATUS current
		DESCRIPTION
			"Received messages and rejected"
	::= { x25InstanceEntry	6 }

smscX25MsgTransmitted OBJECT-TYPE
		SYNTAX	Unsigned32
		MAX-ACCESS read-only
		STATUS current
		DESCRIPTION
			"Transmitted messages"
	::= { x25InstanceEntry	7 }

smscX25MsgFailed OBJECT-TYPE
		SYNTAX	Unsigned32
		MAX-ACCESS read-only
		STATUS current
		DESCRIPTION
			"Messages that failed on sending"
	::= { x25InstanceEntry	8 }

smscX25ConTot OBJECT-TYPE
		SYNTAX	Unsigned32
		MAX-ACCESS read-only
		STATUS current
		DESCRIPTION
			"Network connections"
	::= { x25InstanceEntry	9 }

smscX25ConIn OBJECT-TYPE
		SYNTAX	Unsigned32
		MAX-ACCESS read-only
		STATUS current
		DESCRIPTION
			"Received network connections"
	::= { x25InstanceEntry	10 }

smscX25ConInAcc OBJECT-TYPE
		SYNTAX	Unsigned32
		MAX-ACCESS read-only
		STATUS current
		DESCRIPTION
			"Accepted received network connections"
	::= { x25InstanceEntry	11 }

smscX25ConOut OBJECT-TYPE
		SYNTAX	Unsigned32
		MAX-ACCESS read-only
		STATUS current
		DESCRIPTION
			"Initiated network connections"
	::= { x25InstanceEntry	12 }

smscX25ConOutAcc OBJECT-TYPE
		SYNTAX	Unsigned32
		MAX-ACCESS read-only
		STATUS current
		DESCRIPTION
			"Accepted initiated network connections"
	::= { x25InstanceEntry	13 }

smscX25ConOutBusy OBJECT-TYPE
		SYNTAX	Unsigned32
		MAX-ACCESS read-only
		STATUS current
		DESCRIPTION
			"Initiated network connections resulting in busy tone"
	::= { x25InstanceEntry	14 }

smscX25ConOutNoAnswer OBJECT-TYPE
		SYNTAX	Unsigned32
		MAX-ACCESS read-only
		STATUS current
		DESCRIPTION
			"Initiated network connections resulting in no answer tone"
	::= { x25InstanceEntry	15 }

smscX25ConOutOtherFail OBJECT-TYPE
		SYNTAX	Unsigned32
		MAX-ACCESS read-only
		STATUS current
		DESCRIPTION
			"Initiated network connections resulting in other failures"
	::= { x25InstanceEntry	16 }

smscX25ConTimeCumulative OBJECT-TYPE
		SYNTAX	Unsigned32
		MAX-ACCESS read-only
		STATUS current
		DESCRIPTION
			"Accumulated session duration time"
	::= { x25InstanceEntry	17 }

smscX25QelemUsed OBJECT-TYPE
		SYNTAX	Unsigned32
		MAX-ACCESS read-only
		STATUS current
		DESCRIPTION
			"Number of elements in internal queues"
	::= { x25InstanceEntry	18 }

smscX25QelemInProcqueue OBJECT-TYPE
		SYNTAX	Unsigned32
		MAX-ACCESS read-only
		STATUS current
		DESCRIPTION
			"Number of elements used in process queue"
	::= { x25InstanceEntry	19 }

smscX25QelemInExpqueue OBJECT-TYPE
		SYNTAX	Unsigned32
		MAX-ACCESS read-only
		STATUS current
		DESCRIPTION
			"Number of elements used in expedited queue"
	::= { x25InstanceEntry	20 }

smscX25NrTimersRunning OBJECT-TYPE
		SYNTAX	Unsigned32
		MAX-ACCESS read-only
		STATUS current
		DESCRIPTION
			"Total number of timers running"
	::= { x25InstanceEntry	21 }

smscX25NrSystemTimers OBJECT-TYPE
		SYNTAX	Unsigned32
		MAX-ACCESS read-only
		STATUS current
		DESCRIPTION
			"Number of system timers running"
	::= { x25InstanceEntry	22 }

smscX25ImiRecallQelem OBJECT-TYPE
		SYNTAX	Unsigned32
		MAX-ACCESS read-only
		STATUS current
		DESCRIPTION
			"Number of IMI recall-queue elements used"
	::= { x25InstanceEntry	23 }

smscX25ImiRecallQueues OBJECT-TYPE
		SYNTAX	Unsigned32
		MAX-ACCESS read-only
		STATUS current
		DESCRIPTION
			"Number of IMI-recall-queues used"
	::= { x25InstanceEntry	24 }

smscX25IdiRecallQelem OBJECT-TYPE
		SYNTAX	Unsigned32
		MAX-ACCESS read-only
		STATUS current
		DESCRIPTION
			"Number of IDI recall-queue elements used"
	::= { x25InstanceEntry	25 }

smscX25IdiRecallQueues OBJECT-TYPE
		SYNTAX	Unsigned32
		MAX-ACCESS read-only
		STATUS current
		DESCRIPTION
			"Number of IDI recall-queues used"
	::= { x25InstanceEntry	26 }

smscX25IosRecallQelem OBJECT-TYPE
		SYNTAX	Unsigned32
		MAX-ACCESS read-only
		STATUS current
		DESCRIPTION
			"Number of IOS recall-queue elements used"
	::= { x25InstanceEntry	27 }

smscX25IosRecallQueues OBJECT-TYPE
		SYNTAX	Unsigned32
		MAX-ACCESS read-only
		STATUS current
		DESCRIPTION
			"Number of IOS recall-queues used"
	::= { x25InstanceEntry	28 }

smscX25LogRecallQelem OBJECT-TYPE
		SYNTAX	Unsigned32
		MAX-ACCESS read-only
		STATUS current
		DESCRIPTION
			"Number of LOG recall-queue elements used"
	::= { x25InstanceEntry	29 }

smscX25LogRecallQueues OBJECT-TYPE
		SYNTAX	Unsigned32
		MAX-ACCESS read-only
		STATUS current
		DESCRIPTION
			"Number of LOG recall-queues used"
	::= { x25InstanceEntry	30 }

smscX25TrcreqDiscarded OBJECT-TYPE
		SYNTAX	Unsigned32
		MAX-ACCESS read-only
		STATUS current
		DESCRIPTION
			"Number of trace requests discarded"
	::= { x25InstanceEntry	31 }



-- end of X25 description.
-- --------------------------------------


-- --------------------------------------
-- Class TCP
-- 
smscTcp OBJECT-TYPE
	SYNTAX  SEQUENCE OF TcpInstanceEntry
	MAX-ACCESS  not-accessible
	STATUS  current
	DESCRIPTION
		"Mapping table for SMSC TCP entities."
   ::= { smscClassServer   2  }

tcpInstanceEntry  OBJECT-TYPE
	SYNTAX TcpInstanceEntry
	MAX-ACCESS  not-accessible
	STATUS  current
	DESCRIPTION
		"An entry (row) in the entityInstanceTable."
	INDEX { IMPLIED smscTcpName }
   ::= { smscTcp 1 }

TcpInstanceEntry ::= SEQUENCE {
		smscTcpName     DisplayString,
		smscTcpState   INTEGER,
		smscTcpLastupdate   TimeTicks,
		smscTcpNode	   DisplayString, 
		smscTcpMsgReceived	 Unsigned32, 
		smscTcpMsgRejected	 Unsigned32, 
		smscTcpMsgTransmitted	 Unsigned32, 
		smscTcpMsgFailed	 Unsigned32, 
		smscTcpConTot	 Unsigned32, 
		smscTcpConIn	 Unsigned32, 
		smscTcpConInAcc	 Unsigned32, 
		smscTcpConOut	 Unsigned32, 
		smscTcpConOutAcc	 Unsigned32, 
		smscTcpConOutBusy	 Unsigned32, 
		smscTcpConOutNoAnswer	 Unsigned32, 
		smscTcpConOutOtherFail	 Unsigned32, 
		smscTcpConTimeCumulative	 Unsigned32, 
		smscTcpQelemUsed	 Unsigned32, 
		smscTcpQelemInProcqueue	 Unsigned32, 
		smscTcpQelemInExpqueue	 Unsigned32, 
		smscTcpNrTimersRunning	 Unsigned32, 
		smscTcpNrSystemTimers	 Unsigned32, 
		smscTcpImiRecallQelem	 Unsigned32, 
		smscTcpImiRecallQueues	 Unsigned32, 
		smscTcpIdiRecallQelem	 Unsigned32, 
		smscTcpIdiRecallQueues	 Unsigned32, 
		smscTcpIosRecallQelem	 Unsigned32, 
		smscTcpIosRecallQueues	 Unsigned32, 
		smscTcpLogRecallQelem	 Unsigned32, 
		smscTcpLogRecallQueues	 Unsigned32, 
		smscTcpTrcreqDiscarded	 Unsigned32
	}

smscTcpName  OBJECT-TYPE
	SYNTAX  DisplayString
	MAX-ACCESS  read-only
	STATUS   current
	DESCRIPTION
		"Identifies the name of the entity."
   ::= {tcpInstanceEntry 1 }

smscTcpState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { tcpInstanceEntry 2 }


smscTcpLastupdate OBJECT-TYPE
		SYNTAX	TimeTicks
		MAX-ACCESS read-only
		STATUS current
		DESCRIPTION
			"Value which reflects the last time the entities fields have been updated"
	::= { tcpInstanceEntry	3 }

smscTcpNode  OBJECT-TYPE
	SYNTAX  DisplayString
	MAX-ACCESS  read-only
	STATUS   current
	DESCRIPTION
		"Identifies the node the entity is running on."
   ::= {tcpInstanceEntry 4 }

smscTcpMsgReceived OBJECT-TYPE
		SYNTAX	Unsigned32
		MAX-ACCESS read-only
		STATUS current
		DESCRIPTION
			"Received messages"
	::= { tcpInstanceEntry	5 }

smscTcpMsgRejected OBJECT-TYPE
		SYNTAX	Unsigned32
		MAX-ACCESS read-only
		STATUS current
		DESCRIPTION
			"Received messages and rejected"
	::= { tcpInstanceEntry	6 }

smscTcpMsgTransmitted OBJECT-TYPE
		SYNTAX	Unsigned32
		MAX-ACCESS read-only
		STATUS current
		DESCRIPTION
			"Transmitted messages"
	::= { tcpInstanceEntry	7 }

smscTcpMsgFailed OBJECT-TYPE
		SYNTAX	Unsigned32
		MAX-ACCESS read-only
		STATUS current
		DESCRIPTION
			"Messages that failed on sending"
	::= { tcpInstanceEntry	8 }

smscTcpConTot OBJECT-TYPE
		SYNTAX	Unsigned32
		MAX-ACCESS read-only
		STATUS current
		DESCRIPTION
			"Network connections"
	::= { tcpInstanceEntry	9 }

smscTcpConIn OBJECT-TYPE
		SYNTAX	Unsigned32
		MAX-ACCESS read-only
		STATUS current
		DESCRIPTION
			"Received network connections"
	::= { tcpInstanceEntry	10 }

smscTcpConInAcc OBJECT-TYPE
		SYNTAX	Unsigned32
		MAX-ACCESS read-only
		STATUS current
		DESCRIPTION
			"Accepted received network connections"
	::= { tcpInstanceEntry	11 }

smscTcpConOut OBJECT-TYPE
		SYNTAX	Unsigned32
		MAX-ACCESS read-only
		STATUS current
		DESCRIPTION
			"Initiated network connections"
	::= { tcpInstanceEntry	12 }

smscTcpConOutAcc OBJECT-TYPE
		SYNTAX	Unsigned32
		MAX-ACCESS read-only
		STATUS current
		DESCRIPTION
			"Accepted initiated network connections"
	::= { tcpInstanceEntry	13 }

smscTcpConOutBusy OBJECT-TYPE
		SYNTAX	Unsigned32
		MAX-ACCESS read-only
		STATUS current
		DESCRIPTION
			"Initiated network connections resulting in busy tone"
	::= { tcpInstanceEntry	14 }

smscTcpConOutNoAnswer OBJECT-TYPE
		SYNTAX	Unsigned32
		MAX-ACCESS read-only
		STATUS current
		DESCRIPTION
			"Initiated network connections resulting in no answer tone"
	::= { tcpInstanceEntry	15 }

smscTcpConOutOtherFail OBJECT-TYPE
		SYNTAX	Unsigned32
		MAX-ACCESS read-only
		STATUS current
		DESCRIPTION
			"Initiated network connections resulting in other failures"
	::= { tcpInstanceEntry	16 }

smscTcpConTimeCumulative OBJECT-TYPE
		SYNTAX	Unsigned32
		MAX-ACCESS read-only
		STATUS current
		DESCRIPTION
			"Accumulated session duration time"
	::= { tcpInstanceEntry	17 }

smscTcpQelemUsed OBJECT-TYPE
		SYNTAX	Unsigned32
		MAX-ACCESS read-only
		STATUS current
		DESCRIPTION
			"Number of elements in internal queues"
	::= { tcpInstanceEntry	18 }

smscTcpQelemInProcqueue OBJECT-TYPE
		SYNTAX	Unsigned32
		MAX-ACCESS read-only
		STATUS current
		DESCRIPTION
			"Number of elements used in process queue"
	::= { tcpInstanceEntry	19 }

smscTcpQelemInExpqueue OBJECT-TYPE
		SYNTAX	Unsigned32
		MAX-ACCESS read-only
		STATUS current
		DESCRIPTION
			"Number of elements used in expedited queue"
	::= { tcpInstanceEntry	20 }

smscTcpNrTimersRunning OBJECT-TYPE
		SYNTAX	Unsigned32
		MAX-ACCESS read-only
		STATUS current
		DESCRIPTION
			"Total number of timers running"
	::= { tcpInstanceEntry	21 }

smscTcpNrSystemTimers OBJECT-TYPE
		SYNTAX	Unsigned32
		MAX-ACCESS read-only
		STATUS current
		DESCRIPTION
			"Number of system timers running"
	::= { tcpInstanceEntry	22 }

smscTcpImiRecallQelem OBJECT-TYPE
		SYNTAX	Unsigned32
		MAX-ACCESS read-only
		STATUS current
		DESCRIPTION
			"Number of IMI recall-queue elements used"
	::= { tcpInstanceEntry	23 }

smscTcpImiRecallQueues OBJECT-TYPE
		SYNTAX	Unsigned32
		MAX-ACCESS read-only
		STATUS current
		DESCRIPTION
			"Number of IMI-recall-queues used"
	::= { tcpInstanceEntry	24 }

smscTcpIdiRecallQelem OBJECT-TYPE
		SYNTAX	Unsigned32
		MAX-ACCESS read-only
		STATUS current
		DESCRIPTION
			"Number of IDI recall-queue elements used"
	::= { tcpInstanceEntry	25 }

smscTcpIdiRecallQueues OBJECT-TYPE
		SYNTAX	Unsigned32
		MAX-ACCESS read-only
		STATUS current
		DESCRIPTION
			"Number of IDI recall-queues used"
	::= { tcpInstanceEntry	26 }

smscTcpIosRecallQelem OBJECT-TYPE
		SYNTAX	Unsigned32
		MAX-ACCESS read-only
		STATUS current
		DESCRIPTION
			"Number of IOS recall-queue elements used"
	::= { tcpInstanceEntry	27 }

smscTcpIosRecallQueues OBJECT-TYPE
		SYNTAX	Unsigned32
		MAX-ACCESS read-only
		STATUS current
		DESCRIPTION
			"Number of IOS recall-queues used"
	::= { tcpInstanceEntry	28 }

smscTcpLogRecallQelem OBJECT-TYPE
		SYNTAX	Unsigned32
		MAX-ACCESS read-only
		STATUS current
		DESCRIPTION
			"Number of LOG recall-queue elements used"
	::= { tcpInstanceEntry	29 }

smscTcpLogRecallQueues OBJECT-TYPE
		SYNTAX	Unsigned32
		MAX-ACCESS read-only
		STATUS current
		DESCRIPTION
			"Number of LOG recall-queues used"
	::= { tcpInstanceEntry	30 }

smscTcpTrcreqDiscarded OBJECT-TYPE
		SYNTAX	Unsigned32
		MAX-ACCESS read-only
		STATUS current
		DESCRIPTION
			"Number of trace requests discarded"
	::= { tcpInstanceEntry	31 }



-- end of TCP description.
-- --------------------------------------


-- --------------------------------------
-- Class X29
-- 
smscX29 OBJECT-TYPE
	SYNTAX  SEQUENCE OF X29InstanceEntry
	MAX-ACCESS  not-accessible
	STATUS  current
	DESCRIPTION
		"Mapping table for SMSC X29 entities."
   ::= { smscClassServer   3  }

x29InstanceEntry  OBJECT-TYPE
	SYNTAX X29InstanceEntry
	MAX-ACCESS  not-accessible
	STATUS  current
	DESCRIPTION
		"An entry (row) in the entityInstanceTable."
	INDEX { IMPLIED smscX29Name }
   ::= { smscX29 1 }

X29InstanceEntry ::= SEQUENCE {
		smscX29Name     DisplayString,
		smscX29State   INTEGER,
		smscX29Lastupdate   TimeTicks,
		smscX29Node	   DisplayString, 
		smscX29MsgReceived	 Unsigned32, 
		smscX29MsgRejected	 Unsigned32, 
		smscX29MsgTransmitted	 Unsigned32, 
		smscX29MsgFailed	 Unsigned32, 
		smscX29ConTot	 Unsigned32, 
		smscX29ConIn	 Unsigned32, 
		smscX29ConInAcc	 Unsigned32, 
		smscX29ConOut	 Unsigned32, 
		smscX29ConOutAcc	 Unsigned32, 
		smscX29ConOutBusy	 Unsigned32, 
		smscX29ConOutNoAnswer	 Unsigned32, 
		smscX29ConOutOtherFail	 Unsigned32, 
		smscX29ConTimeCumulative	 Unsigned32, 
		smscX29QelemUsed	 Unsigned32, 
		smscX29QelemInProcqueue	 Unsigned32, 
		smscX29QelemInExpqueue	 Unsigned32, 
		smscX29NrTimersRunning	 Unsigned32, 
		smscX29NrSystemTimers	 Unsigned32, 
		smscX29ImiRecallQelem	 Unsigned32, 
		smscX29ImiRecallQueues	 Unsigned32, 
		smscX29IdiRecallQelem	 Unsigned32, 
		smscX29IdiRecallQueues	 Unsigned32, 
		smscX29IosRecallQelem	 Unsigned32, 
		smscX29IosRecallQueues	 Unsigned32, 
		smscX29LogRecallQelem	 Unsigned32, 
		smscX29LogRecallQueues	 Unsigned32, 
		smscX29TrcreqDiscarded	 Unsigned32
	}

smscX29Name  OBJECT-TYPE
	SYNTAX  DisplayString
	MAX-ACCESS  read-only
	STATUS   current
	DESCRIPTION
		"Identifies the name of the entity."
   ::= {x29InstanceEntry 1 }

smscX29State  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { x29InstanceEntry 2 }


smscX29Lastupdate OBJECT-TYPE
		SYNTAX	TimeTicks
		MAX-ACCESS read-only
		STATUS current
		DESCRIPTION
			"Value which reflects the last time the entities fields have been updated"
	::= { x29InstanceEntry	3 }

smscX29Node  OBJECT-TYPE
	SYNTAX  DisplayString
	MAX-ACCESS  read-only
	STATUS   current
	DESCRIPTION
		"Identifies the node the entity is running on."
   ::= {x29InstanceEntry 4 }

smscX29MsgReceived OBJECT-TYPE
		SYNTAX	Unsigned32
		MAX-ACCESS read-only
		STATUS current
		DESCRIPTION
			"Received messages"
	::= { x29InstanceEntry	5 }

smscX29MsgRejected OBJECT-TYPE
		SYNTAX	Unsigned32
		MAX-ACCESS read-only
		STATUS current
		DESCRIPTION
			"Received messages and rejected"
	::= { x29InstanceEntry	6 }

smscX29MsgTransmitted OBJECT-TYPE
		SYNTAX	Unsigned32
		MAX-ACCESS read-only
		STATUS current
		DESCRIPTION
			"Transmitted messages"
	::= { x29InstanceEntry	7 }

smscX29MsgFailed OBJECT-TYPE
		SYNTAX	Unsigned32
		MAX-ACCESS read-only
		STATUS current
		DESCRIPTION
			"Messages that failed on sending"
	::= { x29InstanceEntry	8 }

smscX29ConTot OBJECT-TYPE
		SYNTAX	Unsigned32
		MAX-ACCESS read-only
		STATUS current
		DESCRIPTION
			"Network connections"
	::= { x29InstanceEntry	9 }

smscX29ConIn OBJECT-TYPE
		SYNTAX	Unsigned32
		MAX-ACCESS read-only
		STATUS current
		DESCRIPTION
			"Received network connections"
	::= { x29InstanceEntry	10 }

smscX29ConInAcc OBJECT-TYPE
		SYNTAX	Unsigned32
		MAX-ACCESS read-only
		STATUS current
		DESCRIPTION
			"Accepted received network connections"
	::= { x29InstanceEntry	11 }

smscX29ConOut OBJECT-TYPE
		SYNTAX	Unsigned32
		MAX-ACCESS read-only
		STATUS current
		DESCRIPTION
			"Initiated network connections"
	::= { x29InstanceEntry	12 }

smscX29ConOutAcc OBJECT-TYPE
		SYNTAX	Unsigned32
		MAX-ACCESS read-only
		STATUS current
		DESCRIPTION
			"Accepted initiated network connections"
	::= { x29InstanceEntry	13 }

smscX29ConOutBusy OBJECT-TYPE
		SYNTAX	Unsigned32
		MAX-ACCESS read-only
		STATUS current
		DESCRIPTION
			"Initiated network connections resulting in busy tone"
	::= { x29InstanceEntry	14 }

smscX29ConOutNoAnswer OBJECT-TYPE
		SYNTAX	Unsigned32
		MAX-ACCESS read-only
		STATUS current
		DESCRIPTION
			"Initiated network connections resulting in no answer tone"
	::= { x29InstanceEntry	15 }

smscX29ConOutOtherFail OBJECT-TYPE
		SYNTAX	Unsigned32
		MAX-ACCESS read-only
		STATUS current
		DESCRIPTION
			"Initiated network connections resulting in other failures"
	::= { x29InstanceEntry	16 }

smscX29ConTimeCumulative OBJECT-TYPE
		SYNTAX	Unsigned32
		MAX-ACCESS read-only
		STATUS current
		DESCRIPTION
			"Accumulated session duration time"
	::= { x29InstanceEntry	17 }

smscX29QelemUsed OBJECT-TYPE
		SYNTAX	Unsigned32
		MAX-ACCESS read-only
		STATUS current
		DESCRIPTION
			"Number of elements in internal queues"
	::= { x29InstanceEntry	18 }

smscX29QelemInProcqueue OBJECT-TYPE
		SYNTAX	Unsigned32
		MAX-ACCESS read-only
		STATUS current
		DESCRIPTION
			"Number of elements used in process queue"
	::= { x29InstanceEntry	19 }

smscX29QelemInExpqueue OBJECT-TYPE
		SYNTAX	Unsigned32
		MAX-ACCESS read-only
		STATUS current
		DESCRIPTION
			"Number of elements used in expedited queue"
	::= { x29InstanceEntry	20 }

smscX29NrTimersRunning OBJECT-TYPE
		SYNTAX	Unsigned32
		MAX-ACCESS read-only
		STATUS current
		DESCRIPTION
			"Total number of timers running"
	::= { x29InstanceEntry	21 }

smscX29NrSystemTimers OBJECT-TYPE
		SYNTAX	Unsigned32
		MAX-ACCESS read-only
		STATUS current
		DESCRIPTION
			"Number of system timers running"
	::= { x29InstanceEntry	22 }

smscX29ImiRecallQelem OBJECT-TYPE
		SYNTAX	Unsigned32
		MAX-ACCESS read-only
		STATUS current
		DESCRIPTION
			"Number of IMI recall-queue elements used"
	::= { x29InstanceEntry	23 }

smscX29ImiRecallQueues OBJECT-TYPE
		SYNTAX	Unsigned32
		MAX-ACCESS read-only
		STATUS current
		DESCRIPTION
			"Number of IMI-recall-queues used"
	::= { x29InstanceEntry	24 }

smscX29IdiRecallQelem OBJECT-TYPE
		SYNTAX	Unsigned32
		MAX-ACCESS read-only
		STATUS current
		DESCRIPTION
			"Number of IDI recall-queue elements used"
	::= { x29InstanceEntry	25 }

smscX29IdiRecallQueues OBJECT-TYPE
		SYNTAX	Unsigned32
		MAX-ACCESS read-only
		STATUS current
		DESCRIPTION
			"Number of IDI recall-queues used"
	::= { x29InstanceEntry	26 }

smscX29IosRecallQelem OBJECT-TYPE
		SYNTAX	Unsigned32
		MAX-ACCESS read-only
		STATUS current
		DESCRIPTION
			"Number of IOS recall-queue elements used"
	::= { x29InstanceEntry	27 }

smscX29IosRecallQueues OBJECT-TYPE
		SYNTAX	Unsigned32
		MAX-ACCESS read-only
		STATUS current
		DESCRIPTION
			"Number of IOS recall-queues used"
	::= { x29InstanceEntry	28 }

smscX29LogRecallQelem OBJECT-TYPE
		SYNTAX	Unsigned32
		MAX-ACCESS read-only
		STATUS current
		DESCRIPTION
			"Number of LOG recall-queue elements used"
	::= { x29InstanceEntry	29 }

smscX29LogRecallQueues OBJECT-TYPE
		SYNTAX	Unsigned32
		MAX-ACCESS read-only
		STATUS current
		DESCRIPTION
			"Number of LOG recall-queues used"
	::= { x29InstanceEntry	30 }

smscX29TrcreqDiscarded OBJECT-TYPE
		SYNTAX	Unsigned32
		MAX-ACCESS read-only
		STATUS current
		DESCRIPTION
			"Number of trace requests discarded"
	::= { x29InstanceEntry	31 }



-- end of X29 description.
-- --------------------------------------


-- --------------------------------------
-- Class EMAP
-- 
smscEmap OBJECT-TYPE
	SYNTAX  SEQUENCE OF EmapInstanceEntry
	MAX-ACCESS  not-accessible
	STATUS  current
	DESCRIPTION
		"Mapping table for SMSC EMAP entities."
   ::= { smscClassServer   4  }

emapInstanceEntry  OBJECT-TYPE
	SYNTAX EmapInstanceEntry
	MAX-ACCESS  not-accessible
	STATUS  current
	DESCRIPTION
		"An entry (row) in the entityInstanceTable."
	INDEX { IMPLIED smscEmapName }
   ::= { smscEmap 1 }

EmapInstanceEntry ::= SEQUENCE {
		smscEmapName     DisplayString,
		smscEmapState   INTEGER,
		smscEmapLastupdate   TimeTicks,
		smscEmapNode	   DisplayString, 
		smscEmapMsgReceived	 Unsigned32, 
		smscEmapMsgRejected	 Unsigned32, 
		smscEmapMsgTransmitted	 Unsigned32, 
		smscEmapMsgFailed	 Unsigned32, 
		smscEmapQelemUsed	 Unsigned32, 
		smscEmapQelemInProcqueue	 Unsigned32, 
		smscEmapQelemInExpqueue	 Unsigned32, 
		smscEmapNrTimersRunning	 Unsigned32, 
		smscEmapNrSystemTimers	 Unsigned32, 
		smscEmapImiRecallQelem	 Unsigned32, 
		smscEmapImiRecallQueues	 Unsigned32, 
		smscEmapIdiRecallQelem	 Unsigned32, 
		smscEmapIdiRecallQueues	 Unsigned32, 
		smscEmapIosRecallQelem	 Unsigned32, 
		smscEmapIosRecallQueues	 Unsigned32, 
		smscEmapLogRecallQelem	 Unsigned32, 
		smscEmapLogRecallQueues	 Unsigned32, 
		smscEmapTrcreqDiscarded	 Unsigned32, 
		smscEmapDummyStatistic	 Unsigned32, 
		smscEmapAlerts	 Unsigned32, 
		smscEmapErrInternal	 Unsigned32, 
		smscEmapErrUnknownSubs	 Unsigned32, 
		smscEmapErrAbsentSubs	 Unsigned32, 
		smscEmapSmMtFailed	 Unsigned32, 
		smscEmapSmMtOk	 Unsigned32, 
		smscEmapSmMoFailed	 Unsigned32, 
		smscEmapSmMoOk	 Unsigned32
	}

smscEmapName  OBJECT-TYPE
	SYNTAX  DisplayString
	MAX-ACCESS  read-only
	STATUS   current
	DESCRIPTION
		"Identifies the name of the entity."
   ::= {emapInstanceEntry 1 }

smscEmapState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { emapInstanceEntry 2 }


smscEmapLastupdate OBJECT-TYPE
		SYNTAX	TimeTicks
		MAX-ACCESS read-only
		STATUS current
		DESCRIPTION
			"Value which reflects the last time the entities fields have been updated"
	::= { emapInstanceEntry	3 }

smscEmapNode  OBJECT-TYPE
	SYNTAX  DisplayString
	MAX-ACCESS  read-only
	STATUS   current
	DESCRIPTION
		"Identifies the node the entity is running on."
   ::= {emapInstanceEntry 4 }

smscEmapMsgReceived OBJECT-TYPE
		SYNTAX	Unsigned32
		MAX-ACCESS read-only
		STATUS current
		DESCRIPTION
			"Received messages"
	::= { emapInstanceEntry	5 }

smscEmapMsgRejected OBJECT-TYPE
		SYNTAX	Unsigned32
		MAX-ACCESS read-only
		STATUS current
		DESCRIPTION
			"Received messages and rejected"
	::= { emapInstanceEntry	6 }

smscEmapMsgTransmitted OBJECT-TYPE
		SYNTAX	Unsigned32
		MAX-ACCESS read-only
		STATUS current
		DESCRIPTION
			"Transmitted messages"
	::= { emapInstanceEntry	7 }

smscEmapMsgFailed OBJECT-TYPE
		SYNTAX	Unsigned32
		MAX-ACCESS read-only
		STATUS current
		DESCRIPTION
			"Messages that failed on sending"
	::= { emapInstanceEntry	8 }

smscEmapQelemUsed OBJECT-TYPE
		SYNTAX	Unsigned32
		MAX-ACCESS read-only
		STATUS current
		DESCRIPTION
			"Number of elements in internal queues"
	::= { emapInstanceEntry	9 }

smscEmapQelemInProcqueue OBJECT-TYPE
		SYNTAX	Unsigned32
		MAX-ACCESS read-only
		STATUS current
		DESCRIPTION
			"Number of elements used in process queue"
	::= { emapInstanceEntry	10 }

smscEmapQelemInExpqueue OBJECT-TYPE
		SYNTAX	Unsigned32
		MAX-ACCESS read-only
		STATUS current
		DESCRIPTION
			"Number of elements used in expedited queue"
	::= { emapInstanceEntry	11 }

smscEmapNrTimersRunning OBJECT-TYPE
		SYNTAX	Unsigned32
		MAX-ACCESS read-only
		STATUS current
		DESCRIPTION
			"Total number of timers running"
	::= { emapInstanceEntry	12 }

smscEmapNrSystemTimers OBJECT-TYPE
		SYNTAX	Unsigned32
		MAX-ACCESS read-only
		STATUS current
		DESCRIPTION
			"Number of system timers running"
	::= { emapInstanceEntry	13 }

smscEmapImiRecallQelem OBJECT-TYPE
		SYNTAX	Unsigned32
		MAX-ACCESS read-only
		STATUS current
		DESCRIPTION
			"Number of IMI recall-queue elements used"
	::= { emapInstanceEntry	14 }

smscEmapImiRecallQueues OBJECT-TYPE
		SYNTAX	Unsigned32
		MAX-ACCESS read-only
		STATUS current
		DESCRIPTION
			"Number of IMI-recall-queues used"
	::= { emapInstanceEntry	15 }

smscEmapIdiRecallQelem OBJECT-TYPE
		SYNTAX	Unsigned32
		MAX-ACCESS read-only
		STATUS current
		DESCRIPTION
			"Number of IDI recall-queue elements used"
	::= { emapInstanceEntry	16 }

smscEmapIdiRecallQueues OBJECT-TYPE
		SYNTAX	Unsigned32
		MAX-ACCESS read-only
		STATUS current
		DESCRIPTION
			"Number of IDI recall-queues used"
	::= { emapInstanceEntry	17 }

smscEmapIosRecallQelem OBJECT-TYPE
		SYNTAX	Unsigned32
		MAX-ACCESS read-only
		STATUS current
		DESCRIPTION
			"Number of IOS recall-queue elements used"
	::= { emapInstanceEntry	18 }

smscEmapIosRecallQueues OBJECT-TYPE
		SYNTAX	Unsigned32
		MAX-ACCESS read-only
		STATUS current
		DESCRIPTION
			"Number of IOS recall-queues used"
	::= { emapInstanceEntry	19 }

smscEmapLogRecallQelem OBJECT-TYPE
		SYNTAX	Unsigned32
		MAX-ACCESS read-only
		STATUS current
		DESCRIPTION
			"Number of LOG recall-queue elements used"
	::= { emapInstanceEntry	20 }

smscEmapLogRecallQueues OBJECT-TYPE
		SYNTAX	Unsigned32
		MAX-ACCESS read-only
		STATUS current
		DESCRIPTION
			"Number of LOG recall-queues used"
	::= { emapInstanceEntry	21 }

smscEmapTrcreqDiscarded OBJECT-TYPE
		SYNTAX	Unsigned32
		MAX-ACCESS read-only
		STATUS current
		DESCRIPTION
			"Number of trace requests discarded"
	::= { emapInstanceEntry	22 }

smscEmapDummyStatistic OBJECT-TYPE
		SYNTAX	Unsigned32
		MAX-ACCESS read-only
		STATUS current
		DESCRIPTION
			"No statistical counters"
	::= { emapInstanceEntry	23 }

smscEmapAlerts OBJECT-TYPE
		SYNTAX	Unsigned32
		MAX-ACCESS read-only
		STATUS current
		DESCRIPTION
			"Number of invoke indications with ALERT_SC"
	::= { emapInstanceEntry	24 }

smscEmapErrInternal OBJECT-TYPE
		SYNTAX	Unsigned32
		MAX-ACCESS read-only
		STATUS current
		DESCRIPTION
			"Number of Signalling System Nr.7 errors"
	::= { emapInstanceEntry	25 }

smscEmapErrUnknownSubs OBJECT-TYPE
		SYNTAX	Unsigned32
		MAX-ACCESS read-only
		STATUS current
		DESCRIPTION
			"Number of Unknown Subscriber errors"
	::= { emapInstanceEntry	26 }

smscEmapErrAbsentSubs OBJECT-TYPE
		SYNTAX	Unsigned32
		MAX-ACCESS read-only
		STATUS current
		DESCRIPTION
			"Number of Absent Subscriber errors"
	::= { emapInstanceEntry	27 }

smscEmapSmMtFailed OBJECT-TYPE
		SYNTAX	Unsigned32
		MAX-ACCESS read-only
		STATUS current
		DESCRIPTION
			"Number of failed Mobile Terminated SM"
	::= { emapInstanceEntry	28 }

smscEmapSmMtOk OBJECT-TYPE
		SYNTAX	Unsigned32
		MAX-ACCESS read-only
		STATUS current
		DESCRIPTION
			"Number of delivered Forward Mobile Terminated Short Messages"
	::= { emapInstanceEntry	29 }

smscEmapSmMoFailed OBJECT-TYPE
		SYNTAX	Unsigned32
		MAX-ACCESS read-only
		STATUS current
		DESCRIPTION
			"Number of invalid mobile originated SM"
	::= { emapInstanceEntry	30 }

smscEmapSmMoOk OBJECT-TYPE
		SYNTAX	Unsigned32
		MAX-ACCESS read-only
		STATUS current
		DESCRIPTION
			"Number of valid received mobile originated SM"
	::= { emapInstanceEntry	31 }



-- end of EMAP description.
-- --------------------------------------


-- --------------------------------------
-- Class PSTNA
-- 
smscPstna OBJECT-TYPE
	SYNTAX  SEQUENCE OF PstnaInstanceEntry
	MAX-ACCESS  not-accessible
	STATUS  current
	DESCRIPTION
		"Mapping table for SMSC PSTNA entities."
   ::= { smscClassServer   5  }

pstnaInstanceEntry  OBJECT-TYPE
	SYNTAX PstnaInstanceEntry
	MAX-ACCESS  not-accessible
	STATUS  current
	DESCRIPTION
		"An entry (row) in the entityInstanceTable."
	INDEX { IMPLIED smscPstnaName }
   ::= { smscPstna 1 }

PstnaInstanceEntry ::= SEQUENCE {
		smscPstnaName     DisplayString,
		smscPstnaState   INTEGER,
		smscPstnaLastupdate   TimeTicks,
		smscPstnaNode	   DisplayString, 
		smscPstnaMsgReceived	 Unsigned32, 
		smscPstnaMsgRejected	 Unsigned32, 
		smscPstnaMsgTransmitted	 Unsigned32, 
		smscPstnaMsgFailed	 Unsigned32, 
		smscPstnaConTot	 Unsigned32, 
		smscPstnaConIn	 Unsigned32, 
		smscPstnaConInAcc	 Unsigned32, 
		smscPstnaConOut	 Unsigned32, 
		smscPstnaConOutAcc	 Unsigned32, 
		smscPstnaConOutBusy	 Unsigned32, 
		smscPstnaConOutNoAnswer	 Unsigned32, 
		smscPstnaConOutOtherFail	 Unsigned32, 
		smscPstnaConTimeCumulative	 Unsigned32, 
		smscPstnaQelemUsed	 Unsigned32, 
		smscPstnaQelemInProcqueue	 Unsigned32, 
		smscPstnaQelemInExpqueue	 Unsigned32, 
		smscPstnaNrTimersRunning	 Unsigned32, 
		smscPstnaNrSystemTimers	 Unsigned32, 
		smscPstnaImiRecallQelem	 Unsigned32, 
		smscPstnaImiRecallQueues	 Unsigned32, 
		smscPstnaIdiRecallQelem	 Unsigned32, 
		smscPstnaIdiRecallQueues	 Unsigned32, 
		smscPstnaIosRecallQelem	 Unsigned32, 
		smscPstnaIosRecallQueues	 Unsigned32, 
		smscPstnaLogRecallQelem	 Unsigned32, 
		smscPstnaLogRecallQueues	 Unsigned32, 
		smscPstnaTrcreqDiscarded	 Unsigned32
	}

smscPstnaName  OBJECT-TYPE
	SYNTAX  DisplayString
	MAX-ACCESS  read-only
	STATUS   current
	DESCRIPTION
		"Identifies the name of the entity."
   ::= {pstnaInstanceEntry 1 }

smscPstnaState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { pstnaInstanceEntry 2 }


smscPstnaLastupdate OBJECT-TYPE
		SYNTAX	TimeTicks
		MAX-ACCESS read-only
		STATUS current
		DESCRIPTION
			"Value which reflects the last time the entities fields have been updated"
	::= { pstnaInstanceEntry	3 }

smscPstnaNode  OBJECT-TYPE
	SYNTAX  DisplayString
	MAX-ACCESS  read-only
	STATUS   current
	DESCRIPTION
		"Identifies the node the entity is running on."
   ::= {pstnaInstanceEntry 4 }

smscPstnaMsgReceived OBJECT-TYPE
		SYNTAX	Unsigned32
		MAX-ACCESS read-only
		STATUS current
		DESCRIPTION
			"Received messages"
	::= { pstnaInstanceEntry	5 }

smscPstnaMsgRejected OBJECT-TYPE
		SYNTAX	Unsigned32
		MAX-ACCESS read-only
		STATUS current
		DESCRIPTION
			"Received messages and rejected"
	::= { pstnaInstanceEntry	6 }

smscPstnaMsgTransmitted OBJECT-TYPE
		SYNTAX	Unsigned32
		MAX-ACCESS read-only
		STATUS current
		DESCRIPTION
			"Transmitted messages"
	::= { pstnaInstanceEntry	7 }

smscPstnaMsgFailed OBJECT-TYPE
		SYNTAX	Unsigned32
		MAX-ACCESS read-only
		STATUS current
		DESCRIPTION
			"Messages that failed on sending"
	::= { pstnaInstanceEntry	8 }

smscPstnaConTot OBJECT-TYPE
		SYNTAX	Unsigned32
		MAX-ACCESS read-only
		STATUS current
		DESCRIPTION
			"Network connections"
	::= { pstnaInstanceEntry	9 }

smscPstnaConIn OBJECT-TYPE
		SYNTAX	Unsigned32
		MAX-ACCESS read-only
		STATUS current
		DESCRIPTION
			"Received network connections"
	::= { pstnaInstanceEntry	10 }

smscPstnaConInAcc OBJECT-TYPE
		SYNTAX	Unsigned32
		MAX-ACCESS read-only
		STATUS current
		DESCRIPTION
			"Accepted received network connections"
	::= { pstnaInstanceEntry	11 }

smscPstnaConOut OBJECT-TYPE
		SYNTAX	Unsigned32
		MAX-ACCESS read-only
		STATUS current
		DESCRIPTION
			"Initiated network connections"
	::= { pstnaInstanceEntry	12 }

smscPstnaConOutAcc OBJECT-TYPE
		SYNTAX	Unsigned32
		MAX-ACCESS read-only
		STATUS current
		DESCRIPTION
			"Accepted initiated network connections"
	::= { pstnaInstanceEntry	13 }

smscPstnaConOutBusy OBJECT-TYPE
		SYNTAX	Unsigned32
		MAX-ACCESS read-only
		STATUS current
		DESCRIPTION
			"Initiated network connections resulting in busy tone"
	::= { pstnaInstanceEntry	14 }

smscPstnaConOutNoAnswer OBJECT-TYPE
		SYNTAX	Unsigned32
		MAX-ACCESS read-only
		STATUS current
		DESCRIPTION
			"Initiated network connections resulting in no answer tone"
	::= { pstnaInstanceEntry	15 }

smscPstnaConOutOtherFail OBJECT-TYPE
		SYNTAX	Unsigned32
		MAX-ACCESS read-only
		STATUS current
		DESCRIPTION
			"Initiated network connections resulting in other failures"
	::= { pstnaInstanceEntry	16 }

smscPstnaConTimeCumulative OBJECT-TYPE
		SYNTAX	Unsigned32
		MAX-ACCESS read-only
		STATUS current
		DESCRIPTION
			"Accumulated session duration time"
	::= { pstnaInstanceEntry	17 }

smscPstnaQelemUsed OBJECT-TYPE
		SYNTAX	Unsigned32
		MAX-ACCESS read-only
		STATUS current
		DESCRIPTION
			"Number of elements in internal queues"
	::= { pstnaInstanceEntry	18 }

smscPstnaQelemInProcqueue OBJECT-TYPE
		SYNTAX	Unsigned32
		MAX-ACCESS read-only
		STATUS current
		DESCRIPTION
			"Number of elements used in process queue"
	::= { pstnaInstanceEntry	19 }

smscPstnaQelemInExpqueue OBJECT-TYPE
		SYNTAX	Unsigned32
		MAX-ACCESS read-only
		STATUS current
		DESCRIPTION
			"Number of elements used in expedited queue"
	::= { pstnaInstanceEntry	20 }

smscPstnaNrTimersRunning OBJECT-TYPE
		SYNTAX	Unsigned32
		MAX-ACCESS read-only
		STATUS current
		DESCRIPTION
			"Total number of timers running"
	::= { pstnaInstanceEntry	21 }

smscPstnaNrSystemTimers OBJECT-TYPE
		SYNTAX	Unsigned32
		MAX-ACCESS read-only
		STATUS current
		DESCRIPTION
			"Number of system timers running"
	::= { pstnaInstanceEntry	22 }

smscPstnaImiRecallQelem OBJECT-TYPE
		SYNTAX	Unsigned32
		MAX-ACCESS read-only
		STATUS current
		DESCRIPTION
			"Number of IMI recall-queue elements used"
	::= { pstnaInstanceEntry	23 }

smscPstnaImiRecallQueues OBJECT-TYPE
		SYNTAX	Unsigned32
		MAX-ACCESS read-only
		STATUS current
		DESCRIPTION
			"Number of IMI-recall-queues used"
	::= { pstnaInstanceEntry	24 }

smscPstnaIdiRecallQelem OBJECT-TYPE
		SYNTAX	Unsigned32
		MAX-ACCESS read-only
		STATUS current
		DESCRIPTION
			"Number of IDI recall-queue elements used"
	::= { pstnaInstanceEntry	25 }

smscPstnaIdiRecallQueues OBJECT-TYPE
		SYNTAX	Unsigned32
		MAX-ACCESS read-only
		STATUS current
		DESCRIPTION
			"Number of IDI recall-queues used"
	::= { pstnaInstanceEntry	26 }

smscPstnaIosRecallQelem OBJECT-TYPE
		SYNTAX	Unsigned32
		MAX-ACCESS read-only
		STATUS current
		DESCRIPTION
			"Number of IOS recall-queue elements used"
	::= { pstnaInstanceEntry	27 }

smscPstnaIosRecallQueues OBJECT-TYPE
		SYNTAX	Unsigned32
		MAX-ACCESS read-only
		STATUS current
		DESCRIPTION
			"Number of IOS recall-queues used"
	::= { pstnaInstanceEntry	28 }

smscPstnaLogRecallQelem OBJECT-TYPE
		SYNTAX	Unsigned32
		MAX-ACCESS read-only
		STATUS current
		DESCRIPTION
			"Number of LOG recall-queue elements used"
	::= { pstnaInstanceEntry	29 }

smscPstnaLogRecallQueues OBJECT-TYPE
		SYNTAX	Unsigned32
		MAX-ACCESS read-only
		STATUS current
		DESCRIPTION
			"Number of LOG recall-queues used"
	::= { pstnaInstanceEntry	30 }

smscPstnaTrcreqDiscarded OBJECT-TYPE
		SYNTAX	Unsigned32
		MAX-ACCESS read-only
		STATUS current
		DESCRIPTION
			"Number of trace requests discarded"
	::= { pstnaInstanceEntry	31 }



-- end of PSTNA description.
-- --------------------------------------


-- --------------------------------------
-- Class GIW
-- 
smscGiw OBJECT-TYPE
	SYNTAX  SEQUENCE OF GiwInstanceEntry
	MAX-ACCESS  not-accessible
	STATUS  current
	DESCRIPTION
		"Mapping table for SMSC GIW entities."
   ::= { smscClassServer   6  }

giwInstanceEntry  OBJECT-TYPE
	SYNTAX GiwInstanceEntry
	MAX-ACCESS  not-accessible
	STATUS  current
	DESCRIPTION
		"An entry (row) in the entityInstanceTable."
	INDEX { IMPLIED smscGiwName }
   ::= { smscGiw 1 }

GiwInstanceEntry ::= SEQUENCE {
		smscGiwName     DisplayString,
		smscGiwState   INTEGER,
		smscGiwLastupdate   TimeTicks,
		smscGiwNode	   DisplayString, 
		smscGiwMsgReceived	 Unsigned32, 
		smscGiwMsgRejected	 Unsigned32, 
		smscGiwMsgTransmitted	 Unsigned32, 
		smscGiwMsgFailed	 Unsigned32, 
		smscGiwDialogues	 Unsigned32, 
		smscGiwSessionsPending	 Unsigned32, 
		smscGiwDialoguesPending	 Unsigned32, 
		smscGiwSystemFailure	 Unsigned32, 
		smscGiwUnexpectedDataValue	 Unsigned32, 
		smscGiwQelemUsed	 Unsigned32, 
		smscGiwQelemInProcqueue	 Unsigned32, 
		smscGiwQelemInExpqueue	 Unsigned32, 
		smscGiwNrTimersRunning	 Unsigned32, 
		smscGiwNrSystemTimers	 Unsigned32, 
		smscGiwImiRecallQelem	 Unsigned32, 
		smscGiwImiRecallQueues	 Unsigned32, 
		smscGiwIdiRecallQelem	 Unsigned32, 
		smscGiwIdiRecallQueues	 Unsigned32, 
		smscGiwIosRecallQelem	 Unsigned32, 
		smscGiwIosRecallQueues	 Unsigned32, 
		smscGiwLogRecallQelem	 Unsigned32, 
		smscGiwLogRecallQueues	 Unsigned32, 
		smscGiwTrcreqDiscarded	 Unsigned32, 
		smscGiwMtsmOk	 Unsigned32, 
		smscGiwMtsmFail	 Unsigned32, 
		smscGiwMosmOk	 Unsigned32, 
		smscGiwMosmFail	 Unsigned32, 
		smscGiwRoutInfoOk	 Unsigned32, 
		smscGiwRoutInfoFail	 Unsigned32, 
		smscGiwDelStatOk	 Unsigned32, 
		smscGiwDelStatFail	 Unsigned32, 
		smscGiwAlertOk	 Unsigned32, 
		smscGiwAlertFail	 Unsigned32, 
		smscGiwInformOk	 Unsigned32, 
		smscGiwInformFail	 Unsigned32, 
		smscGiwDataMissing	 Unsigned32, 
		smscGiwFacilityNotSupported	 Unsigned32, 
		smscGiwUnknownSubscriber	 Unsigned32, 
		smscGiwAbsentSubscriber	 Unsigned32, 
		smscGiwUnidentifiedSubscriber	 Unsigned32, 
		smscGiwIllegalSubscriber	 Unsigned32, 
		smscGiwIllegalEquipment	 Unsigned32, 
		smscGiwTeleserviceNotProv	 Unsigned32, 
		smscGiwCallBarred	 Unsigned32, 
		smscGiwNoRespFromPeer	 Unsigned32, 
		smscGiwMsgWaitingListFull	 Unsigned32, 
		smscGiwSmDeliveryFailure	 Unsigned32, 
		smscGiwSubscriberBusyForMtSms	 Unsigned32, 
		smscGiwMapOpenRej	 Unsigned32, 
		smscGiwMapAbort	 Unsigned32, 
		smscGiwMtsmOkMscFirst	 Unsigned32, 
		smscGiwMtsmOkSgsnFirst	 Unsigned32, 
		smscGiwMtsmOkMscSecond	 Unsigned32, 
		smscGiwMtsmOkSgsnSecond	 Unsigned32, 
		smscGiwMtsmFailMscFirst	 Unsigned32, 
		smscGiwMtsmFailSgsnFirst	 Unsigned32, 
		smscGiwMtsmFailMscSecond	 Unsigned32, 
		smscGiwMtsmFailSgsnSecond	 Unsigned32, 
		smscGiwAbsentSubsMscFirst	 Unsigned32, 
		smscGiwAbsentSubsSgsnFirst	 Unsigned32, 
		smscGiwAbsentSubsMscSecond	 Unsigned32, 
		smscGiwAbsentSubsSgsnSecond	 Unsigned32, 
		smscGiwAbsentSubsHlr	 Unsigned32, 
		smscGiwMapDiaQueueFailed	 Unsigned32, 
		smscGiwMapDiaFree	 Unsigned32, 
		smscGiwMapDiaInUse	 Unsigned32, 
		smscGiwMapDiaMaxUsed	 Unsigned32, 
		smscGiwMapDiaAllocFailed	 Unsigned32, 
		smscGiwMapOperFree	 Unsigned32, 
		smscGiwMapOperInUse	 Unsigned32, 
		smscGiwMapOperMaxUsed	 Unsigned32, 
		smscGiwMapOperAllocFailed	 Unsigned32, 
		smscGiwMapBufFree	 Unsigned32, 
		smscGiwMapBufInUse	 Unsigned32, 
		smscGiwMapBufMaxUsed	 Unsigned32, 
		smscGiwMapBufAllocFailed	 Unsigned32, 
		smscGiwMapProtoErr	 Unsigned32, 
		smscGiwMapPrvDecErr	 Unsigned32, 
		smscGiwMapPduDecErr	 Unsigned32, 
		smscGiwMapOpcodeErr	 Unsigned32, 
		smscGiwMapInvokeErr	 Unsigned32, 
		smscGiwMapInvAppCtxt	 Unsigned32, 
		smscGiwMapAppCtxtMism	 Unsigned32, 
		smscGiwTcapBeginRcvd	 Unsigned32, 
		smscGiwTcapContRcvd	 Unsigned32, 
		smscGiwTcapEndRcvd	 Unsigned32, 
		smscGiwTcapBeginSnt	 Unsigned32, 
		smscGiwTcapContSnt	 Unsigned32, 
		smscGiwTcapEndSnt	 Unsigned32, 
		smscGiwTcapFailedSent	 Unsigned32, 
		smscGiwTcapTransDisc	 Unsigned32, 
		smscGiwTcapMsgDisc	 Unsigned32, 
		smscGiwTcapUnknMsgRcvd	 Unsigned32, 
		smscGiwTcapNoticeRcvd	 Unsigned32, 
		smscGiwTcapAbtRcvd	 Unsigned32, 
		smscGiwTcapAbtUnrecmtRcvd	 Unsigned32, 
		smscGiwTcapAbtTranpRcvd	 Unsigned32, 
		smscGiwTcapAbtBftpRcvd	 Unsigned32, 
		smscGiwTcapAbtUnrecidRcvd	 Unsigned32, 
		smscGiwTcapAbtReslimitRcvd	 Unsigned32, 
		smscGiwTcapAbtAbnormRcvd	 Unsigned32, 
		smscGiwTcapAbtSnt	 Unsigned32, 
		smscGiwTcapAbtUnrecmtSnt	 Unsigned32, 
		smscGiwTcapAbtTranpSnt	 Unsigned32, 
		smscGiwTcapAbtBftpSnt	 Unsigned32, 
		smscGiwTcapAbtUnrecidSnt	 Unsigned32, 
		smscGiwTcapAbtReslimitSnt	 Unsigned32, 
		smscGiwTcapAbtAbnormSnt	 Unsigned32, 
		smscGiwTcapUabtRcvd	 Unsigned32, 
		smscGiwTcapUabtSnt	 Unsigned32, 
		smscGiwTcapInvkRcvd	 Unsigned32, 
		smscGiwTcapInvkSnt	 Unsigned32, 
		smscGiwTcapResLastRcvd	 Unsigned32, 
		smscGiwTcapResNolastRcvd	 Unsigned32, 
		smscGiwTcapResLastSnt	 Unsigned32, 
		smscGiwTcapResNolastSnt	 Unsigned32, 
		smscGiwTcapErrorRcvd	 Unsigned32, 
		smscGiwTcapErrorSnt	 Unsigned32, 
		smscGiwTcapRjctSnt	 Unsigned32, 
		smscGiwTcapRjctRcvd	 Unsigned32, 
		smscGiwTcapRjctUnrecRcvd	 Unsigned32, 
		smscGiwTcapRjctMistypeRcvd	 Unsigned32, 
		smscGiwTcapRjctBadsRcvd	 Unsigned32, 
		smscGiwTcapRjctUnrLidRcvd	 Unsigned32, 
		smscGiwTcapRjctUiRrRcvd	 Unsigned32, 
		smscGiwTcapRjctUiReRcvd	 Unsigned32, 
		smscGiwTcapRjctUnxpRrRcvd	 Unsigned32, 
		smscGiwTcapRjctUnxpReRcvd	 Unsigned32, 
		smscGiwTcapRjctDupIidRcvd	 Unsigned32, 
		smscGiwTcapPrbUnrecOpRcvd	 Unsigned32, 
		smscGiwTcapPrbMistypeRcvd	 Unsigned32, 
		smscGiwTcapPrbReslimitRcvd	 Unsigned32, 
		smscGiwTcapPrbInitrelRcvd	 Unsigned32, 
		smscGiwTcapPrbUnlRespRcvd	 Unsigned32, 
		smscGiwTcapPrbUnlOpRcvd	 Unsigned32, 
		smscGiwTcapPrbMtRrRcvd	 Unsigned32, 
		smscGiwTcapPrbMtReRcvd	 Unsigned32, 
		smscGiwTcapUserUnrecRcvd	 Unsigned32, 
		smscGiwTcapUserUnxpRcvd	 Unsigned32, 
		smscGiwTcapActiveDialog	 Unsigned32, 
		smscGiwTcapInitiatedDialog	 Unsigned32, 
		smscGiwTcapActiveDlgs	 Unsigned32, 
		smscGiwTcapInitiatedDlgs	 Unsigned32, 
		smscGiwFsgLoopPreventedSm	 Unsigned32, 
		smscGiwFsgMtsmOk	 Unsigned32, 
		smscGiwFsgMtsmFail	 Unsigned32, 
		smscGiwMapScCongestion	 Unsigned32, 
		smscGiwMapInvalidSmeAddress	 Unsigned32, 
		smscGiwMapSubscrNotScSubscriber	 Unsigned32, 
		smscGiwMapUnknownSc	 Unsigned32, 
		smscGiwMtMemcapExceeded	 Unsigned32, 
		smscGiwMtMsProtocolErr	 Unsigned32, 
		smscGiwMtMsNotEquipped	 Unsigned32, 
		smscGiwMoAntiFraudRejHlr	 Unsigned32, 
		smscGiwMoAntiFraudRejGt	 Unsigned32, 
		smscGiwMoAntiFraudRejImsi	 Unsigned32
	}

smscGiwName  OBJECT-TYPE
	SYNTAX  DisplayString
	MAX-ACCESS  read-only
	STATUS   current
	DESCRIPTION
		"Identifies the name of the entity."
   ::= {giwInstanceEntry 1 }

smscGiwState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { giwInstanceEntry 2 }


smscGiwLastupdate OBJECT-TYPE
		SYNTAX	TimeTicks
		MAX-ACCESS read-only
		STATUS current
		DESCRIPTION
			"Value which reflects the last time the entities fields have been updated"
	::= { giwInstanceEntry	3 }

smscGiwNode  OBJECT-TYPE
	SYNTAX  DisplayString
	MAX-ACCESS  read-only
	STATUS   current
	DESCRIPTION
		"Identifies the node the entity is running on."
   ::= {giwInstanceEntry 4 }

smscGiwMsgReceived OBJECT-TYPE
		SYNTAX	Unsigned32
		MAX-ACCESS read-only
		STATUS current
		DESCRIPTION
			"Received messages"
	::= { giwInstanceEntry	5 }

smscGiwMsgRejected OBJECT-TYPE
		SYNTAX	Unsigned32
		MAX-ACCESS read-only
		STATUS current
		DESCRIPTION
			"Received messages and rejected"
	::= { giwInstanceEntry	6 }

smscGiwMsgTransmitted OBJECT-TYPE
		SYNTAX	Unsigned32
		MAX-ACCESS read-only
		STATUS current
		DESCRIPTION
			"Transmitted messages"
	::= { giwInstanceEntry	7 }

smscGiwMsgFailed OBJECT-TYPE
		SYNTAX	Unsigned32
		MAX-ACCESS read-only
		STATUS current
		DESCRIPTION
			"Messages that failed on sending"
	::= { giwInstanceEntry	8 }

smscGiwDialogues OBJECT-TYPE
		SYNTAX	Unsigned32
		MAX-ACCESS read-only
		STATUS current
		DESCRIPTION
			"Number of dialogues"
	::= { giwInstanceEntry	9 }

smscGiwSessionsPending OBJECT-TYPE
		SYNTAX	Unsigned32
		MAX-ACCESS read-only
		STATUS current
		DESCRIPTION
			"Number of sessions (currently) pending"
	::= { giwInstanceEntry	10 }

smscGiwDialoguesPending OBJECT-TYPE
		SYNTAX	Unsigned32
		MAX-ACCESS read-only
		STATUS current
		DESCRIPTION
			"Number of dialogues (currently) pending"
	::= { giwInstanceEntry	11 }

smscGiwSystemFailure OBJECT-TYPE
		SYNTAX	Unsigned32
		MAX-ACCESS read-only
		STATUS current
		DESCRIPTION
			"Number of System Failure errors"
	::= { giwInstanceEntry	12 }

smscGiwUnexpectedDataValue OBJECT-TYPE
		SYNTAX	Unsigned32
		MAX-ACCESS read-only
		STATUS current
		DESCRIPTION
			"Number of Unexpected Data Value errors"
	::= { giwInstanceEntry	13 }

smscGiwQelemUsed OBJECT-TYPE
		SYNTAX	Unsigned32
		MAX-ACCESS read-only
		STATUS current
		DESCRIPTION
			"Number of elements in internal queues"
	::= { giwInstanceEntry	14 }

smscGiwQelemInProcqueue OBJECT-TYPE
		SYNTAX	Unsigned32
		MAX-ACCESS read-only
		STATUS current
		DESCRIPTION
			"Number of elements used in process queue"
	::= { giwInstanceEntry	15 }

smscGiwQelemInExpqueue OBJECT-TYPE
		SYNTAX	Unsigned32
		MAX-ACCESS read-only
		STATUS current
		DESCRIPTION
			"Number of elements used in expedited queue"
	::= { giwInstanceEntry	16 }

smscGiwNrTimersRunning OBJECT-TYPE
		SYNTAX	Unsigned32
		MAX-ACCESS read-only
		STATUS current
		DESCRIPTION
			"Total number of timers running"
	::= { giwInstanceEntry	17 }

smscGiwNrSystemTimers OBJECT-TYPE
		SYNTAX	Unsigned32
		MAX-ACCESS read-only
		STATUS current
		DESCRIPTION
			"Number of system timers running"
	::= { giwInstanceEntry	18 }

smscGiwImiRecallQelem OBJECT-TYPE
		SYNTAX	Unsigned32
		MAX-ACCESS read-only
		STATUS current
		DESCRIPTION
			"Number of IMI recall-queue elements used"
	::= { giwInstanceEntry	19 }

smscGiwImiRecallQueues OBJECT-TYPE
		SYNTAX	Unsigned32
		MAX-ACCESS read-only
		STATUS current
		DESCRIPTION
			"Number of IMI-recall-queues used"
	::= { giwInstanceEntry	20 }

smscGiwIdiRecallQelem OBJECT-TYPE
		SYNTAX	Unsigned32
		MAX-ACCESS read-only
		STATUS current
		DESCRIPTION
			"Number of IDI recall-queue elements used"
	::= { giwInstanceEntry	21 }

smscGiwIdiRecallQueues OBJECT-TYPE
		SYNTAX	Unsigned32
		MAX-ACCESS read-only
		STATUS current
		DESCRIPTION
			"Number of IDI recall-queues used"
	::= { giwInstanceEntry	22 }

smscGiwIosRecallQelem OBJECT-TYPE
		SYNTAX	Unsigned32
		MAX-ACCESS read-only
		STATUS current
		DESCRIPTION
			"Number of IOS recall-queue elements used"
	::= { giwInstanceEntry	23 }

smscGiwIosRecallQueues OBJECT-TYPE
		SYNTAX	Unsigned32
		MAX-ACCESS read-only
		STATUS current
		DESCRIPTION
			"Number of IOS recall-queues used"
	::= { giwInstanceEntry	24 }

smscGiwLogRecallQelem OBJECT-TYPE
		SYNTAX	Unsigned32
		MAX-ACCESS read-only
		STATUS current
		DESCRIPTION
			"Number of LOG recall-queue elements used"
	::= { giwInstanceEntry	25 }

smscGiwLogRecallQueues OBJECT-TYPE
		SYNTAX	Unsigned32
		MAX-ACCESS read-only
		STATUS current
		DESCRIPTION
			"Number of LOG recall-queues used"
	::= { giwInstanceEntry	26 }

smscGiwTrcreqDiscarded OBJECT-TYPE
		SYNTAX	Unsigned32
		MAX-ACCESS read-only
		STATUS current
		DESCRIPTION
			"Number of trace requests discarded"
	::= { giwInstanceEntry	27 }

smscGiwMtsmOk OBJECT-TYPE
		SYNTAX	Unsigned32
		MAX-ACCESS read-only
		STATUS current
		DESCRIPTION
			"Number of delivered Mobile Terminated SM"
	::= { giwInstanceEntry	28 }

smscGiwMtsmFail OBJECT-TYPE
		SYNTAX	Unsigned32
		MAX-ACCESS read-only
		STATUS current
		DESCRIPTION
			"Number of failed Mobile Terminated SM"
	::= { giwInstanceEntry	29 }

smscGiwMosmOk OBJECT-TYPE
		SYNTAX	Unsigned32
		MAX-ACCESS read-only
		STATUS current
		DESCRIPTION
			"Number of accepted Mobile Originated SM"
	::= { giwInstanceEntry	30 }

smscGiwMosmFail OBJECT-TYPE
		SYNTAX	Unsigned32
		MAX-ACCESS read-only
		STATUS current
		DESCRIPTION
			"Number of rejected Mobile Originated SM"
	::= { giwInstanceEntry	31 }

smscGiwRoutInfoOk OBJECT-TYPE
		SYNTAX	Unsigned32
		MAX-ACCESS read-only
		STATUS current
		DESCRIPTION
			"Number of succesful Routing Info requests"
	::= { giwInstanceEntry	32 }

smscGiwRoutInfoFail OBJECT-TYPE
		SYNTAX	Unsigned32
		MAX-ACCESS read-only
		STATUS current
		DESCRIPTION
			"Number of failed Routing Info requests"
	::= { giwInstanceEntry	33 }

smscGiwDelStatOk OBJECT-TYPE
		SYNTAX	Unsigned32
		MAX-ACCESS read-only
		STATUS current
		DESCRIPTION
			"Number of successful Delivery Status Reports"
	::= { giwInstanceEntry	34 }

smscGiwDelStatFail OBJECT-TYPE
		SYNTAX	Unsigned32
		MAX-ACCESS read-only
		STATUS current
		DESCRIPTION
			"Number of failed Delivery Status Reports"
	::= { giwInstanceEntry	35 }

smscGiwAlertOk OBJECT-TYPE
		SYNTAX	Unsigned32
		MAX-ACCESS read-only
		STATUS current
		DESCRIPTION
			"Number of accepted Alert SC indications"
	::= { giwInstanceEntry	36 }

smscGiwAlertFail OBJECT-TYPE
		SYNTAX	Unsigned32
		MAX-ACCESS read-only
		STATUS current
		DESCRIPTION
			"Number of rejected Alert SC indications"
	::= { giwInstanceEntry	37 }

smscGiwInformOk OBJECT-TYPE
		SYNTAX	Unsigned32
		MAX-ACCESS read-only
		STATUS current
		DESCRIPTION
			"Number of accepted Inform SC indications"
	::= { giwInstanceEntry	38 }

smscGiwInformFail OBJECT-TYPE
		SYNTAX	Unsigned32
		MAX-ACCESS read-only
		STATUS current
		DESCRIPTION
			"Number of rejected Inform SC indications"
	::= { giwInstanceEntry	39 }

smscGiwDataMissing OBJECT-TYPE
		SYNTAX	Unsigned32
		MAX-ACCESS read-only
		STATUS current
		DESCRIPTION
			"Number of Data Missing errors"
	::= { giwInstanceEntry	40 }

smscGiwFacilityNotSupported OBJECT-TYPE
		SYNTAX	Unsigned32
		MAX-ACCESS read-only
		STATUS current
		DESCRIPTION
			"Number of Facility Not Supported errors"
	::= { giwInstanceEntry	41 }

smscGiwUnknownSubscriber OBJECT-TYPE
		SYNTAX	Unsigned32
		MAX-ACCESS read-only
		STATUS current
		DESCRIPTION
			"Number of Unknown Subscriber errors"
	::= { giwInstanceEntry	42 }

smscGiwAbsentSubscriber OBJECT-TYPE
		SYNTAX	Unsigned32
		MAX-ACCESS read-only
		STATUS current
		DESCRIPTION
			"Number of Absent Subscriber errors"
	::= { giwInstanceEntry	43 }

smscGiwUnidentifiedSubscriber OBJECT-TYPE
		SYNTAX	Unsigned32
		MAX-ACCESS read-only
		STATUS current
		DESCRIPTION
			"Number of Unidentified Subscriber errors"
	::= { giwInstanceEntry	44 }

smscGiwIllegalSubscriber OBJECT-TYPE
		SYNTAX	Unsigned32
		MAX-ACCESS read-only
		STATUS current
		DESCRIPTION
			"Number of Illegal Subscriber errors"
	::= { giwInstanceEntry	45 }

smscGiwIllegalEquipment OBJECT-TYPE
		SYNTAX	Unsigned32
		MAX-ACCESS read-only
		STATUS current
		DESCRIPTION
			"Number of Illegal Equipment errors"
	::= { giwInstanceEntry	46 }

smscGiwTeleserviceNotProv OBJECT-TYPE
		SYNTAX	Unsigned32
		MAX-ACCESS read-only
		STATUS current
		DESCRIPTION
			"Number of Teleservice Not Provisioned errors"
	::= { giwInstanceEntry	47 }

smscGiwCallBarred OBJECT-TYPE
		SYNTAX	Unsigned32
		MAX-ACCESS read-only
		STATUS current
		DESCRIPTION
			"Number of Call Barred errors"
	::= { giwInstanceEntry	48 }

smscGiwNoRespFromPeer OBJECT-TYPE
		SYNTAX	Unsigned32
		MAX-ACCESS read-only
		STATUS current
		DESCRIPTION
			"Number of No Response From Peer (Timeout) errors"
	::= { giwInstanceEntry	49 }

smscGiwMsgWaitingListFull OBJECT-TYPE
		SYNTAX	Unsigned32
		MAX-ACCESS read-only
		STATUS current
		DESCRIPTION
			"Number of Message Waiting List Full errors"
	::= { giwInstanceEntry	50 }

smscGiwSmDeliveryFailure OBJECT-TYPE
		SYNTAX	Unsigned32
		MAX-ACCESS read-only
		STATUS current
		DESCRIPTION
			"Number of Short Message Delivery Failure errors"
	::= { giwInstanceEntry	51 }

smscGiwSubscriberBusyForMtSms OBJECT-TYPE
		SYNTAX	Unsigned32
		MAX-ACCESS read-only
		STATUS current
		DESCRIPTION
			"Number of Subscriber Busy for MT SMS errors"
	::= { giwInstanceEntry	52 }

smscGiwMapOpenRej OBJECT-TYPE
		SYNTAX	Unsigned32
		MAX-ACCESS read-only
		STATUS current
		DESCRIPTION
			"Number of rejected MAP-OPEN requests"
	::= { giwInstanceEntry	53 }

smscGiwMapAbort OBJECT-TYPE
		SYNTAX	Unsigned32
		MAX-ACCESS read-only
		STATUS current
		DESCRIPTION
			"Number of received MAP-ABORT indications"
	::= { giwInstanceEntry	54 }

smscGiwMtsmOkMscFirst OBJECT-TYPE
		SYNTAX	Unsigned32
		MAX-ACCESS read-only
		STATUS current
		DESCRIPTION
			"MTSM delivered via MSC in single/first attempt"
	::= { giwInstanceEntry	55 }

smscGiwMtsmOkSgsnFirst OBJECT-TYPE
		SYNTAX	Unsigned32
		MAX-ACCESS read-only
		STATUS current
		DESCRIPTION
			"MTSM delivered via SGSN in single/first attempt"
	::= { giwInstanceEntry	56 }

smscGiwMtsmOkMscSecond OBJECT-TYPE
		SYNTAX	Unsigned32
		MAX-ACCESS read-only
		STATUS current
		DESCRIPTION
			"MTSM delivered via MSC after delivery SGSN failed"
	::= { giwInstanceEntry	57 }

smscGiwMtsmOkSgsnSecond OBJECT-TYPE
		SYNTAX	Unsigned32
		MAX-ACCESS read-only
		STATUS current
		DESCRIPTION
			"MTSM delivered via SGSN after delivery MSC failed"
	::= { giwInstanceEntry	58 }

smscGiwMtsmFailMscFirst OBJECT-TYPE
		SYNTAX	Unsigned32
		MAX-ACCESS read-only
		STATUS current
		DESCRIPTION
			"MTSM via MSC failed in single/first attempt"
	::= { giwInstanceEntry	59 }

smscGiwMtsmFailSgsnFirst OBJECT-TYPE
		SYNTAX	Unsigned32
		MAX-ACCESS read-only
		STATUS current
		DESCRIPTION
			"MTSM via SGSN failed in single/first attempt"
	::= { giwInstanceEntry	60 }

smscGiwMtsmFailMscSecond OBJECT-TYPE
		SYNTAX	Unsigned32
		MAX-ACCESS read-only
		STATUS current
		DESCRIPTION
			"MTSM via MSC failed after delivery SGSN failed"
	::= { giwInstanceEntry	61 }

smscGiwMtsmFailSgsnSecond OBJECT-TYPE
		SYNTAX	Unsigned32
		MAX-ACCESS read-only
		STATUS current
		DESCRIPTION
			"MTSM via SGSN failed after delivery MSC failed"
	::= { giwInstanceEntry	62 }

smscGiwAbsentSubsMscFirst OBJECT-TYPE
		SYNTAX	Unsigned32
		MAX-ACCESS read-only
		STATUS current
		DESCRIPTION
			"Absent Sub from MSC in single/first attempt"
	::= { giwInstanceEntry	63 }

smscGiwAbsentSubsSgsnFirst OBJECT-TYPE
		SYNTAX	Unsigned32
		MAX-ACCESS read-only
		STATUS current
		DESCRIPTION
			"Absent Sub from SGSN in single/first attempt"
	::= { giwInstanceEntry	64 }

smscGiwAbsentSubsMscSecond OBJECT-TYPE
		SYNTAX	Unsigned32
		MAX-ACCESS read-only
		STATUS current
		DESCRIPTION
			"Absent Sub from MSC after delivery SGSN failed "
	::= { giwInstanceEntry	65 }

smscGiwAbsentSubsSgsnSecond OBJECT-TYPE
		SYNTAX	Unsigned32
		MAX-ACCESS read-only
		STATUS current
		DESCRIPTION
			"Absent Sub from SGSN after delivery MSC failed"
	::= { giwInstanceEntry	66 }

smscGiwAbsentSubsHlr OBJECT-TYPE
		SYNTAX	Unsigned32
		MAX-ACCESS read-only
		STATUS current
		DESCRIPTION
			"Absent Sub errors from HLR"
	::= { giwInstanceEntry	67 }

smscGiwMapDiaQueueFailed OBJECT-TYPE
		SYNTAX	Unsigned32
		MAX-ACCESS read-only
		STATUS current
		DESCRIPTION
			"Number of MAP dialogue queue failures"
	::= { giwInstanceEntry	68 }

smscGiwMapDiaFree OBJECT-TYPE
		SYNTAX	Unsigned32
		MAX-ACCESS read-only
		STATUS current
		DESCRIPTION
			"Number of free MAP dialogues"
	::= { giwInstanceEntry	69 }

smscGiwMapDiaInUse OBJECT-TYPE
		SYNTAX	Unsigned32
		MAX-ACCESS read-only
		STATUS current
		DESCRIPTION
			"Number of MAP dialogues in use"
	::= { giwInstanceEntry	70 }

smscGiwMapDiaMaxUsed OBJECT-TYPE
		SYNTAX	Unsigned32
		MAX-ACCESS read-only
		STATUS current
		DESCRIPTION
			"Maximum number of MAP dialogues used"
	::= { giwInstanceEntry	71 }

smscGiwMapDiaAllocFailed OBJECT-TYPE
		SYNTAX	Unsigned32
		MAX-ACCESS read-only
		STATUS current
		DESCRIPTION
			"Number of MAP dialogue allocation failures"
	::= { giwInstanceEntry	72 }

smscGiwMapOperFree OBJECT-TYPE
		SYNTAX	Unsigned32
		MAX-ACCESS read-only
		STATUS current
		DESCRIPTION
			"Number of free MAP operations"
	::= { giwInstanceEntry	73 }

smscGiwMapOperInUse OBJECT-TYPE
		SYNTAX	Unsigned32
		MAX-ACCESS read-only
		STATUS current
		DESCRIPTION
			"Number of MAP operations in use"
	::= { giwInstanceEntry	74 }

smscGiwMapOperMaxUsed OBJECT-TYPE
		SYNTAX	Unsigned32
		MAX-ACCESS read-only
		STATUS current
		DESCRIPTION
			"Maximum number of MAP operations used"
	::= { giwInstanceEntry	75 }

smscGiwMapOperAllocFailed OBJECT-TYPE
		SYNTAX	Unsigned32
		MAX-ACCESS read-only
		STATUS current
		DESCRIPTION
			"Number of MAP operation allocation failures"
	::= { giwInstanceEntry	76 }

smscGiwMapBufFree OBJECT-TYPE
		SYNTAX	Unsigned32
		MAX-ACCESS read-only
		STATUS current
		DESCRIPTION
			"Number of free MAP buffers"
	::= { giwInstanceEntry	77 }

smscGiwMapBufInUse OBJECT-TYPE
		SYNTAX	Unsigned32
		MAX-ACCESS read-only
		STATUS current
		DESCRIPTION
			"Number of MAP buffers in use"
	::= { giwInstanceEntry	78 }

smscGiwMapBufMaxUsed OBJECT-TYPE
		SYNTAX	Unsigned32
		MAX-ACCESS read-only
		STATUS current
		DESCRIPTION
			"Maximum number of MAP buffers used"
	::= { giwInstanceEntry	79 }

smscGiwMapBufAllocFailed OBJECT-TYPE
		SYNTAX	Unsigned32
		MAX-ACCESS read-only
		STATUS current
		DESCRIPTION
			"Number of MAP buffer allocation failures"
	::= { giwInstanceEntry	80 }

smscGiwMapProtoErr OBJECT-TYPE
		SYNTAX	Unsigned32
		MAX-ACCESS read-only
		STATUS current
		DESCRIPTION
			"Number of MAP protocol errors"
	::= { giwInstanceEntry	81 }

smscGiwMapPrvDecErr OBJECT-TYPE
		SYNTAX	Unsigned32
		MAX-ACCESS read-only
		STATUS current
		DESCRIPTION
			"Number of MAP provider decode errors"
	::= { giwInstanceEntry	82 }

smscGiwMapPduDecErr OBJECT-TYPE
		SYNTAX	Unsigned32
		MAX-ACCESS read-only
		STATUS current
		DESCRIPTION
			"Number of MAP PDU decode errors"
	::= { giwInstanceEntry	83 }

smscGiwMapOpcodeErr OBJECT-TYPE
		SYNTAX	Unsigned32
		MAX-ACCESS read-only
		STATUS current
		DESCRIPTION
			"Number of invalid MAP operation codes received"
	::= { giwInstanceEntry	84 }

smscGiwMapInvokeErr OBJECT-TYPE
		SYNTAX	Unsigned32
		MAX-ACCESS read-only
		STATUS current
		DESCRIPTION
			"Number of invalid MAP invoke IDs received"
	::= { giwInstanceEntry	85 }

smscGiwMapInvAppCtxt OBJECT-TYPE
		SYNTAX	Unsigned32
		MAX-ACCESS read-only
		STATUS current
		DESCRIPTION
			"Invalid MAP application contexts received"
	::= { giwInstanceEntry	86 }

smscGiwMapAppCtxtMism OBJECT-TYPE
		SYNTAX	Unsigned32
		MAX-ACCESS read-only
		STATUS current
		DESCRIPTION
			"Non-matching MAP application contexts received"
	::= { giwInstanceEntry	87 }

smscGiwTcapBeginRcvd OBJECT-TYPE
		SYNTAX	Unsigned32
		MAX-ACCESS read-only
		STATUS current
		DESCRIPTION
			"Number of Begin Dialogue transactions received"
	::= { giwInstanceEntry	88 }

smscGiwTcapContRcvd OBJECT-TYPE
		SYNTAX	Unsigned32
		MAX-ACCESS read-only
		STATUS current
		DESCRIPTION
			"Number of Continue transactions received"
	::= { giwInstanceEntry	89 }

smscGiwTcapEndRcvd OBJECT-TYPE
		SYNTAX	Unsigned32
		MAX-ACCESS read-only
		STATUS current
		DESCRIPTION
			"Number of End transactions received"
	::= { giwInstanceEntry	90 }

smscGiwTcapBeginSnt OBJECT-TYPE
		SYNTAX	Unsigned32
		MAX-ACCESS read-only
		STATUS current
		DESCRIPTION
			"Number of Begin Dialogue transactions sent"
	::= { giwInstanceEntry	91 }

smscGiwTcapContSnt OBJECT-TYPE
		SYNTAX	Unsigned32
		MAX-ACCESS read-only
		STATUS current
		DESCRIPTION
			"Number of Continue transactions sent"
	::= { giwInstanceEntry	92 }

smscGiwTcapEndSnt OBJECT-TYPE
		SYNTAX	Unsigned32
		MAX-ACCESS read-only
		STATUS current
		DESCRIPTION
			"Number of End transactions sent"
	::= { giwInstanceEntry	93 }

smscGiwTcapFailedSent OBJECT-TYPE
		SYNTAX	Unsigned32
		MAX-ACCESS read-only
		STATUS current
		DESCRIPTION
			"Number of Message failed to be sent"
	::= { giwInstanceEntry	94 }

smscGiwTcapTransDisc OBJECT-TYPE
		SYNTAX	Unsigned32
		MAX-ACCESS read-only
		STATUS current
		DESCRIPTION
			"Number of discarded msgs due to transport problem"
	::= { giwInstanceEntry	95 }

smscGiwTcapMsgDisc OBJECT-TYPE
		SYNTAX	Unsigned32
		MAX-ACCESS read-only
		STATUS current
		DESCRIPTION
			"Number of discarded TCAP messages"
	::= { giwInstanceEntry	96 }

smscGiwTcapUnknMsgRcvd OBJECT-TYPE
		SYNTAX	Unsigned32
		MAX-ACCESS read-only
		STATUS current
		DESCRIPTION
			"Number of incorrect or unknown TCAP msgs received"
	::= { giwInstanceEntry	97 }

smscGiwTcapNoticeRcvd OBJECT-TYPE
		SYNTAX	Unsigned32
		MAX-ACCESS read-only
		STATUS current
		DESCRIPTION
			"Number of Notice rcvd"
	::= { giwInstanceEntry	98 }

smscGiwTcapAbtRcvd OBJECT-TYPE
		SYNTAX	Unsigned32
		MAX-ACCESS read-only
		STATUS current
		DESCRIPTION
			"Number of P_ABORT transacs rcvd"
	::= { giwInstanceEntry	99 }

smscGiwTcapAbtUnrecmtRcvd OBJECT-TYPE
		SYNTAX	Unsigned32
		MAX-ACCESS read-only
		STATUS current
		DESCRIPTION
			"Number of P_ABORT transacs rcvd (unrec msg type)"
	::= { giwInstanceEntry	100 }

smscGiwTcapAbtTranpRcvd OBJECT-TYPE
		SYNTAX	Unsigned32
		MAX-ACCESS read-only
		STATUS current
		DESCRIPTION
			"Number of P_ABORT msgs rcvd (inc trans portion)"
	::= { giwInstanceEntry	101 }

smscGiwTcapAbtBftpRcvd OBJECT-TYPE
		SYNTAX	Unsigned32
		MAX-ACCESS read-only
		STATUS current
		DESCRIPTION
			"Number of P_ABORT msgs rcvd (badly formed tp)"
	::= { giwInstanceEntry	102 }

smscGiwTcapAbtUnrecidRcvd OBJECT-TYPE
		SYNTAX	Unsigned32
		MAX-ACCESS read-only
		STATUS current
		DESCRIPTION
			"Number of P_ABORT msgs rcvd (unrec trans id)"
	::= { giwInstanceEntry	103 }

smscGiwTcapAbtReslimitRcvd OBJECT-TYPE
		SYNTAX	Unsigned32
		MAX-ACCESS read-only
		STATUS current
		DESCRIPTION
			"Number of P_ABORT msgs rcvd (resouce limitation)"
	::= { giwInstanceEntry	104 }

smscGiwTcapAbtAbnormRcvd OBJECT-TYPE
		SYNTAX	Unsigned32
		MAX-ACCESS read-only
		STATUS current
		DESCRIPTION
			"Number of P_ABORT msgs rcvd (abnormal dialog)"
	::= { giwInstanceEntry	105 }

smscGiwTcapAbtSnt OBJECT-TYPE
		SYNTAX	Unsigned32
		MAX-ACCESS read-only
		STATUS current
		DESCRIPTION
			"Number of P_ABORT transacs sent"
	::= { giwInstanceEntry	106 }

smscGiwTcapAbtUnrecmtSnt OBJECT-TYPE
		SYNTAX	Unsigned32
		MAX-ACCESS read-only
		STATUS current
		DESCRIPTION
			"Number of P_ABORT transacs sent (unrec msg type)"
	::= { giwInstanceEntry	107 }

smscGiwTcapAbtTranpSnt OBJECT-TYPE
		SYNTAX	Unsigned32
		MAX-ACCESS read-only
		STATUS current
		DESCRIPTION
			"Number of P_ABORT transacs sent (inc trns portion)"
	::= { giwInstanceEntry	108 }

smscGiwTcapAbtBftpSnt OBJECT-TYPE
		SYNTAX	Unsigned32
		MAX-ACCESS read-only
		STATUS current
		DESCRIPTION
			"Number of P_ABORT transacs sent (badly formed tp)"
	::= { giwInstanceEntry	109 }

smscGiwTcapAbtUnrecidSnt OBJECT-TYPE
		SYNTAX	Unsigned32
		MAX-ACCESS read-only
		STATUS current
		DESCRIPTION
			"Number of P_ABORT transacs sent (unrec trns id)"
	::= { giwInstanceEntry	110 }

smscGiwTcapAbtReslimitSnt OBJECT-TYPE
		SYNTAX	Unsigned32
		MAX-ACCESS read-only
		STATUS current
		DESCRIPTION
			"Number of P_ABORT transacs sent (res limitation)"
	::= { giwInstanceEntry	111 }

smscGiwTcapAbtAbnormSnt OBJECT-TYPE
		SYNTAX	Unsigned32
		MAX-ACCESS read-only
		STATUS current
		DESCRIPTION
			"Number of P_ABORT transacs sent (abnormal dialog)"
	::= { giwInstanceEntry	112 }

smscGiwTcapUabtRcvd OBJECT-TYPE
		SYNTAX	Unsigned32
		MAX-ACCESS read-only
		STATUS current
		DESCRIPTION
			"Number of U_ABORT transactions received"
	::= { giwInstanceEntry	113 }

smscGiwTcapUabtSnt OBJECT-TYPE
		SYNTAX	Unsigned32
		MAX-ACCESS read-only
		STATUS current
		DESCRIPTION
			"Number of U_ABORT transactions sent"
	::= { giwInstanceEntry	114 }

smscGiwTcapInvkRcvd OBJECT-TYPE
		SYNTAX	Unsigned32
		MAX-ACCESS read-only
		STATUS current
		DESCRIPTION
			"Number of Invoke components received"
	::= { giwInstanceEntry	115 }

smscGiwTcapInvkSnt OBJECT-TYPE
		SYNTAX	Unsigned32
		MAX-ACCESS read-only
		STATUS current
		DESCRIPTION
			"Number of Invoke components sent"
	::= { giwInstanceEntry	116 }

smscGiwTcapResLastRcvd OBJECT-TYPE
		SYNTAX	Unsigned32
		MAX-ACCESS read-only
		STATUS current
		DESCRIPTION
			"Number of Result Last components received"
	::= { giwInstanceEntry	117 }

smscGiwTcapResNolastRcvd OBJECT-TYPE
		SYNTAX	Unsigned32
		MAX-ACCESS read-only
		STATUS current
		DESCRIPTION
			"Number of Result No Last components received"
	::= { giwInstanceEntry	118 }

smscGiwTcapResLastSnt OBJECT-TYPE
		SYNTAX	Unsigned32
		MAX-ACCESS read-only
		STATUS current
		DESCRIPTION
			"Number of Result Last components sent"
	::= { giwInstanceEntry	119 }

smscGiwTcapResNolastSnt OBJECT-TYPE
		SYNTAX	Unsigned32
		MAX-ACCESS read-only
		STATUS current
		DESCRIPTION
			"Number of Result No Last components sent"
	::= { giwInstanceEntry	120 }

smscGiwTcapErrorRcvd OBJECT-TYPE
		SYNTAX	Unsigned32
		MAX-ACCESS read-only
		STATUS current
		DESCRIPTION
			"Number of Error components received"
	::= { giwInstanceEntry	121 }

smscGiwTcapErrorSnt OBJECT-TYPE
		SYNTAX	Unsigned32
		MAX-ACCESS read-only
		STATUS current
		DESCRIPTION
			"Number of Error components sent"
	::= { giwInstanceEntry	122 }

smscGiwTcapRjctSnt OBJECT-TYPE
		SYNTAX	Unsigned32
		MAX-ACCESS read-only
		STATUS current
		DESCRIPTION
			"Number of Reject components sent"
	::= { giwInstanceEntry	123 }

smscGiwTcapRjctRcvd OBJECT-TYPE
		SYNTAX	Unsigned32
		MAX-ACCESS read-only
		STATUS current
		DESCRIPTION
			"Number of Reject components rcvd"
	::= { giwInstanceEntry	124 }

smscGiwTcapRjctUnrecRcvd OBJECT-TYPE
		SYNTAX	Unsigned32
		MAX-ACCESS read-only
		STATUS current
		DESCRIPTION
			"Number of Reject components rcvd (unrecognized)"
	::= { giwInstanceEntry	125 }

smscGiwTcapRjctMistypeRcvd OBJECT-TYPE
		SYNTAX	Unsigned32
		MAX-ACCESS read-only
		STATUS current
		DESCRIPTION
			"Number of Reject components rcvd (mistyped)"
	::= { giwInstanceEntry	126 }

smscGiwTcapRjctBadsRcvd OBJECT-TYPE
		SYNTAX	Unsigned32
		MAX-ACCESS read-only
		STATUS current
		DESCRIPTION
			"Number of Reject components rcvd (badly struct)"
	::= { giwInstanceEntry	127 }

smscGiwTcapRjctUnrLidRcvd OBJECT-TYPE
		SYNTAX	Unsigned32
		MAX-ACCESS read-only
		STATUS current
		DESCRIPTION
			"Number of Reject components rcvd (unrec link_id)"
	::= { giwInstanceEntry	128 }

smscGiwTcapRjctUiRrRcvd OBJECT-TYPE
		SYNTAX	Unsigned32
		MAX-ACCESS read-only
		STATUS current
		DESCRIPTION
			"Number of Reject components rcvd (unr ivk ret res)"
	::= { giwInstanceEntry	129 }

smscGiwTcapRjctUiReRcvd OBJECT-TYPE
		SYNTAX	Unsigned32
		MAX-ACCESS read-only
		STATUS current
		DESCRIPTION
			"Number of Reject components rcvd (unr ivk ret err)"
	::= { giwInstanceEntry	130 }

smscGiwTcapRjctUnxpRrRcvd OBJECT-TYPE
		SYNTAX	Unsigned32
		MAX-ACCESS read-only
		STATUS current
		DESCRIPTION
			"Number of Reject components rcvd (unexp ret res)"
	::= { giwInstanceEntry	131 }

smscGiwTcapRjctUnxpReRcvd OBJECT-TYPE
		SYNTAX	Unsigned32
		MAX-ACCESS read-only
		STATUS current
		DESCRIPTION
			"Number of Reject components rcvd (unexp ret err)"
	::= { giwInstanceEntry	132 }

smscGiwTcapRjctDupIidRcvd OBJECT-TYPE
		SYNTAX	Unsigned32
		MAX-ACCESS read-only
		STATUS current
		DESCRIPTION
			"Number of Reject components rcvd (dupl ivk_id)"
	::= { giwInstanceEntry	133 }

smscGiwTcapPrbUnrecOpRcvd OBJECT-TYPE
		SYNTAX	Unsigned32
		MAX-ACCESS read-only
		STATUS current
		DESCRIPTION
			"Number of TC user problems rcvd (unrec operations)"
	::= { giwInstanceEntry	134 }

smscGiwTcapPrbMistypeRcvd OBJECT-TYPE
		SYNTAX	Unsigned32
		MAX-ACCESS read-only
		STATUS current
		DESCRIPTION
			"Number of TC user problems rcvd (mistyped param)"
	::= { giwInstanceEntry	135 }

smscGiwTcapPrbReslimitRcvd OBJECT-TYPE
		SYNTAX	Unsigned32
		MAX-ACCESS read-only
		STATUS current
		DESCRIPTION
			"Number of TC user problems rcvd (res limitation)"
	::= { giwInstanceEntry	136 }

smscGiwTcapPrbInitrelRcvd OBJECT-TYPE
		SYNTAX	Unsigned32
		MAX-ACCESS read-only
		STATUS current
		DESCRIPTION
			"Number of TC user problems rcvd (init release)"
	::= { giwInstanceEntry	137 }

smscGiwTcapPrbUnlRespRcvd OBJECT-TYPE
		SYNTAX	Unsigned32
		MAX-ACCESS read-only
		STATUS current
		DESCRIPTION
			"Number of TC user problems rcvd (unexp link resp)"
	::= { giwInstanceEntry	138 }

smscGiwTcapPrbUnlOpRcvd OBJECT-TYPE
		SYNTAX	Unsigned32
		MAX-ACCESS read-only
		STATUS current
		DESCRIPTION
			"Number of TC user problems rcvd (unexp link oper)"
	::= { giwInstanceEntry	139 }

smscGiwTcapPrbMtRrRcvd OBJECT-TYPE
		SYNTAX	Unsigned32
		MAX-ACCESS read-only
		STATUS current
		DESCRIPTION
			"Number of TC user problems rcvd (mistyped ret res)"
	::= { giwInstanceEntry	140 }

smscGiwTcapPrbMtReRcvd OBJECT-TYPE
		SYNTAX	Unsigned32
		MAX-ACCESS read-only
		STATUS current
		DESCRIPTION
			"Number of TC user problems rcvd (mistyped ret err)"
	::= { giwInstanceEntry	141 }

smscGiwTcapUserUnrecRcvd OBJECT-TYPE
		SYNTAX	Unsigned32
		MAX-ACCESS read-only
		STATUS current
		DESCRIPTION
			"Number of TC user unrecognized errors received"
	::= { giwInstanceEntry	142 }

smscGiwTcapUserUnxpRcvd OBJECT-TYPE
		SYNTAX	Unsigned32
		MAX-ACCESS read-only
		STATUS current
		DESCRIPTION
			"Number of TC user unexpected errors received"
	::= { giwInstanceEntry	143 }

smscGiwTcapActiveDialog OBJECT-TYPE
		SYNTAX	Unsigned32
		MAX-ACCESS read-only
		STATUS current
		DESCRIPTION
			"Number of simultaneous active TCAP dialogues"
	::= { giwInstanceEntry	144 }

smscGiwTcapInitiatedDialog OBJECT-TYPE
		SYNTAX	Unsigned32
		MAX-ACCESS read-only
		STATUS current
		DESCRIPTION
			"Number of simultaneous initiated TCAP dialogues"
	::= { giwInstanceEntry	145 }

smscGiwTcapActiveDlgs OBJECT-TYPE
		SYNTAX	Unsigned32
		MAX-ACCESS read-only
		STATUS current
		DESCRIPTION
			"Number of simultaneous active TCAP dialogues"
	::= { giwInstanceEntry	146 }

smscGiwTcapInitiatedDlgs OBJECT-TYPE
		SYNTAX	Unsigned32
		MAX-ACCESS read-only
		STATUS current
		DESCRIPTION
			"Number of simultaneous initiated TCAP dialogues"
	::= { giwInstanceEntry	147 }

smscGiwFsgLoopPreventedSm OBJECT-TYPE
		SYNTAX	Unsigned32
		MAX-ACCESS read-only
		STATUS current
		DESCRIPTION
			"Number of FSG loop prevented short messages"
	::= { giwInstanceEntry	148 }

smscGiwFsgMtsmOk OBJECT-TYPE
		SYNTAX	Unsigned32
		MAX-ACCESS read-only
		STATUS current
		DESCRIPTION
			"Number of FSG accepted Mobile Terminated SM"
	::= { giwInstanceEntry	149 }

smscGiwFsgMtsmFail OBJECT-TYPE
		SYNTAX	Unsigned32
		MAX-ACCESS read-only
		STATUS current
		DESCRIPTION
			"Number of FSG rejected Mobile Terminated SM"
	::= { giwInstanceEntry	150 }

smscGiwMapScCongestion OBJECT-TYPE
		SYNTAX	Unsigned32
		MAX-ACCESS read-only
		STATUS current
		DESCRIPTION
			"Number of MAP SC Congestion Errors"
	::= { giwInstanceEntry	151 }

smscGiwMapInvalidSmeAddress OBJECT-TYPE
		SYNTAX	Unsigned32
		MAX-ACCESS read-only
		STATUS current
		DESCRIPTION
			"Number of MAP Invalid SME Address Errors"
	::= { giwInstanceEntry	152 }

smscGiwMapSubscrNotScSubscriber OBJECT-TYPE
		SYNTAX	Unsigned32
		MAX-ACCESS read-only
		STATUS current
		DESCRIPTION
			"Number of MAP Subscr Not SC Subscriber Errors"
	::= { giwInstanceEntry	153 }

smscGiwMapUnknownSc OBJECT-TYPE
		SYNTAX	Unsigned32
		MAX-ACCESS read-only
		STATUS current
		DESCRIPTION
			"Number of MAP Unknown SC Errors"
	::= { giwInstanceEntry	154 }

smscGiwMtMemcapExceeded OBJECT-TYPE
		SYNTAX	Unsigned32
		MAX-ACCESS read-only
		STATUS current
		DESCRIPTION
			"Number of MAP 'MS memory capacity exceeded' Errors"
	::= { giwInstanceEntry	155 }

smscGiwMtMsProtocolErr OBJECT-TYPE
		SYNTAX	Unsigned32
		MAX-ACCESS read-only
		STATUS current
		DESCRIPTION
			"Number of MAP 'Receiving MS protocol error' Errors"
	::= { giwInstanceEntry	156 }

smscGiwMtMsNotEquipped OBJECT-TYPE
		SYNTAX	Unsigned32
		MAX-ACCESS read-only
		STATUS current
		DESCRIPTION
			"Number of MAP 'Receiving MS not equipped' Errors"
	::= { giwInstanceEntry	157 }

smscGiwMoAntiFraudRejHlr OBJECT-TYPE
		SYNTAX	Unsigned32
		MAX-ACCESS read-only
		STATUS current
		DESCRIPTION
			"Number of Anti-Fraud rejected MO (HLR failure)"
	::= { giwInstanceEntry	158 }

smscGiwMoAntiFraudRejGt OBJECT-TYPE
		SYNTAX	Unsigned32
		MAX-ACCESS read-only
		STATUS current
		DESCRIPTION
			"Number of Anti-Fraud rejected MO (GT mismatch)"
	::= { giwInstanceEntry	159 }

smscGiwMoAntiFraudRejImsi OBJECT-TYPE
		SYNTAX	Unsigned32
		MAX-ACCESS read-only
		STATUS current
		DESCRIPTION
			"Number of Anti-Fraud rejected MO (IMSI mismatch)"
	::= { giwInstanceEntry	160 }



-- end of GIW description.
-- --------------------------------------


-- --------------------------------------
-- Class FAX3SRV
-- 
smscFax3srv OBJECT-TYPE
	SYNTAX  SEQUENCE OF Fax3srvInstanceEntry
	MAX-ACCESS  not-accessible
	STATUS  current
	DESCRIPTION
		"Mapping table for SMSC FAX3SRV entities."
   ::= { smscClassServer   7  }

fax3srvInstanceEntry  OBJECT-TYPE
	SYNTAX Fax3srvInstanceEntry
	MAX-ACCESS  not-accessible
	STATUS  current
	DESCRIPTION
		"An entry (row) in the entityInstanceTable."
	INDEX { IMPLIED smscFax3srvName }
   ::= { smscFax3srv 1 }

Fax3srvInstanceEntry ::= SEQUENCE {
		smscFax3srvName     DisplayString,
		smscFax3srvState   INTEGER,
		smscFax3srvLastupdate   TimeTicks,
		smscFax3srvNode	   DisplayString, 
		smscFax3srvMsgReceived	 Unsigned32, 
		smscFax3srvMsgRejected	 Unsigned32, 
		smscFax3srvMsgTransmitted	 Unsigned32, 
		smscFax3srvMsgFailed	 Unsigned32, 
		smscFax3srvQelemUsed	 Unsigned32, 
		smscFax3srvQelemInProcqueue	 Unsigned32, 
		smscFax3srvQelemInExpqueue	 Unsigned32, 
		smscFax3srvNrTimersRunning	 Unsigned32, 
		smscFax3srvNrSystemTimers	 Unsigned32, 
		smscFax3srvImiRecallQelem	 Unsigned32, 
		smscFax3srvImiRecallQueues	 Unsigned32, 
		smscFax3srvIdiRecallQelem	 Unsigned32, 
		smscFax3srvIdiRecallQueues	 Unsigned32, 
		smscFax3srvIosRecallQelem	 Unsigned32, 
		smscFax3srvIosRecallQueues	 Unsigned32, 
		smscFax3srvLogRecallQelem	 Unsigned32, 
		smscFax3srvLogRecallQueues	 Unsigned32, 
		smscFax3srvTrcreqDiscarded	 Unsigned32, 
		smscFax3srvDummyStatistic	 Unsigned32, 
		smscFax3srvFaxSent	 Unsigned32, 
		smscFax3srvFaxFailed	 Unsigned32, 
		smscFax3srvPosNotifDfax	 Unsigned32, 
		smscFax3srvNegNotifDfax	 Unsigned32, 
		smscFax3srvPosNotifFrep	 Unsigned32, 
		smscFax3srvNegNotifFrep	 Unsigned32
	}

smscFax3srvName  OBJECT-TYPE
	SYNTAX  DisplayString
	MAX-ACCESS  read-only
	STATUS   current
	DESCRIPTION
		"Identifies the name of the entity."
   ::= {fax3srvInstanceEntry 1 }

smscFax3srvState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { fax3srvInstanceEntry 2 }


smscFax3srvLastupdate OBJECT-TYPE
		SYNTAX	TimeTicks
		MAX-ACCESS read-only
		STATUS current
		DESCRIPTION
			"Value which reflects the last time the entities fields have been updated"
	::= { fax3srvInstanceEntry	3 }

smscFax3srvNode  OBJECT-TYPE
	SYNTAX  DisplayString
	MAX-ACCESS  read-only
	STATUS   current
	DESCRIPTION
		"Identifies the node the entity is running on."
   ::= {fax3srvInstanceEntry 4 }

smscFax3srvMsgReceived OBJECT-TYPE
		SYNTAX	Unsigned32
		MAX-ACCESS read-only
		STATUS current
		DESCRIPTION
			"Received messages"
	::= { fax3srvInstanceEntry	5 }

smscFax3srvMsgRejected OBJECT-TYPE
		SYNTAX	Unsigned32
		MAX-ACCESS read-only
		STATUS current
		DESCRIPTION
			"Received messages and rejected"
	::= { fax3srvInstanceEntry	6 }

smscFax3srvMsgTransmitted OBJECT-TYPE
		SYNTAX	Unsigned32
		MAX-ACCESS read-only
		STATUS current
		DESCRIPTION
			"Transmitted messages"
	::= { fax3srvInstanceEntry	7 }

smscFax3srvMsgFailed OBJECT-TYPE
		SYNTAX	Unsigned32
		MAX-ACCESS read-only
		STATUS current
		DESCRIPTION
			"Messages that failed on sending"
	::= { fax3srvInstanceEntry	8 }

smscFax3srvQelemUsed OBJECT-TYPE
		SYNTAX	Unsigned32
		MAX-ACCESS read-only
		STATUS current
		DESCRIPTION
			"Number of elements in internal queues"
	::= { fax3srvInstanceEntry	9 }

smscFax3srvQelemInProcqueue OBJECT-TYPE
		SYNTAX	Unsigned32
		MAX-ACCESS read-only
		STATUS current
		DESCRIPTION
			"Number of elements used in process queue"
	::= { fax3srvInstanceEntry	10 }

smscFax3srvQelemInExpqueue OBJECT-TYPE
		SYNTAX	Unsigned32
		MAX-ACCESS read-only
		STATUS current
		DESCRIPTION
			"Number of elements used in expedited queue"
	::= { fax3srvInstanceEntry	11 }

smscFax3srvNrTimersRunning OBJECT-TYPE
		SYNTAX	Unsigned32
		MAX-ACCESS read-only
		STATUS current
		DESCRIPTION
			"Total number of timers running"
	::= { fax3srvInstanceEntry	12 }

smscFax3srvNrSystemTimers OBJECT-TYPE
		SYNTAX	Unsigned32
		MAX-ACCESS read-only
		STATUS current
		DESCRIPTION
			"Number of system timers running"
	::= { fax3srvInstanceEntry	13 }

smscFax3srvImiRecallQelem OBJECT-TYPE
		SYNTAX	Unsigned32
		MAX-ACCESS read-only
		STATUS current
		DESCRIPTION
			"Number of IMI recall-queue elements used"
	::= { fax3srvInstanceEntry	14 }

smscFax3srvImiRecallQueues OBJECT-TYPE
		SYNTAX	Unsigned32
		MAX-ACCESS read-only
		STATUS current
		DESCRIPTION
			"Number of IMI-recall-queues used"
	::= { fax3srvInstanceEntry	15 }

smscFax3srvIdiRecallQelem OBJECT-TYPE
		SYNTAX	Unsigned32
		MAX-ACCESS read-only
		STATUS current
		DESCRIPTION
			"Number of IDI recall-queue elements used"
	::= { fax3srvInstanceEntry	16 }

smscFax3srvIdiRecallQueues OBJECT-TYPE
		SYNTAX	Unsigned32
		MAX-ACCESS read-only
		STATUS current
		DESCRIPTION
			"Number of IDI recall-queues used"
	::= { fax3srvInstanceEntry	17 }

smscFax3srvIosRecallQelem OBJECT-TYPE
		SYNTAX	Unsigned32
		MAX-ACCESS read-only
		STATUS current
		DESCRIPTION
			"Number of IOS recall-queue elements used"
	::= { fax3srvInstanceEntry	18 }

smscFax3srvIosRecallQueues OBJECT-TYPE
		SYNTAX	Unsigned32
		MAX-ACCESS read-only
		STATUS current
		DESCRIPTION
			"Number of IOS recall-queues used"
	::= { fax3srvInstanceEntry	19 }

smscFax3srvLogRecallQelem OBJECT-TYPE
		SYNTAX	Unsigned32
		MAX-ACCESS read-only
		STATUS current
		DESCRIPTION
			"Number of LOG recall-queue elements used"
	::= { fax3srvInstanceEntry	20 }

smscFax3srvLogRecallQueues OBJECT-TYPE
		SYNTAX	Unsigned32
		MAX-ACCESS read-only
		STATUS current
		DESCRIPTION
			"Number of LOG recall-queues used"
	::= { fax3srvInstanceEntry	21 }

smscFax3srvTrcreqDiscarded OBJECT-TYPE
		SYNTAX	Unsigned32
		MAX-ACCESS read-only
		STATUS current
		DESCRIPTION
			"Number of trace requests discarded"
	::= { fax3srvInstanceEntry	22 }

smscFax3srvDummyStatistic OBJECT-TYPE
		SYNTAX	Unsigned32
		MAX-ACCESS read-only
		STATUS current
		DESCRIPTION
			"No statistical counters"
	::= { fax3srvInstanceEntry	23 }

smscFax3srvFaxSent OBJECT-TYPE
		SYNTAX	Unsigned32
		MAX-ACCESS read-only
		STATUS current
		DESCRIPTION
			"Number of faxes accepted by fax device"
	::= { fax3srvInstanceEntry	24 }

smscFax3srvFaxFailed OBJECT-TYPE
		SYNTAX	Unsigned32
		MAX-ACCESS read-only
		STATUS current
		DESCRIPTION
			"Number of faxes rejected by fax device"
	::= { fax3srvInstanceEntry	25 }

smscFax3srvPosNotifDfax OBJECT-TYPE
		SYNTAX	Unsigned32
		MAX-ACCESS read-only
		STATUS current
		DESCRIPTION
			"Number of positive notifications sent to DIWFAX"
	::= { fax3srvInstanceEntry	26 }

smscFax3srvNegNotifDfax OBJECT-TYPE
		SYNTAX	Unsigned32
		MAX-ACCESS read-only
		STATUS current
		DESCRIPTION
			"Number of negative notifications sent to DIWFAX"
	::= { fax3srvInstanceEntry	27 }

smscFax3srvPosNotifFrep OBJECT-TYPE
		SYNTAX	Unsigned32
		MAX-ACCESS read-only
		STATUS current
		DESCRIPTION
			"Number of positive notifications sent to FRH"
	::= { fax3srvInstanceEntry	28 }

smscFax3srvNegNotifFrep OBJECT-TYPE
		SYNTAX	Unsigned32
		MAX-ACCESS read-only
		STATUS current
		DESCRIPTION
			"Number of negative notifications sent to FRH"
	::= { fax3srvInstanceEntry	29 }



-- end of FAX3SRV description.
-- --------------------------------------


-- --------------------------------------
-- Class ISDN
-- 
smscIsdn OBJECT-TYPE
	SYNTAX  SEQUENCE OF IsdnInstanceEntry
	MAX-ACCESS  not-accessible
	STATUS  current
	DESCRIPTION
		"Mapping table for SMSC ISDN entities."
   ::= { smscClassServer   8  }

isdnInstanceEntry  OBJECT-TYPE
	SYNTAX IsdnInstanceEntry
	MAX-ACCESS  not-accessible
	STATUS  current
	DESCRIPTION
		"An entry (row) in the entityInstanceTable."
	INDEX { IMPLIED smscIsdnName }
   ::= { smscIsdn 1 }

IsdnInstanceEntry ::= SEQUENCE {
		smscIsdnName     DisplayString,
		smscIsdnState   INTEGER,
		smscIsdnLastupdate   TimeTicks,
		smscIsdnNode	   DisplayString, 
		smscIsdnMsgReceived	 Unsigned32, 
		smscIsdnMsgRejected	 Unsigned32, 
		smscIsdnMsgTransmitted	 Unsigned32, 
		smscIsdnMsgFailed	 Unsigned32, 
		smscIsdnConTot	 Unsigned32, 
		smscIsdnConIn	 Unsigned32, 
		smscIsdnConInAcc	 Unsigned32, 
		smscIsdnConOut	 Unsigned32, 
		smscIsdnConOutAcc	 Unsigned32, 
		smscIsdnConOutBusy	 Unsigned32, 
		smscIsdnConOutNoAnswer	 Unsigned32, 
		smscIsdnConOutOtherFail	 Unsigned32, 
		smscIsdnConTimeCumulative	 Unsigned32, 
		smscIsdnQelemUsed	 Unsigned32, 
		smscIsdnQelemInProcqueue	 Unsigned32, 
		smscIsdnQelemInExpqueue	 Unsigned32, 
		smscIsdnNrTimersRunning	 Unsigned32, 
		smscIsdnNrSystemTimers	 Unsigned32, 
		smscIsdnImiRecallQelem	 Unsigned32, 
		smscIsdnImiRecallQueues	 Unsigned32, 
		smscIsdnIdiRecallQelem	 Unsigned32, 
		smscIsdnIdiRecallQueues	 Unsigned32, 
		smscIsdnIosRecallQelem	 Unsigned32, 
		smscIsdnIosRecallQueues	 Unsigned32, 
		smscIsdnLogRecallQelem	 Unsigned32, 
		smscIsdnLogRecallQueues	 Unsigned32, 
		smscIsdnTrcreqDiscarded	 Unsigned32
	}

smscIsdnName  OBJECT-TYPE
	SYNTAX  DisplayString
	MAX-ACCESS  read-only
	STATUS   current
	DESCRIPTION
		"Identifies the name of the entity."
   ::= {isdnInstanceEntry 1 }

smscIsdnState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { isdnInstanceEntry 2 }


smscIsdnLastupdate OBJECT-TYPE
		SYNTAX	TimeTicks
		MAX-ACCESS read-only
		STATUS current
		DESCRIPTION
			"Value which reflects the last time the entities fields have been updated"
	::= { isdnInstanceEntry	3 }

smscIsdnNode  OBJECT-TYPE
	SYNTAX  DisplayString
	MAX-ACCESS  read-only
	STATUS   current
	DESCRIPTION
		"Identifies the node the entity is running on."
   ::= {isdnInstanceEntry 4 }

smscIsdnMsgReceived OBJECT-TYPE
		SYNTAX	Unsigned32
		MAX-ACCESS read-only
		STATUS current
		DESCRIPTION
			"Received messages"
	::= { isdnInstanceEntry	5 }

smscIsdnMsgRejected OBJECT-TYPE
		SYNTAX	Unsigned32
		MAX-ACCESS read-only
		STATUS current
		DESCRIPTION
			"Received messages and rejected"
	::= { isdnInstanceEntry	6 }

smscIsdnMsgTransmitted OBJECT-TYPE
		SYNTAX	Unsigned32
		MAX-ACCESS read-only
		STATUS current
		DESCRIPTION
			"Transmitted messages"
	::= { isdnInstanceEntry	7 }

smscIsdnMsgFailed OBJECT-TYPE
		SYNTAX	Unsigned32
		MAX-ACCESS read-only
		STATUS current
		DESCRIPTION
			"Messages that failed on sending"
	::= { isdnInstanceEntry	8 }

smscIsdnConTot OBJECT-TYPE
		SYNTAX	Unsigned32
		MAX-ACCESS read-only
		STATUS current
		DESCRIPTION
			"Network connections"
	::= { isdnInstanceEntry	9 }

smscIsdnConIn OBJECT-TYPE
		SYNTAX	Unsigned32
		MAX-ACCESS read-only
		STATUS current
		DESCRIPTION
			"Received network connections"
	::= { isdnInstanceEntry	10 }

smscIsdnConInAcc OBJECT-TYPE
		SYNTAX	Unsigned32
		MAX-ACCESS read-only
		STATUS current
		DESCRIPTION
			"Accepted received network connections"
	::= { isdnInstanceEntry	11 }

smscIsdnConOut OBJECT-TYPE
		SYNTAX	Unsigned32
		MAX-ACCESS read-only
		STATUS current
		DESCRIPTION
			"Initiated network connections"
	::= { isdnInstanceEntry	12 }

smscIsdnConOutAcc OBJECT-TYPE
		SYNTAX	Unsigned32
		MAX-ACCESS read-only
		STATUS current
		DESCRIPTION
			"Accepted initiated network connections"
	::= { isdnInstanceEntry	13 }

smscIsdnConOutBusy OBJECT-TYPE
		SYNTAX	Unsigned32
		MAX-ACCESS read-only
		STATUS current
		DESCRIPTION
			"Initiated network connections resulting in busy tone"
	::= { isdnInstanceEntry	14 }

smscIsdnConOutNoAnswer OBJECT-TYPE
		SYNTAX	Unsigned32
		MAX-ACCESS read-only
		STATUS current
		DESCRIPTION
			"Initiated network connections resulting in no answer tone"
	::= { isdnInstanceEntry	15 }

smscIsdnConOutOtherFail OBJECT-TYPE
		SYNTAX	Unsigned32
		MAX-ACCESS read-only
		STATUS current
		DESCRIPTION
			"Initiated network connections resulting in other failures"
	::= { isdnInstanceEntry	16 }

smscIsdnConTimeCumulative OBJECT-TYPE
		SYNTAX	Unsigned32
		MAX-ACCESS read-only
		STATUS current
		DESCRIPTION
			"Accumulated session duration time"
	::= { isdnInstanceEntry	17 }

smscIsdnQelemUsed OBJECT-TYPE
		SYNTAX	Unsigned32
		MAX-ACCESS read-only
		STATUS current
		DESCRIPTION
			"Number of elements in internal queues"
	::= { isdnInstanceEntry	18 }

smscIsdnQelemInProcqueue OBJECT-TYPE
		SYNTAX	Unsigned32
		MAX-ACCESS read-only
		STATUS current
		DESCRIPTION
			"Number of elements used in process queue"
	::= { isdnInstanceEntry	19 }

smscIsdnQelemInExpqueue OBJECT-TYPE
		SYNTAX	Unsigned32
		MAX-ACCESS read-only
		STATUS current
		DESCRIPTION
			"Number of elements used in expedited queue"
	::= { isdnInstanceEntry	20 }

smscIsdnNrTimersRunning OBJECT-TYPE
		SYNTAX	Unsigned32
		MAX-ACCESS read-only
		STATUS current
		DESCRIPTION
			"Total number of timers running"
	::= { isdnInstanceEntry	21 }

smscIsdnNrSystemTimers OBJECT-TYPE
		SYNTAX	Unsigned32
		MAX-ACCESS read-only
		STATUS current
		DESCRIPTION
			"Number of system timers running"
	::= { isdnInstanceEntry	22 }

smscIsdnImiRecallQelem OBJECT-TYPE
		SYNTAX	Unsigned32
		MAX-ACCESS read-only
		STATUS current
		DESCRIPTION
			"Number of IMI recall-queue elements used"
	::= { isdnInstanceEntry	23 }

smscIsdnImiRecallQueues OBJECT-TYPE
		SYNTAX	Unsigned32
		MAX-ACCESS read-only
		STATUS current
		DESCRIPTION
			"Number of IMI-recall-queues used"
	::= { isdnInstanceEntry	24 }

smscIsdnIdiRecallQelem OBJECT-TYPE
		SYNTAX	Unsigned32
		MAX-ACCESS read-only
		STATUS current
		DESCRIPTION
			"Number of IDI recall-queue elements used"
	::= { isdnInstanceEntry	25 }

smscIsdnIdiRecallQueues OBJECT-TYPE
		SYNTAX	Unsigned32
		MAX-ACCESS read-only
		STATUS current
		DESCRIPTION
			"Number of IDI recall-queues used"
	::= { isdnInstanceEntry	26 }

smscIsdnIosRecallQelem OBJECT-TYPE
		SYNTAX	Unsigned32
		MAX-ACCESS read-only
		STATUS current
		DESCRIPTION
			"Number of IOS recall-queue elements used"
	::= { isdnInstanceEntry	27 }

smscIsdnIosRecallQueues OBJECT-TYPE
		SYNTAX	Unsigned32
		MAX-ACCESS read-only
		STATUS current
		DESCRIPTION
			"Number of IOS recall-queues used"
	::= { isdnInstanceEntry	28 }

smscIsdnLogRecallQelem OBJECT-TYPE
		SYNTAX	Unsigned32
		MAX-ACCESS read-only
		STATUS current
		DESCRIPTION
			"Number of LOG recall-queue elements used"
	::= { isdnInstanceEntry	29 }

smscIsdnLogRecallQueues OBJECT-TYPE
		SYNTAX	Unsigned32
		MAX-ACCESS read-only
		STATUS current
		DESCRIPTION
			"Number of LOG recall-queues used"
	::= { isdnInstanceEntry	30 }

smscIsdnTrcreqDiscarded OBJECT-TYPE
		SYNTAX	Unsigned32
		MAX-ACCESS read-only
		STATUS current
		DESCRIPTION
			"Number of trace requests discarded"
	::= { isdnInstanceEntry	31 }



-- end of ISDN description.
-- --------------------------------------


-- --------------------------------------
-- Class IS41
-- 
smscIs41 OBJECT-TYPE
	SYNTAX  SEQUENCE OF Is41InstanceEntry
	MAX-ACCESS  not-accessible
	STATUS  current
	DESCRIPTION
		"Mapping table for SMSC IS41 entities."
   ::= { smscClassServer   9  }

is41InstanceEntry  OBJECT-TYPE
	SYNTAX Is41InstanceEntry
	MAX-ACCESS  not-accessible
	STATUS  current
	DESCRIPTION
		"An entry (row) in the entityInstanceTable."
	INDEX { IMPLIED smscIs41Name }
   ::= { smscIs41 1 }

Is41InstanceEntry ::= SEQUENCE {
		smscIs41Name     DisplayString,
		smscIs41State   INTEGER,
		smscIs41Lastupdate   TimeTicks,
		smscIs41Node	   DisplayString, 
		smscIs41MsgReceived	 Unsigned32, 
		smscIs41MsgRejected	 Unsigned32, 
		smscIs41MsgTransmitted	 Unsigned32, 
		smscIs41MsgFailed	 Unsigned32, 
		smscIs41SessionsPending	 Unsigned32, 
		smscIs41DialoguesPending	 Unsigned32, 
		smscIs41QelemUsed	 Unsigned32, 
		smscIs41QelemInProcqueue	 Unsigned32, 
		smscIs41QelemInExpqueue	 Unsigned32, 
		smscIs41NrTimersRunning	 Unsigned32, 
		smscIs41NrSystemTimers	 Unsigned32, 
		smscIs41ImiRecallQelem	 Unsigned32, 
		smscIs41ImiRecallQueues	 Unsigned32, 
		smscIs41IdiRecallQelem	 Unsigned32, 
		smscIs41IdiRecallQueues	 Unsigned32, 
		smscIs41IosRecallQelem	 Unsigned32, 
		smscIs41IosRecallQueues	 Unsigned32, 
		smscIs41LogRecallQelem	 Unsigned32, 
		smscIs41LogRecallQueues	 Unsigned32, 
		smscIs41TrcreqDiscarded	 Unsigned32, 
		smscIs41MtSmsOk	 Unsigned32, 
		smscIs41MtSmsFail	 Unsigned32, 
		smscIs41MoSmsAccepted	 Unsigned32, 
		smscIs41MoSmsRejected	 Unsigned32, 
		smscIs41SmsRequestOk	 Unsigned32, 
		smscIs41SmsRequestFail	 Unsigned32, 
		smscIs41SmsNotifAccepted	 Unsigned32, 
		smscIs41SmsNotifRejected	 Unsigned32, 
		smscIs41SccpAddrErrors	 Unsigned32, 
		smscIs41TcapErrors	 Unsigned32, 
		smscIs41TimeOuts	 Unsigned32, 
		smscIs41SmsAddrProblem	 Unsigned32, 
		smscIs41SmsInvalidServiceId	 Unsigned32, 
		smscIs41SmsNetworkProblem	 Unsigned32, 
		smscIs41SmsTerminalProblem	 Unsigned32, 
		smscIs41SmsRadioProblem	 Unsigned32, 
		smscIs41SmsEncodingProblem	 Unsigned32, 
		smscIs41SmsMissingParameter	 Unsigned32, 
		smscIs41SmsParamValueErr	 Unsigned32, 
		smscIs41SmsGeneralProblem	 Unsigned32, 
		smscIs41AbsentSubscriber	 Unsigned32, 
		smscIs41SmsDestBusy	 Unsigned32, 
		smscIs41SmsDestResourceShort	 Unsigned32, 
		smscIs41SmsSvcDenied	 Unsigned32, 
		smscIs41MsInvalid	 Unsigned32, 
		smscIs41MsUnreachable	 Unsigned32, 
		smscIs41MsUnavailable	 Unsigned32, 
		smscIs41NoPageResponse	 Unsigned32, 
		smscIs41DeliveryPostponed	 Unsigned32, 
		smscIs41DestLeftAddr	 Unsigned32, 
		smscIs41Dialogues	 Unsigned32, 
		smscIs41OtaspReqOk	 Unsigned32, 
		smscIs41OtaspReqFail	 Unsigned32, 
		smscIs41TcapBeginRcvd	 Unsigned32, 
		smscIs41TcapContRcvd	 Unsigned32, 
		smscIs41TcapEndRcvd	 Unsigned32, 
		smscIs41TcapBeginSnt	 Unsigned32, 
		smscIs41TcapEndSnt	 Unsigned32, 
		smscIs41TcapFailedSent	 Unsigned32, 
		smscIs41TcapTransDisc	 Unsigned32, 
		smscIs41TcapMsgDisc	 Unsigned32, 
		smscIs41TcapAbtRcvd	 Unsigned32, 
		smscIs41TcapAbtUnrecmtRcvd	 Unsigned32, 
		smscIs41TcapAbtTranpRcvd	 Unsigned32, 
		smscIs41TcapAbtBftpRcvd	 Unsigned32, 
		smscIs41TcapAbtUnrecidRcvd	 Unsigned32, 
		smscIs41TcapAbtReslimitRcvd	 Unsigned32, 
		smscIs41TcapAbtAbnormRcvd	 Unsigned32, 
		smscIs41TcapUabtRcvd	 Unsigned32, 
		smscIs41TcapInvkRcvd	 Unsigned32, 
		smscIs41TcapInvknlRcvd	 Unsigned32, 
		smscIs41TcapInvkSnt	 Unsigned32, 
		smscIs41TcapResLastRcvd	 Unsigned32, 
		smscIs41TcapResNolastRcvd	 Unsigned32, 
		smscIs41TcapResLastSnt	 Unsigned32, 
		smscIs41TcapErrorRcvd	 Unsigned32, 
		smscIs41TcapErrorSnt	 Unsigned32, 
		smscIs41TcapRejectSnt	 Unsigned32, 
		smscIs41TcapRejectRcvd	 Unsigned32, 
		smscIs41TcapRjctUnrecRcvd	 Unsigned32, 
		smscIs41TcapRjctIcpRcvd	 Unsigned32, 
		smscIs41TcapRjctBadsRcvd	 Unsigned32, 
		smscIs41TcapRjctIccRcvd	 Unsigned32, 
		smscIs41TcapRjctDupIidRcvd	 Unsigned32, 
		smscIs41TcapPrbUnrecOpRcvd	 Unsigned32, 
		smscIs41TcapPrbMistypeRcvd	 Unsigned32, 
		smscIs41TcapRjctUnrLidRcvd	 Unsigned32, 
		smscIs41TcapRjctRruciRcvd	 Unsigned32, 
		smscIs41TcapRjctUnxpRrRcvd	 Unsigned32, 
		smscIs41TcapPrbMtRrRcvd	 Unsigned32, 
		smscIs41TcapRjctReuciRcvd	 Unsigned32, 
		smscIs41TcapRjctUnxpReRcvd	 Unsigned32, 
		smscIs41TcapUserUnrecRcvd	 Unsigned32, 
		smscIs41TcapUserUnxpRcvd	 Unsigned32, 
		smscIs41TcapPrbMtReRcvd	 Unsigned32, 
		smscIs41TcapRjtUnrecmtRcvd	 Unsigned32, 
		smscIs41TcapRjtTranpRcvd	 Unsigned32, 
		smscIs41TcapRjtBftpRcvd	 Unsigned32, 
		smscIs41TcapRjtUnrecidRcvd	 Unsigned32, 
		smscIs41TcapRjctTp2rRcvd	 Unsigned32, 
		smscIs41TcapPrbReslimitRcvd	 Unsigned32, 
		smscIs41TcapAbtUnrecmtSnt	 Unsigned32, 
		smscIs41TcapAbtTranpSnt	 Unsigned32, 
		smscIs41TcapAbtBftpSnt	 Unsigned32, 
		smscIs41TcapAbtUnrecidSnt	 Unsigned32, 
		smscIs41TcapRjctTp2rSnt	 Unsigned32, 
		smscIs41TcapAbtReslimitSnt	 Unsigned32, 
		smscIs41TcapRjctUctSnt	 Unsigned32, 
		smscIs41TcapRjctIcpSnt	 Unsigned32, 
		smscIs41TcapRjctBscpSnt	 Unsigned32, 
		smscIs41TcapRjctIccSnt	 Unsigned32, 
		smscIs41TcapRjctIvdidSnt	 Unsigned32, 
		smscIs41TcapRjctIvuocSnt	 Unsigned32, 
		smscIs41TcapRjctIviparSnt	 Unsigned32, 
		smscIs41TcapRjctUcidSnt	 Unsigned32, 
		smscIs41TcapRjctRruciSnt	 Unsigned32, 
		smscIs41TcapRjctRrurrSnt	 Unsigned32, 
		smscIs41TcapRjctRripSnt	 Unsigned32, 
		smscIs41TcapRjctEruciSnt	 Unsigned32, 
		smscIs41TcapRjctErureSnt	 Unsigned32, 
		smscIs41TcapRjctErueSnt	 Unsigned32, 
		smscIs41TcapRjctErunxSnt	 Unsigned32, 
		smscIs41TcapRjctEripSnt	 Unsigned32, 
		smscIs41TcapActiveDialog	 Unsigned32, 
		smscIs41TcapInitiatedDialog	 Unsigned32, 
		smscIs41TcapUnknMsgRcvd	 Unsigned32, 
		smscIs41TcapNoticeRcvd	 Unsigned32, 
		smscIs41CdmaWptMoAccepted	 Unsigned32, 
		smscIs41CdmaWptMoRejected	 Unsigned32, 
		smscIs41CdmaWmtMoAccepted	 Unsigned32, 
		smscIs41CdmaWmtMoRejected	 Unsigned32, 
		smscIs41CdmaVmnMoAccepted	 Unsigned32, 
		smscIs41CdmaVmnMoRejected	 Unsigned32, 
		smscIs41CdmaWemtMoAccepted	 Unsigned32, 
		smscIs41CdmaWemtMoRejected	 Unsigned32, 
		smscIs41CdmaScptMoAccepted	 Unsigned32, 
		smscIs41CdmaScptMoRejected	 Unsigned32, 
		smscIs41CdmaCatptMoAccepted	 Unsigned32, 
		smscIs41CdmaCatptMoRejected	 Unsigned32, 
		smscIs41CdmaWptMtOk	 Unsigned32, 
		smscIs41CdmaWptMtFail	 Unsigned32, 
		smscIs41CdmaWmtMtOk	 Unsigned32, 
		smscIs41CdmaWmtMtFail	 Unsigned32, 
		smscIs41CdmaVmnMtOk	 Unsigned32, 
		smscIs41CdmaVmnMtFail	 Unsigned32, 
		smscIs41CdmaWapMtOk	 Unsigned32, 
		smscIs41CdmaWapMtFail	 Unsigned32, 
		smscIs41CdmaWemtMtOk	 Unsigned32, 
		smscIs41CdmaWemtMtFail	 Unsigned32, 
		smscIs41CdmaScptMtOk	 Unsigned32, 
		smscIs41CdmaScptMtFail	 Unsigned32, 
		smscIs41CdmaCatptMtOk	 Unsigned32, 
		smscIs41CdmaCatptMtFail	 Unsigned32, 
		smscIs41TdmaCmtMoAccepted	 Unsigned32, 
		smscIs41TdmaCmtMoRejected	 Unsigned32, 
		smscIs41TdmaCptMoAccepted	 Unsigned32, 
		smscIs41TdmaCptMoRejected	 Unsigned32, 
		smscIs41TdmaVmnMoAccepted	 Unsigned32, 
		smscIs41TdmaVmnMoRejected	 Unsigned32, 
		smscIs41TdmaGutsMoAccepted	 Unsigned32, 
		smscIs41TdmaGutsMoRejected	 Unsigned32, 
		smscIs41TdmaOatsMoAccepted	 Unsigned32, 
		smscIs41TdmaOatsMoRejected	 Unsigned32, 
		smscIs41TdmaCptMtOk	 Unsigned32, 
		smscIs41TdmaCptMtFail	 Unsigned32, 
		smscIs41TdmaCmtMtOk	 Unsigned32, 
		smscIs41TdmaCmtMtFail	 Unsigned32, 
		smscIs41TdmaVmnMtOk	 Unsigned32, 
		smscIs41TdmaVmnMtFail	 Unsigned32, 
		smscIs41TdmaGutsMtOk	 Unsigned32, 
		smscIs41TdmaGutsMtFail	 Unsigned32, 
		smscIs41TdmaOptsMtOk	 Unsigned32, 
		smscIs41TdmaOptsMtFail	 Unsigned32, 
		smscIs41TdmaOatsMtOk	 Unsigned32, 
		smscIs41TdmaOatsMtFail	 Unsigned32, 
		smscIs41GhostMoAccepted	 Unsigned32, 
		smscIs41GhostMoRejected	 Unsigned32, 
		smscIs41GhostMtOk	 Unsigned32, 
		smscIs41GhostMtFail	 Unsigned32, 
		smscIs41CarrSpecMoAccepted	 Unsigned32, 
		smscIs41CarrSpecMoRejected	 Unsigned32, 
		smscIs41CarrSpecMtOk	 Unsigned32, 
		smscIs41CarrSpecMtFail	 Unsigned32
	}

smscIs41Name  OBJECT-TYPE
	SYNTAX  DisplayString
	MAX-ACCESS  read-only
	STATUS   current
	DESCRIPTION
		"Identifies the name of the entity."
   ::= {is41InstanceEntry 1 }

smscIs41State  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { is41InstanceEntry 2 }


smscIs41Lastupdate OBJECT-TYPE
		SYNTAX	TimeTicks
		MAX-ACCESS read-only
		STATUS current
		DESCRIPTION
			"Value which reflects the last time the entities fields have been updated"
	::= { is41InstanceEntry	3 }

smscIs41Node  OBJECT-TYPE
	SYNTAX  DisplayString
	MAX-ACCESS  read-only
	STATUS   current
	DESCRIPTION
		"Identifies the node the entity is running on."
   ::= {is41InstanceEntry 4 }

smscIs41MsgReceived OBJECT-TYPE
		SYNTAX	Unsigned32
		MAX-ACCESS read-only
		STATUS current
		DESCRIPTION
			"Received messages"
	::= { is41InstanceEntry	5 }

smscIs41MsgRejected OBJECT-TYPE
		SYNTAX	Unsigned32
		MAX-ACCESS read-only
		STATUS current
		DESCRIPTION
			"Received messages and rejected"
	::= { is41InstanceEntry	6 }

smscIs41MsgTransmitted OBJECT-TYPE
		SYNTAX	Unsigned32
		MAX-ACCESS read-only
		STATUS current
		DESCRIPTION
			"Transmitted messages"
	::= { is41InstanceEntry	7 }

smscIs41MsgFailed OBJECT-TYPE
		SYNTAX	Unsigned32
		MAX-ACCESS read-only
		STATUS current
		DESCRIPTION
			"Messages that failed on sending"
	::= { is41InstanceEntry	8 }

smscIs41SessionsPending OBJECT-TYPE
		SYNTAX	Unsigned32
		MAX-ACCESS read-only
		STATUS current
		DESCRIPTION
			"Number of sessions (currently) pending"
	::= { is41InstanceEntry	9 }

smscIs41DialoguesPending OBJECT-TYPE
		SYNTAX	Unsigned32
		MAX-ACCESS read-only
		STATUS current
		DESCRIPTION
			"Number of dialogues (currently) pending"
	::= { is41InstanceEntry	10 }

smscIs41QelemUsed OBJECT-TYPE
		SYNTAX	Unsigned32
		MAX-ACCESS read-only
		STATUS current
		DESCRIPTION
			"Number of elements in internal queues"
	::= { is41InstanceEntry	11 }

smscIs41QelemInProcqueue OBJECT-TYPE
		SYNTAX	Unsigned32
		MAX-ACCESS read-only
		STATUS current
		DESCRIPTION
			"Number of elements used in process queue"
	::= { is41InstanceEntry	12 }

smscIs41QelemInExpqueue OBJECT-TYPE
		SYNTAX	Unsigned32
		MAX-ACCESS read-only
		STATUS current
		DESCRIPTION
			"Number of elements used in expedited queue"
	::= { is41InstanceEntry	13 }

smscIs41NrTimersRunning OBJECT-TYPE
		SYNTAX	Unsigned32
		MAX-ACCESS read-only
		STATUS current
		DESCRIPTION
			"Total number of timers running"
	::= { is41InstanceEntry	14 }

smscIs41NrSystemTimers OBJECT-TYPE
		SYNTAX	Unsigned32
		MAX-ACCESS read-only
		STATUS current
		DESCRIPTION
			"Number of system timers running"
	::= { is41InstanceEntry	15 }

smscIs41ImiRecallQelem OBJECT-TYPE
		SYNTAX	Unsigned32
		MAX-ACCESS read-only
		STATUS current
		DESCRIPTION
			"Number of IMI recall-queue elements used"
	::= { is41InstanceEntry	16 }

smscIs41ImiRecallQueues OBJECT-TYPE
		SYNTAX	Unsigned32
		MAX-ACCESS read-only
		STATUS current
		DESCRIPTION
			"Number of IMI-recall-queues used"
	::= { is41InstanceEntry	17 }

smscIs41IdiRecallQelem OBJECT-TYPE
		SYNTAX	Unsigned32
		MAX-ACCESS read-only
		STATUS current
		DESCRIPTION
			"Number of IDI recall-queue elements used"
	::= { is41InstanceEntry	18 }

smscIs41IdiRecallQueues OBJECT-TYPE
		SYNTAX	Unsigned32
		MAX-ACCESS read-only
		STATUS current
		DESCRIPTION
			"Number of IDI recall-queues used"
	::= { is41InstanceEntry	19 }

smscIs41IosRecallQelem OBJECT-TYPE
		SYNTAX	Unsigned32
		MAX-ACCESS read-only
		STATUS current
		DESCRIPTION
			"Number of IOS recall-queue elements used"
	::= { is41InstanceEntry	20 }

smscIs41IosRecallQueues OBJECT-TYPE
		SYNTAX	Unsigned32
		MAX-ACCESS read-only
		STATUS current
		DESCRIPTION
			"Number of IOS recall-queues used"
	::= { is41InstanceEntry	21 }

smscIs41LogRecallQelem OBJECT-TYPE
		SYNTAX	Unsigned32
		MAX-ACCESS read-only
		STATUS current
		DESCRIPTION
			"Number of LOG recall-queue elements used"
	::= { is41InstanceEntry	22 }

smscIs41LogRecallQueues OBJECT-TYPE
		SYNTAX	Unsigned32
		MAX-ACCESS read-only
		STATUS current
		DESCRIPTION
			"Number of LOG recall-queues used"
	::= { is41InstanceEntry	23 }

smscIs41TrcreqDiscarded OBJECT-TYPE
		SYNTAX	Unsigned32
		MAX-ACCESS read-only
		STATUS current
		DESCRIPTION
			"Number of trace requests discarded"
	::= { is41InstanceEntry	24 }

smscIs41MtSmsOk OBJECT-TYPE
		SYNTAX	Unsigned32
		MAX-ACCESS read-only
		STATUS current
		DESCRIPTION
			"Number of delivered Mobile Terminated SM"
	::= { is41InstanceEntry	25 }

smscIs41MtSmsFail OBJECT-TYPE
		SYNTAX	Unsigned32
		MAX-ACCESS read-only
		STATUS current
		DESCRIPTION
			"Number of failed Mobile Terminated SM"
	::= { is41InstanceEntry	26 }

smscIs41MoSmsAccepted OBJECT-TYPE
		SYNTAX	Unsigned32
		MAX-ACCESS read-only
		STATUS current
		DESCRIPTION
			"Number of accepted Mobile Originated SM"
	::= { is41InstanceEntry	27 }

smscIs41MoSmsRejected OBJECT-TYPE
		SYNTAX	Unsigned32
		MAX-ACCESS read-only
		STATUS current
		DESCRIPTION
			"Number of rejected Mobile Originated SM"
	::= { is41InstanceEntry	28 }

smscIs41SmsRequestOk OBJECT-TYPE
		SYNTAX	Unsigned32
		MAX-ACCESS read-only
		STATUS current
		DESCRIPTION
			"Number of successful SMSRequest operations"
	::= { is41InstanceEntry	29 }

smscIs41SmsRequestFail OBJECT-TYPE
		SYNTAX	Unsigned32
		MAX-ACCESS read-only
		STATUS current
		DESCRIPTION
			"Number of failed SMSRequest operations"
	::= { is41InstanceEntry	30 }

smscIs41SmsNotifAccepted OBJECT-TYPE
		SYNTAX	Unsigned32
		MAX-ACCESS read-only
		STATUS current
		DESCRIPTION
			"Number of accepted SMSNotification operations"
	::= { is41InstanceEntry	31 }

smscIs41SmsNotifRejected OBJECT-TYPE
		SYNTAX	Unsigned32
		MAX-ACCESS read-only
		STATUS current
		DESCRIPTION
			"Number of rejected SMSNotification operations"
	::= { is41InstanceEntry	32 }

smscIs41SccpAddrErrors OBJECT-TYPE
		SYNTAX	Unsigned32
		MAX-ACCESS read-only
		STATUS current
		DESCRIPTION
			"Number of SCCP address errors"
	::= { is41InstanceEntry	33 }

smscIs41TcapErrors OBJECT-TYPE
		SYNTAX	Unsigned32
		MAX-ACCESS read-only
		STATUS current
		DESCRIPTION
			"Number of TCAP errors/problems"
	::= { is41InstanceEntry	34 }

smscIs41TimeOuts OBJECT-TYPE
		SYNTAX	Unsigned32
		MAX-ACCESS read-only
		STATUS current
		DESCRIPTION
			"Number of IS-41 Network or Server time-outs"
	::= { is41InstanceEntry	35 }

smscIs41SmsAddrProblem OBJECT-TYPE
		SYNTAX	Unsigned32
		MAX-ACCESS read-only
		STATUS current
		DESCRIPTION
			"Number of SMS Address errors"
	::= { is41InstanceEntry	36 }

smscIs41SmsInvalidServiceId OBJECT-TYPE
		SYNTAX	Unsigned32
		MAX-ACCESS read-only
		STATUS current
		DESCRIPTION
			"Number of SMS Invalid Teleservice ID errors"
	::= { is41InstanceEntry	37 }

smscIs41SmsNetworkProblem OBJECT-TYPE
		SYNTAX	Unsigned32
		MAX-ACCESS read-only
		STATUS current
		DESCRIPTION
			"Number of SMS Network Problem errors"
	::= { is41InstanceEntry	38 }

smscIs41SmsTerminalProblem OBJECT-TYPE
		SYNTAX	Unsigned32
		MAX-ACCESS read-only
		STATUS current
		DESCRIPTION
			"Number of SMS Terminal Problem errors"
	::= { is41InstanceEntry	39 }

smscIs41SmsRadioProblem OBJECT-TYPE
		SYNTAX	Unsigned32
		MAX-ACCESS read-only
		STATUS current
		DESCRIPTION
			"Number of SMS Radio Interface Problem errors"
	::= { is41InstanceEntry	40 }

smscIs41SmsEncodingProblem OBJECT-TYPE
		SYNTAX	Unsigned32
		MAX-ACCESS read-only
		STATUS current
		DESCRIPTION
			"SMS Encoding Problem (parameter size) errors"
	::= { is41InstanceEntry	41 }

smscIs41SmsMissingParameter OBJECT-TYPE
		SYNTAX	Unsigned32
		MAX-ACCESS read-only
		STATUS current
		DESCRIPTION
			"Number of SMS Missing Parameter errors"
	::= { is41InstanceEntry	42 }

smscIs41SmsParamValueErr OBJECT-TYPE
		SYNTAX	Unsigned32
		MAX-ACCESS read-only
		STATUS current
		DESCRIPTION
			"Number of SMS Parameter Value errors"
	::= { is41InstanceEntry	43 }

smscIs41SmsGeneralProblem OBJECT-TYPE
		SYNTAX	Unsigned32
		MAX-ACCESS read-only
		STATUS current
		DESCRIPTION
			"Number of SMS General Problem errors"
	::= { is41InstanceEntry	44 }

smscIs41AbsentSubscriber OBJECT-TYPE
		SYNTAX	Unsigned32
		MAX-ACCESS read-only
		STATUS current
		DESCRIPTION
			"Number of Absent Subscriber errors"
	::= { is41InstanceEntry	45 }

smscIs41SmsDestBusy OBJECT-TYPE
		SYNTAX	Unsigned32
		MAX-ACCESS read-only
		STATUS current
		DESCRIPTION
			"Number of Destination Busy errors"
	::= { is41InstanceEntry	46 }

smscIs41SmsDestResourceShort OBJECT-TYPE
		SYNTAX	Unsigned32
		MAX-ACCESS read-only
		STATUS current
		DESCRIPTION
			"Number of Destination Resource Shortage errors"
	::= { is41InstanceEntry	47 }

smscIs41SmsSvcDenied OBJECT-TYPE
		SYNTAX	Unsigned32
		MAX-ACCESS read-only
		STATUS current
		DESCRIPTION
			"Number of Service Denied Errors"
	::= { is41InstanceEntry	48 }

smscIs41MsInvalid OBJECT-TYPE
		SYNTAX	Unsigned32
		MAX-ACCESS read-only
		STATUS current
		DESCRIPTION
			"Number of MS Invalid (HLR Denied) errors"
	::= { is41InstanceEntry	49 }

smscIs41MsUnreachable OBJECT-TYPE
		SYNTAX	Unsigned32
		MAX-ACCESS read-only
		STATUS current
		DESCRIPTION
			"Number of MS Unreachable (HLR Postponed) errors"
	::= { is41InstanceEntry	50 }

smscIs41MsUnavailable OBJECT-TYPE
		SYNTAX	Unsigned32
		MAX-ACCESS read-only
		STATUS current
		DESCRIPTION
			"Number of MS Unavailable (HLR Unavailable) errors"
	::= { is41InstanceEntry	51 }

smscIs41NoPageResponse OBJECT-TYPE
		SYNTAX	Unsigned32
		MAX-ACCESS read-only
		STATUS current
		DESCRIPTION
			"Number of No Page Response errors"
	::= { is41InstanceEntry	52 }

smscIs41DeliveryPostponed OBJECT-TYPE
		SYNTAX	Unsigned32
		MAX-ACCESS read-only
		STATUS current
		DESCRIPTION
			"Number of MSC Delivery Postponed errors"
	::= { is41InstanceEntry	53 }

smscIs41DestLeftAddr OBJECT-TYPE
		SYNTAX	Unsigned32
		MAX-ACCESS read-only
		STATUS current
		DESCRIPTION
			"Number of Destination Left Address errors"
	::= { is41InstanceEntry	54 }

smscIs41Dialogues OBJECT-TYPE
		SYNTAX	Unsigned32
		MAX-ACCESS read-only
		STATUS current
		DESCRIPTION
			"Number of dialogues"
	::= { is41InstanceEntry	55 }

smscIs41OtaspReqOk OBJECT-TYPE
		SYNTAX	Unsigned32
		MAX-ACCESS read-only
		STATUS current
		DESCRIPTION
			"Number successful OTASPRequest operations"
	::= { is41InstanceEntry	56 }

smscIs41OtaspReqFail OBJECT-TYPE
		SYNTAX	Unsigned32
		MAX-ACCESS read-only
		STATUS current
		DESCRIPTION
			"Number failed OTASPRequest operations"
	::= { is41InstanceEntry	57 }

smscIs41TcapBeginRcvd OBJECT-TYPE
		SYNTAX	Unsigned32
		MAX-ACCESS read-only
		STATUS current
		DESCRIPTION
			"Number of Begin Dialogue transactions received"
	::= { is41InstanceEntry	58 }

smscIs41TcapContRcvd OBJECT-TYPE
		SYNTAX	Unsigned32
		MAX-ACCESS read-only
		STATUS current
		DESCRIPTION
			"Number of Continue transactions received"
	::= { is41InstanceEntry	59 }

smscIs41TcapEndRcvd OBJECT-TYPE
		SYNTAX	Unsigned32
		MAX-ACCESS read-only
		STATUS current
		DESCRIPTION
			"Number of End transactions received"
	::= { is41InstanceEntry	60 }

smscIs41TcapBeginSnt OBJECT-TYPE
		SYNTAX	Unsigned32
		MAX-ACCESS read-only
		STATUS current
		DESCRIPTION
			"Number of Begin Dialogue transactions sent"
	::= { is41InstanceEntry	61 }

smscIs41TcapEndSnt OBJECT-TYPE
		SYNTAX	Unsigned32
		MAX-ACCESS read-only
		STATUS current
		DESCRIPTION
			"Number of End transactions sent"
	::= { is41InstanceEntry	62 }

smscIs41TcapFailedSent OBJECT-TYPE
		SYNTAX	Unsigned32
		MAX-ACCESS read-only
		STATUS current
		DESCRIPTION
			"Number of Message failed to be sent"
	::= { is41InstanceEntry	63 }

smscIs41TcapTransDisc OBJECT-TYPE
		SYNTAX	Unsigned32
		MAX-ACCESS read-only
		STATUS current
		DESCRIPTION
			"Number of discarded msgs due to transport problem"
	::= { is41InstanceEntry	64 }

smscIs41TcapMsgDisc OBJECT-TYPE
		SYNTAX	Unsigned32
		MAX-ACCESS read-only
		STATUS current
		DESCRIPTION
			"Number of discarded TCAP messages"
	::= { is41InstanceEntry	65 }

smscIs41TcapAbtRcvd OBJECT-TYPE
		SYNTAX	Unsigned32
		MAX-ACCESS read-only
		STATUS current
		DESCRIPTION
			"Number of P_ABORT transacs rcvd"
	::= { is41InstanceEntry	66 }

smscIs41TcapAbtUnrecmtRcvd OBJECT-TYPE
		SYNTAX	Unsigned32
		MAX-ACCESS read-only
		STATUS current
		DESCRIPTION
			"Number of P_ABORT transacs rcvd (unrec msg type)"
	::= { is41InstanceEntry	67 }

smscIs41TcapAbtTranpRcvd OBJECT-TYPE
		SYNTAX	Unsigned32
		MAX-ACCESS read-only
		STATUS current
		DESCRIPTION
			"Number of P_ABORT msgs rcvd (inc trans portion)"
	::= { is41InstanceEntry	68 }

smscIs41TcapAbtBftpRcvd OBJECT-TYPE
		SYNTAX	Unsigned32
		MAX-ACCESS read-only
		STATUS current
		DESCRIPTION
			"Number of P_ABORT msgs rcvd (badly formed tp)"
	::= { is41InstanceEntry	69 }

smscIs41TcapAbtUnrecidRcvd OBJECT-TYPE
		SYNTAX	Unsigned32
		MAX-ACCESS read-only
		STATUS current
		DESCRIPTION
			"Number of P_ABORT msgs rcvd (unrec trans id)"
	::= { is41InstanceEntry	70 }

smscIs41TcapAbtReslimitRcvd OBJECT-TYPE
		SYNTAX	Unsigned32
		MAX-ACCESS read-only
		STATUS current
		DESCRIPTION
			"Number of P_ABORT msgs rcvd (resouce limitation)"
	::= { is41InstanceEntry	71 }

smscIs41TcapAbtAbnormRcvd OBJECT-TYPE
		SYNTAX	Unsigned32
		MAX-ACCESS read-only
		STATUS current
		DESCRIPTION
			"Number of P_ABORT msgs rcvd (abnormal dialog)"
	::= { is41InstanceEntry	72 }

smscIs41TcapUabtRcvd OBJECT-TYPE
		SYNTAX	Unsigned32
		MAX-ACCESS read-only
		STATUS current
		DESCRIPTION
			"Number of U_ABORT transactions received"
	::= { is41InstanceEntry	73 }

smscIs41TcapInvkRcvd OBJECT-TYPE
		SYNTAX	Unsigned32
		MAX-ACCESS read-only
		STATUS current
		DESCRIPTION
			"Number of Invoke Last components received"
	::= { is41InstanceEntry	74 }

smscIs41TcapInvknlRcvd OBJECT-TYPE
		SYNTAX	Unsigned32
		MAX-ACCESS read-only
		STATUS current
		DESCRIPTION
			"Number of Invoke Not Last components received"
	::= { is41InstanceEntry	75 }

smscIs41TcapInvkSnt OBJECT-TYPE
		SYNTAX	Unsigned32
		MAX-ACCESS read-only
		STATUS current
		DESCRIPTION
			"Number of Invoke Last components sent"
	::= { is41InstanceEntry	76 }

smscIs41TcapResLastRcvd OBJECT-TYPE
		SYNTAX	Unsigned32
		MAX-ACCESS read-only
		STATUS current
		DESCRIPTION
			"Number of Result Last components received"
	::= { is41InstanceEntry	77 }

smscIs41TcapResNolastRcvd OBJECT-TYPE
		SYNTAX	Unsigned32
		MAX-ACCESS read-only
		STATUS current
		DESCRIPTION
			"Number of Result No Last components received"
	::= { is41InstanceEntry	78 }

smscIs41TcapResLastSnt OBJECT-TYPE
		SYNTAX	Unsigned32
		MAX-ACCESS read-only
		STATUS current
		DESCRIPTION
			"Number of Result Last components sent"
	::= { is41InstanceEntry	79 }

smscIs41TcapErrorRcvd OBJECT-TYPE
		SYNTAX	Unsigned32
		MAX-ACCESS read-only
		STATUS current
		DESCRIPTION
			"Number of Error components received"
	::= { is41InstanceEntry	80 }

smscIs41TcapErrorSnt OBJECT-TYPE
		SYNTAX	Unsigned32
		MAX-ACCESS read-only
		STATUS current
		DESCRIPTION
			"Number of Error components sent"
	::= { is41InstanceEntry	81 }

smscIs41TcapRejectSnt OBJECT-TYPE
		SYNTAX	Unsigned32
		MAX-ACCESS read-only
		STATUS current
		DESCRIPTION
			"Number of Reject components sent"
	::= { is41InstanceEntry	82 }

smscIs41TcapRejectRcvd OBJECT-TYPE
		SYNTAX	Unsigned32
		MAX-ACCESS read-only
		STATUS current
		DESCRIPTION
			"Number of Reject components rcvd"
	::= { is41InstanceEntry	83 }

smscIs41TcapRjctUnrecRcvd OBJECT-TYPE
		SYNTAX	Unsigned32
		MAX-ACCESS read-only
		STATUS current
		DESCRIPTION
			"Number of Reject components rcvd (unrec comp type)"
	::= { is41InstanceEntry	84 }

smscIs41TcapRjctIcpRcvd OBJECT-TYPE
		SYNTAX	Unsigned32
		MAX-ACCESS read-only
		STATUS current
		DESCRIPTION
			"Number of Reject components rcvd (incor comp por)"
	::= { is41InstanceEntry	85 }

smscIs41TcapRjctBadsRcvd OBJECT-TYPE
		SYNTAX	Unsigned32
		MAX-ACCESS read-only
		STATUS current
		DESCRIPTION
			"Number of Reject components rcvd(badly struct comp)"
	::= { is41InstanceEntry	86 }

smscIs41TcapRjctIccRcvd OBJECT-TYPE
		SYNTAX	Unsigned32
		MAX-ACCESS read-only
		STATUS current
		DESCRIPTION
			"Number of Reject components rcvd(incorr comp coding)"
	::= { is41InstanceEntry	87 }

smscIs41TcapRjctDupIidRcvd OBJECT-TYPE
		SYNTAX	Unsigned32
		MAX-ACCESS read-only
		STATUS current
		DESCRIPTION
			"Number of Rejects rcvd (invoke dup id)"
	::= { is41InstanceEntry	88 }

smscIs41TcapPrbUnrecOpRcvd OBJECT-TYPE
		SYNTAX	Unsigned32
		MAX-ACCESS read-only
		STATUS current
		DESCRIPTION
			"Number of Rejects rcvd (invoke unrec oper)"
	::= { is41InstanceEntry	89 }

smscIs41TcapPrbMistypeRcvd OBJECT-TYPE
		SYNTAX	Unsigned32
		MAX-ACCESS read-only
		STATUS current
		DESCRIPTION
			"Number of Rejects rcvd (incor param)"
	::= { is41InstanceEntry	90 }

smscIs41TcapRjctUnrLidRcvd OBJECT-TYPE
		SYNTAX	Unsigned32
		MAX-ACCESS read-only
		STATUS current
		DESCRIPTION
			"Number of Rejects rcvd (invoke unrec corr ID)"
	::= { is41InstanceEntry	91 }

smscIs41TcapRjctRruciRcvd OBJECT-TYPE
		SYNTAX	Unsigned32
		MAX-ACCESS read-only
		STATUS current
		DESCRIPTION
			"Number of Rejects rcvd (result unass corr ID)"
	::= { is41InstanceEntry	92 }

smscIs41TcapRjctUnxpRrRcvd OBJECT-TYPE
		SYNTAX	Unsigned32
		MAX-ACCESS read-only
		STATUS current
		DESCRIPTION
			"Number of Rejects rcvd (result unexpected)"
	::= { is41InstanceEntry	93 }

smscIs41TcapPrbMtRrRcvd OBJECT-TYPE
		SYNTAX	Unsigned32
		MAX-ACCESS read-only
		STATUS current
		DESCRIPTION
			"Number of Rejects rcvd (result inc par)"
	::= { is41InstanceEntry	94 }

smscIs41TcapRjctReuciRcvd OBJECT-TYPE
		SYNTAX	Unsigned32
		MAX-ACCESS read-only
		STATUS current
		DESCRIPTION
			"Number of Rejects rcvd (error unass corr ID)"
	::= { is41InstanceEntry	95 }

smscIs41TcapRjctUnxpReRcvd OBJECT-TYPE
		SYNTAX	Unsigned32
		MAX-ACCESS read-only
		STATUS current
		DESCRIPTION
			"Number of Rejects rcvd (error unexp ret err)"
	::= { is41InstanceEntry	96 }

smscIs41TcapUserUnrecRcvd OBJECT-TYPE
		SYNTAX	Unsigned32
		MAX-ACCESS read-only
		STATUS current
		DESCRIPTION
			"Number of Rejects rcvd (error unrec err)"
	::= { is41InstanceEntry	97 }

smscIs41TcapUserUnxpRcvd OBJECT-TYPE
		SYNTAX	Unsigned32
		MAX-ACCESS read-only
		STATUS current
		DESCRIPTION
			"Number of Rejects rcvd (error unexpected)"
	::= { is41InstanceEntry	98 }

smscIs41TcapPrbMtReRcvd OBJECT-TYPE
		SYNTAX	Unsigned32
		MAX-ACCESS read-only
		STATUS current
		DESCRIPTION
			"Number of Rejects rcvd (error inc param)"
	::= { is41InstanceEntry	99 }

smscIs41TcapRjtUnrecmtRcvd OBJECT-TYPE
		SYNTAX	Unsigned32
		MAX-ACCESS read-only
		STATUS current
		DESCRIPTION
			"Number of Rejects rcvd (trans unrec package)"
	::= { is41InstanceEntry	100 }

smscIs41TcapRjtTranpRcvd OBJECT-TYPE
		SYNTAX	Unsigned32
		MAX-ACCESS read-only
		STATUS current
		DESCRIPTION
			"Number of Rejects rcvd (trans inc trans portion)"
	::= { is41InstanceEntry	101 }

smscIs41TcapRjtBftpRcvd OBJECT-TYPE
		SYNTAX	Unsigned32
		MAX-ACCESS read-only
		STATUS current
		DESCRIPTION
			"Number of Rejects rcvd (trans badly formed tp)"
	::= { is41InstanceEntry	102 }

smscIs41TcapRjtUnrecidRcvd OBJECT-TYPE
		SYNTAX	Unsigned32
		MAX-ACCESS read-only
		STATUS current
		DESCRIPTION
			"Number of Rejects rcvd (trans unassigned TID)"
	::= { is41InstanceEntry	103 }

smscIs41TcapRjctTp2rRcvd OBJECT-TYPE
		SYNTAX	Unsigned32
		MAX-ACCESS read-only
		STATUS current
		DESCRIPTION
			"Number of Rejects rcvd (trans permiss to rel)"
	::= { is41InstanceEntry	104 }

smscIs41TcapPrbReslimitRcvd OBJECT-TYPE
		SYNTAX	Unsigned32
		MAX-ACCESS read-only
		STATUS current
		DESCRIPTION
			"Number of Rejects rcvd (trans resource limit)"
	::= { is41InstanceEntry	105 }

smscIs41TcapAbtUnrecmtSnt OBJECT-TYPE
		SYNTAX	Unsigned32
		MAX-ACCESS read-only
		STATUS current
		DESCRIPTION
			"Number of Rejects sent (trans unrec msg type)"
	::= { is41InstanceEntry	106 }

smscIs41TcapAbtTranpSnt OBJECT-TYPE
		SYNTAX	Unsigned32
		MAX-ACCESS read-only
		STATUS current
		DESCRIPTION
			"Number of Rejects sent (trans inc trns portion)"
	::= { is41InstanceEntry	107 }

smscIs41TcapAbtBftpSnt OBJECT-TYPE
		SYNTAX	Unsigned32
		MAX-ACCESS read-only
		STATUS current
		DESCRIPTION
			"Number of Rejects sent (trans badly formed tp)"
	::= { is41InstanceEntry	108 }

smscIs41TcapAbtUnrecidSnt OBJECT-TYPE
		SYNTAX	Unsigned32
		MAX-ACCESS read-only
		STATUS current
		DESCRIPTION
			"Number of Rejects sent (unrec trns ID)"
	::= { is41InstanceEntry	109 }

smscIs41TcapRjctTp2rSnt OBJECT-TYPE
		SYNTAX	Unsigned32
		MAX-ACCESS read-only
		STATUS current
		DESCRIPTION
			"Number of Rejects sent (trans perm to release)"
	::= { is41InstanceEntry	110 }

smscIs41TcapAbtReslimitSnt OBJECT-TYPE
		SYNTAX	Unsigned32
		MAX-ACCESS read-only
		STATUS current
		DESCRIPTION
			"Number of Rejects sent (trans res lim)"
	::= { is41InstanceEntry	111 }

smscIs41TcapRjctUctSnt OBJECT-TYPE
		SYNTAX	Unsigned32
		MAX-ACCESS read-only
		STATUS current
		DESCRIPTION
			"Number of Rejects sent (unrec comp type)"
	::= { is41InstanceEntry	112 }

smscIs41TcapRjctIcpSnt OBJECT-TYPE
		SYNTAX	Unsigned32
		MAX-ACCESS read-only
		STATUS current
		DESCRIPTION
			"Number of Rejects sent (inc comp portion)"
	::= { is41InstanceEntry	113 }

smscIs41TcapRjctBscpSnt OBJECT-TYPE
		SYNTAX	Unsigned32
		MAX-ACCESS read-only
		STATUS current
		DESCRIPTION
			"Number of Rejects sent (badly str comp)"
	::= { is41InstanceEntry	114 }

smscIs41TcapRjctIccSnt OBJECT-TYPE
		SYNTAX	Unsigned32
		MAX-ACCESS read-only
		STATUS current
		DESCRIPTION
			"Number of Rejects sent (inc comp coding)"
	::= { is41InstanceEntry	115 }

smscIs41TcapRjctIvdidSnt OBJECT-TYPE
		SYNTAX	Unsigned32
		MAX-ACCESS read-only
		STATUS current
		DESCRIPTION
			"Number of Rejects sent (inv dup invk ID)"
	::= { is41InstanceEntry	116 }

smscIs41TcapRjctIvuocSnt OBJECT-TYPE
		SYNTAX	Unsigned32
		MAX-ACCESS read-only
		STATUS current
		DESCRIPTION
			"Number of Rejects sent (inv unrec oper)"
	::= { is41InstanceEntry	117 }

smscIs41TcapRjctIviparSnt OBJECT-TYPE
		SYNTAX	Unsigned32
		MAX-ACCESS read-only
		STATUS current
		DESCRIPTION
			"Number of Rejects sent (inv inc param)"
	::= { is41InstanceEntry	118 }

smscIs41TcapRjctUcidSnt OBJECT-TYPE
		SYNTAX	Unsigned32
		MAX-ACCESS read-only
		STATUS current
		DESCRIPTION
			"Number of Rejects sent (inv unrec corr ID)"
	::= { is41InstanceEntry	119 }

smscIs41TcapRjctRruciSnt OBJECT-TYPE
		SYNTAX	Unsigned32
		MAX-ACCESS read-only
		STATUS current
		DESCRIPTION
			"Number of Rejects sent (result unass corr ID)"
	::= { is41InstanceEntry	120 }

smscIs41TcapRjctRrurrSnt OBJECT-TYPE
		SYNTAX	Unsigned32
		MAX-ACCESS read-only
		STATUS current
		DESCRIPTION
			"Number of Rejects sent (result unexp result)"
	::= { is41InstanceEntry	121 }

smscIs41TcapRjctRripSnt OBJECT-TYPE
		SYNTAX	Unsigned32
		MAX-ACCESS read-only
		STATUS current
		DESCRIPTION
			"Number of Rejects sent (result inc param)"
	::= { is41InstanceEntry	122 }

smscIs41TcapRjctEruciSnt OBJECT-TYPE
		SYNTAX	Unsigned32
		MAX-ACCESS read-only
		STATUS current
		DESCRIPTION
			"Number of Rejects sent (error unass corr ID)"
	::= { is41InstanceEntry	123 }

smscIs41TcapRjctErureSnt OBJECT-TYPE
		SYNTAX	Unsigned32
		MAX-ACCESS read-only
		STATUS current
		DESCRIPTION
			"Number of Rejects sent (error unexp ret error)"
	::= { is41InstanceEntry	124 }

smscIs41TcapRjctErueSnt OBJECT-TYPE
		SYNTAX	Unsigned32
		MAX-ACCESS read-only
		STATUS current
		DESCRIPTION
			"Number of Rejects sent (error unrec error)"
	::= { is41InstanceEntry	125 }

smscIs41TcapRjctErunxSnt OBJECT-TYPE
		SYNTAX	Unsigned32
		MAX-ACCESS read-only
		STATUS current
		DESCRIPTION
			"Number of Rejects sent (error unexp error)"
	::= { is41InstanceEntry	126 }

smscIs41TcapRjctEripSnt OBJECT-TYPE
		SYNTAX	Unsigned32
		MAX-ACCESS read-only
		STATUS current
		DESCRIPTION
			"Number of Rejects sent (error inc param)"
	::= { is41InstanceEntry	127 }

smscIs41TcapActiveDialog OBJECT-TYPE
		SYNTAX	Unsigned32
		MAX-ACCESS read-only
		STATUS current
		DESCRIPTION
			"Number of simultaneous active TCAP dialogues"
	::= { is41InstanceEntry	128 }

smscIs41TcapInitiatedDialog OBJECT-TYPE
		SYNTAX	Unsigned32
		MAX-ACCESS read-only
		STATUS current
		DESCRIPTION
			"Number of simultaneous initiated TCAP dialogues"
	::= { is41InstanceEntry	129 }

smscIs41TcapUnknMsgRcvd OBJECT-TYPE
		SYNTAX	Unsigned32
		MAX-ACCESS read-only
		STATUS current
		DESCRIPTION
			"Number of incorrect or unknown TCAP msgs received"
	::= { is41InstanceEntry	130 }

smscIs41TcapNoticeRcvd OBJECT-TYPE
		SYNTAX	Unsigned32
		MAX-ACCESS read-only
		STATUS current
		DESCRIPTION
			"Number of Notice rcvd"
	::= { is41InstanceEntry	131 }

smscIs41CdmaWptMoAccepted OBJECT-TYPE
		SYNTAX	Unsigned32
		MAX-ACCESS read-only
		STATUS current
		DESCRIPTION
			"Number of accepted msgs with Teleservice CDMA WPT"
	::= { is41InstanceEntry	132 }

smscIs41CdmaWptMoRejected OBJECT-TYPE
		SYNTAX	Unsigned32
		MAX-ACCESS read-only
		STATUS current
		DESCRIPTION
			"Number of rejected msgs with Teleservice CDMA WPT"
	::= { is41InstanceEntry	133 }

smscIs41CdmaWmtMoAccepted OBJECT-TYPE
		SYNTAX	Unsigned32
		MAX-ACCESS read-only
		STATUS current
		DESCRIPTION
			"Number of accepted msgs with Teleservice CDMA WMT"
	::= { is41InstanceEntry	134 }

smscIs41CdmaWmtMoRejected OBJECT-TYPE
		SYNTAX	Unsigned32
		MAX-ACCESS read-only
		STATUS current
		DESCRIPTION
			"Number of rejected msgs with Teleservice CDMA WMT"
	::= { is41InstanceEntry	135 }

smscIs41CdmaVmnMoAccepted OBJECT-TYPE
		SYNTAX	Unsigned32
		MAX-ACCESS read-only
		STATUS current
		DESCRIPTION
			"Number of accepted msgs with Teleservice CDMA VMN"
	::= { is41InstanceEntry	136 }

smscIs41CdmaVmnMoRejected OBJECT-TYPE
		SYNTAX	Unsigned32
		MAX-ACCESS read-only
		STATUS current
		DESCRIPTION
			"Number of rejected msgs with Teleservice CDMA VMN"
	::= { is41InstanceEntry	137 }

smscIs41CdmaWemtMoAccepted OBJECT-TYPE
		SYNTAX	Unsigned32
		MAX-ACCESS read-only
		STATUS current
		DESCRIPTION
			"Number of accepted msgs with Teleservice CDMA WEMT"
	::= { is41InstanceEntry	138 }

smscIs41CdmaWemtMoRejected OBJECT-TYPE
		SYNTAX	Unsigned32
		MAX-ACCESS read-only
		STATUS current
		DESCRIPTION
			"Number of rejected msgs with Teleservice CDMA WEMT"
	::= { is41InstanceEntry	139 }

smscIs41CdmaScptMoAccepted OBJECT-TYPE
		SYNTAX	Unsigned32
		MAX-ACCESS read-only
		STATUS current
		DESCRIPTION
			"Number of accepted msgs with Teleservice CDMA SCPT"
	::= { is41InstanceEntry	140 }

smscIs41CdmaScptMoRejected OBJECT-TYPE
		SYNTAX	Unsigned32
		MAX-ACCESS read-only
		STATUS current
		DESCRIPTION
			"Number of rejected msgs with Teleservice CDMA SCPT"
	::= { is41InstanceEntry	141 }

smscIs41CdmaCatptMoAccepted OBJECT-TYPE
		SYNTAX	Unsigned32
		MAX-ACCESS read-only
		STATUS current
		DESCRIPTION
			"Number of accepted msgs with TeleserviceCDMA CATPT"
	::= { is41InstanceEntry	142 }

smscIs41CdmaCatptMoRejected OBJECT-TYPE
		SYNTAX	Unsigned32
		MAX-ACCESS read-only
		STATUS current
		DESCRIPTION
			"Number of rejected msgs with TeleserviceCDMA CATPT"
	::= { is41InstanceEntry	143 }

smscIs41CdmaWptMtOk OBJECT-TYPE
		SYNTAX	Unsigned32
		MAX-ACCESS read-only
		STATUS current
		DESCRIPTION
			"Number of delivered msgs with Teleservice CDMA WPT"
	::= { is41InstanceEntry	144 }

smscIs41CdmaWptMtFail OBJECT-TYPE
		SYNTAX	Unsigned32
		MAX-ACCESS read-only
		STATUS current
		DESCRIPTION
			"Number of failed msgs with Teleservice CDMA WPT"
	::= { is41InstanceEntry	145 }

smscIs41CdmaWmtMtOk OBJECT-TYPE
		SYNTAX	Unsigned32
		MAX-ACCESS read-only
		STATUS current
		DESCRIPTION
			"Number of delivered msgs with Teleservice CDMA WMT"
	::= { is41InstanceEntry	146 }

smscIs41CdmaWmtMtFail OBJECT-TYPE
		SYNTAX	Unsigned32
		MAX-ACCESS read-only
		STATUS current
		DESCRIPTION
			"Number of failed msgs with Teleservice CDMA WMT"
	::= { is41InstanceEntry	147 }

smscIs41CdmaVmnMtOk OBJECT-TYPE
		SYNTAX	Unsigned32
		MAX-ACCESS read-only
		STATUS current
		DESCRIPTION
			"Number of delivered msgs with Teleservice CDMA VMN"
	::= { is41InstanceEntry	148 }

smscIs41CdmaVmnMtFail OBJECT-TYPE
		SYNTAX	Unsigned32
		MAX-ACCESS read-only
		STATUS current
		DESCRIPTION
			"Number of failed msgs with Teleservice CDMA VMN"
	::= { is41InstanceEntry	149 }

smscIs41CdmaWapMtOk OBJECT-TYPE
		SYNTAX	Unsigned32
		MAX-ACCESS read-only
		STATUS current
		DESCRIPTION
			"Number of delivered msgs with Teleservice CDMA WAP"
	::= { is41InstanceEntry	150 }

smscIs41CdmaWapMtFail OBJECT-TYPE
		SYNTAX	Unsigned32
		MAX-ACCESS read-only
		STATUS current
		DESCRIPTION
			"Number of failed msgs with Teleservice CDMA WAP"
	::= { is41InstanceEntry	151 }

smscIs41CdmaWemtMtOk OBJECT-TYPE
		SYNTAX	Unsigned32
		MAX-ACCESS read-only
		STATUS current
		DESCRIPTION
			"Number of delivered msgs with Teleserv. CDMA WEMT"
	::= { is41InstanceEntry	152 }

smscIs41CdmaWemtMtFail OBJECT-TYPE
		SYNTAX	Unsigned32
		MAX-ACCESS read-only
		STATUS current
		DESCRIPTION
			"Number of failed msgs with Teleservice CDMA WEMT"
	::= { is41InstanceEntry	153 }

smscIs41CdmaScptMtOk OBJECT-TYPE
		SYNTAX	Unsigned32
		MAX-ACCESS read-only
		STATUS current
		DESCRIPTION
			"Number of delivered msgs with Teleserv. CDMA SCPT"
	::= { is41InstanceEntry	154 }

smscIs41CdmaScptMtFail OBJECT-TYPE
		SYNTAX	Unsigned32
		MAX-ACCESS read-only
		STATUS current
		DESCRIPTION
			"Number of failed msgs with Teleservice CDMA SCPT"
	::= { is41InstanceEntry	155 }

smscIs41CdmaCatptMtOk OBJECT-TYPE
		SYNTAX	Unsigned32
		MAX-ACCESS read-only
		STATUS current
		DESCRIPTION
			"Number of delivered msgs with Teleserv. CDMA CATPT"
	::= { is41InstanceEntry	156 }

smscIs41CdmaCatptMtFail OBJECT-TYPE
		SYNTAX	Unsigned32
		MAX-ACCESS read-only
		STATUS current
		DESCRIPTION
			"Number of failed msgs with Teleservice CDMA CATPT"
	::= { is41InstanceEntry	157 }

smscIs41TdmaCmtMoAccepted OBJECT-TYPE
		SYNTAX	Unsigned32
		MAX-ACCESS read-only
		STATUS current
		DESCRIPTION
			"Number of accepted msgs with Teleservice TDMA CMT"
	::= { is41InstanceEntry	158 }

smscIs41TdmaCmtMoRejected OBJECT-TYPE
		SYNTAX	Unsigned32
		MAX-ACCESS read-only
		STATUS current
		DESCRIPTION
			"Number of rejected msgs with Teleservice TDMA CMT"
	::= { is41InstanceEntry	159 }

smscIs41TdmaCptMoAccepted OBJECT-TYPE
		SYNTAX	Unsigned32
		MAX-ACCESS read-only
		STATUS current
		DESCRIPTION
			"Number of accepted msgs with Teleservice TDMA CPT"
	::= { is41InstanceEntry	160 }

smscIs41TdmaCptMoRejected OBJECT-TYPE
		SYNTAX	Unsigned32
		MAX-ACCESS read-only
		STATUS current
		DESCRIPTION
			"Number of rejected msgs with Teleservice TDMA CPT"
	::= { is41InstanceEntry	161 }

smscIs41TdmaVmnMoAccepted OBJECT-TYPE
		SYNTAX	Unsigned32
		MAX-ACCESS read-only
		STATUS current
		DESCRIPTION
			"Number of accepted msgs with Teleservice TDMA VMN"
	::= { is41InstanceEntry	162 }

smscIs41TdmaVmnMoRejected OBJECT-TYPE
		SYNTAX	Unsigned32
		MAX-ACCESS read-only
		STATUS current
		DESCRIPTION
			"Number of rejected msgs with Teleservice TDMA VMN"
	::= { is41InstanceEntry	163 }

smscIs41TdmaGutsMoAccepted OBJECT-TYPE
		SYNTAX	Unsigned32
		MAX-ACCESS read-only
		STATUS current
		DESCRIPTION
			"Number of accepted msgs with Teleservice TDMA GUTS"
	::= { is41InstanceEntry	164 }

smscIs41TdmaGutsMoRejected OBJECT-TYPE
		SYNTAX	Unsigned32
		MAX-ACCESS read-only
		STATUS current
		DESCRIPTION
			"Number of rejected msgs with Teleservice TDMA GUTS"
	::= { is41InstanceEntry	165 }

smscIs41TdmaOatsMoAccepted OBJECT-TYPE
		SYNTAX	Unsigned32
		MAX-ACCESS read-only
		STATUS current
		DESCRIPTION
			"Number of accepted msgs with Teleservice TDMA OATS"
	::= { is41InstanceEntry	166 }

smscIs41TdmaOatsMoRejected OBJECT-TYPE
		SYNTAX	Unsigned32
		MAX-ACCESS read-only
		STATUS current
		DESCRIPTION
			"Number of rejected msgs with Teleservice TDMA OATS"
	::= { is41InstanceEntry	167 }

smscIs41TdmaCptMtOk OBJECT-TYPE
		SYNTAX	Unsigned32
		MAX-ACCESS read-only
		STATUS current
		DESCRIPTION
			"Number of delivered msgs with Teleservice TDMA CPT"
	::= { is41InstanceEntry	168 }

smscIs41TdmaCptMtFail OBJECT-TYPE
		SYNTAX	Unsigned32
		MAX-ACCESS read-only
		STATUS current
		DESCRIPTION
			"Number of failed msgs with Teleservice TDMA CPT"
	::= { is41InstanceEntry	169 }

smscIs41TdmaCmtMtOk OBJECT-TYPE
		SYNTAX	Unsigned32
		MAX-ACCESS read-only
		STATUS current
		DESCRIPTION
			"Number of delivered msgs with Teleservice TDMA CMT"
	::= { is41InstanceEntry	170 }

smscIs41TdmaCmtMtFail OBJECT-TYPE
		SYNTAX	Unsigned32
		MAX-ACCESS read-only
		STATUS current
		DESCRIPTION
			"Number of failed msgs with Teleservice TDMA CMT"
	::= { is41InstanceEntry	171 }

smscIs41TdmaVmnMtOk OBJECT-TYPE
		SYNTAX	Unsigned32
		MAX-ACCESS read-only
		STATUS current
		DESCRIPTION
			"Number of delivered msgs with Teleservice TDMA VMN"
	::= { is41InstanceEntry	172 }

smscIs41TdmaVmnMtFail OBJECT-TYPE
		SYNTAX	Unsigned32
		MAX-ACCESS read-only
		STATUS current
		DESCRIPTION
			"Number of failed msgs with Teleservice TDMA VMN"
	::= { is41InstanceEntry	173 }

smscIs41TdmaGutsMtOk OBJECT-TYPE
		SYNTAX	Unsigned32
		MAX-ACCESS read-only
		STATUS current
		DESCRIPTION
			"Number of delivered msgs with Teleserv. TDMA GUTS"
	::= { is41InstanceEntry	174 }

smscIs41TdmaGutsMtFail OBJECT-TYPE
		SYNTAX	Unsigned32
		MAX-ACCESS read-only
		STATUS current
		DESCRIPTION
			"Number of failed msgs with Teleservice TDMA GUTS"
	::= { is41InstanceEntry	175 }

smscIs41TdmaOptsMtOk OBJECT-TYPE
		SYNTAX	Unsigned32
		MAX-ACCESS read-only
		STATUS current
		DESCRIPTION
			"Number of delivered msgs with Teleserv. TDMA OPTS"
	::= { is41InstanceEntry	176 }

smscIs41TdmaOptsMtFail OBJECT-TYPE
		SYNTAX	Unsigned32
		MAX-ACCESS read-only
		STATUS current
		DESCRIPTION
			"Number of failed msgs with Teleservice TDMA OPTS"
	::= { is41InstanceEntry	177 }

smscIs41TdmaOatsMtOk OBJECT-TYPE
		SYNTAX	Unsigned32
		MAX-ACCESS read-only
		STATUS current
		DESCRIPTION
			"Number of delivered msgs with Teleserv. TDMA OATS"
	::= { is41InstanceEntry	178 }

smscIs41TdmaOatsMtFail OBJECT-TYPE
		SYNTAX	Unsigned32
		MAX-ACCESS read-only
		STATUS current
		DESCRIPTION
			"Number of failed msgs with Teleservice TDMA OATS"
	::= { is41InstanceEntry	179 }

smscIs41GhostMoAccepted OBJECT-TYPE
		SYNTAX	Unsigned32
		MAX-ACCESS read-only
		STATUS current
		DESCRIPTION
			"Number of accepted msgs with Teleservice GHOST"
	::= { is41InstanceEntry	180 }

smscIs41GhostMoRejected OBJECT-TYPE
		SYNTAX	Unsigned32
		MAX-ACCESS read-only
		STATUS current
		DESCRIPTION
			"Number of rejected msgs with Teleservice GHOST"
	::= { is41InstanceEntry	181 }

smscIs41GhostMtOk OBJECT-TYPE
		SYNTAX	Unsigned32
		MAX-ACCESS read-only
		STATUS current
		DESCRIPTION
			"Number of delivered msgs with Teleservice GHOST"
	::= { is41InstanceEntry	182 }

smscIs41GhostMtFail OBJECT-TYPE
		SYNTAX	Unsigned32
		MAX-ACCESS read-only
		STATUS current
		DESCRIPTION
			"Number of failed msgs with Teleservice GHOST"
	::= { is41InstanceEntry	183 }

smscIs41CarrSpecMoAccepted OBJECT-TYPE
		SYNTAX	Unsigned32
		MAX-ACCESS read-only
		STATUS current
		DESCRIPTION
			"Accepted msgs with Carrier-specific Teleservices"
	::= { is41InstanceEntry	184 }

smscIs41CarrSpecMoRejected OBJECT-TYPE
		SYNTAX	Unsigned32
		MAX-ACCESS read-only
		STATUS current
		DESCRIPTION
			"Rejected msgs with Carrier-specific Teleservices"
	::= { is41InstanceEntry	185 }

smscIs41CarrSpecMtOk OBJECT-TYPE
		SYNTAX	Unsigned32
		MAX-ACCESS read-only
		STATUS current
		DESCRIPTION
			"Delivered msgs with Carrier-specific Teleservices"
	::= { is41InstanceEntry	186 }

smscIs41CarrSpecMtFail OBJECT-TYPE
		SYNTAX	Unsigned32
		MAX-ACCESS read-only
		STATUS current
		DESCRIPTION
			"Failed msgs with Carrier-specific Teleservices"
	::= { is41InstanceEntry	187 }



-- end of IS41 description.
-- --------------------------------------


-- --------------------------------------
-- Class RTR
-- 
smscRtr OBJECT-TYPE
	SYNTAX  SEQUENCE OF RtrInstanceEntry
	MAX-ACCESS  not-accessible
	STATUS  current
	DESCRIPTION
		"Mapping table for SMSC RTR entities."
   ::= { smscClassServer   10  }

rtrInstanceEntry  OBJECT-TYPE
	SYNTAX RtrInstanceEntry
	MAX-ACCESS  not-accessible
	STATUS  current
	DESCRIPTION
		"An entry (row) in the entityInstanceTable."
	INDEX { IMPLIED smscRtrName }
   ::= { smscRtr 1 }

RtrInstanceEntry ::= SEQUENCE {
		smscRtrName     DisplayString,
		smscRtrState   INTEGER,
		smscRtrLastupdate   TimeTicks,
		smscRtrNode	   DisplayString, 
		smscRtrMsgReceived	 Unsigned32, 
		smscRtrMsgRejected	 Unsigned32, 
		smscRtrMsgTransmitted	 Unsigned32, 
		smscRtrMsgFailed	 Unsigned32, 
		smscRtrQelemUsed	 Unsigned32, 
		smscRtrQelemInProcqueue	 Unsigned32, 
		smscRtrQelemInExpqueue	 Unsigned32, 
		smscRtrNrTimersRunning	 Unsigned32, 
		smscRtrNrSystemTimers	 Unsigned32, 
		smscRtrImiRecallQelem	 Unsigned32, 
		smscRtrImiRecallQueues	 Unsigned32, 
		smscRtrIdiRecallQelem	 Unsigned32, 
		smscRtrIdiRecallQueues	 Unsigned32, 
		smscRtrIosRecallQelem	 Unsigned32, 
		smscRtrIosRecallQueues	 Unsigned32, 
		smscRtrLogRecallQelem	 Unsigned32, 
		smscRtrLogRecallQueues	 Unsigned32, 
		smscRtrTrcreqDiscarded	 Unsigned32, 
		smscRtrDummyStatistic	 Unsigned32
	}

smscRtrName  OBJECT-TYPE
	SYNTAX  DisplayString
	MAX-ACCESS  read-only
	STATUS   current
	DESCRIPTION
		"Identifies the name of the entity."
   ::= {rtrInstanceEntry 1 }

smscRtrState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { rtrInstanceEntry 2 }


smscRtrLastupdate OBJECT-TYPE
		SYNTAX	TimeTicks
		MAX-ACCESS read-only
		STATUS current
		DESCRIPTION
			"Value which reflects the last time the entities fields have been updated"
	::= { rtrInstanceEntry	3 }

smscRtrNode  OBJECT-TYPE
	SYNTAX  DisplayString
	MAX-ACCESS  read-only
	STATUS   current
	DESCRIPTION
		"Identifies the node the entity is running on."
   ::= {rtrInstanceEntry 4 }

smscRtrMsgReceived OBJECT-TYPE
		SYNTAX	Unsigned32
		MAX-ACCESS read-only
		STATUS current
		DESCRIPTION
			"Received messages"
	::= { rtrInstanceEntry	5 }

smscRtrMsgRejected OBJECT-TYPE
		SYNTAX	Unsigned32
		MAX-ACCESS read-only
		STATUS current
		DESCRIPTION
			"Received messages and rejected"
	::= { rtrInstanceEntry	6 }

smscRtrMsgTransmitted OBJECT-TYPE
		SYNTAX	Unsigned32
		MAX-ACCESS read-only
		STATUS current
		DESCRIPTION
			"Transmitted messages"
	::= { rtrInstanceEntry	7 }

smscRtrMsgFailed OBJECT-TYPE
		SYNTAX	Unsigned32
		MAX-ACCESS read-only
		STATUS current
		DESCRIPTION
			"Messages that failed on sending"
	::= { rtrInstanceEntry	8 }

smscRtrQelemUsed OBJECT-TYPE
		SYNTAX	Unsigned32
		MAX-ACCESS read-only
		STATUS current
		DESCRIPTION
			"Number of elements in internal queues"
	::= { rtrInstanceEntry	9 }

smscRtrQelemInProcqueue OBJECT-TYPE
		SYNTAX	Unsigned32
		MAX-ACCESS read-only
		STATUS current
		DESCRIPTION
			"Number of elements used in process queue"
	::= { rtrInstanceEntry	10 }

smscRtrQelemInExpqueue OBJECT-TYPE
		SYNTAX	Unsigned32
		MAX-ACCESS read-only
		STATUS current
		DESCRIPTION
			"Number of elements used in expedited queue"
	::= { rtrInstanceEntry	11 }

smscRtrNrTimersRunning OBJECT-TYPE
		SYNTAX	Unsigned32
		MAX-ACCESS read-only
		STATUS current
		DESCRIPTION
			"Total number of timers running"
	::= { rtrInstanceEntry	12 }

smscRtrNrSystemTimers OBJECT-TYPE
		SYNTAX	Unsigned32
		MAX-ACCESS read-only
		STATUS current
		DESCRIPTION
			"Number of system timers running"
	::= { rtrInstanceEntry	13 }

smscRtrImiRecallQelem OBJECT-TYPE
		SYNTAX	Unsigned32
		MAX-ACCESS read-only
		STATUS current
		DESCRIPTION
			"Number of IMI recall-queue elements used"
	::= { rtrInstanceEntry	14 }

smscRtrImiRecallQueues OBJECT-TYPE
		SYNTAX	Unsigned32
		MAX-ACCESS read-only
		STATUS current
		DESCRIPTION
			"Number of IMI-recall-queues used"
	::= { rtrInstanceEntry	15 }

smscRtrIdiRecallQelem OBJECT-TYPE
		SYNTAX	Unsigned32
		MAX-ACCESS read-only
		STATUS current
		DESCRIPTION
			"Number of IDI recall-queue elements used"
	::= { rtrInstanceEntry	16 }

smscRtrIdiRecallQueues OBJECT-TYPE
		SYNTAX	Unsigned32
		MAX-ACCESS read-only
		STATUS current
		DESCRIPTION
			"Number of IDI recall-queues used"
	::= { rtrInstanceEntry	17 }

smscRtrIosRecallQelem OBJECT-TYPE
		SYNTAX	Unsigned32
		MAX-ACCESS read-only
		STATUS current
		DESCRIPTION
			"Number of IOS recall-queue elements used"
	::= { rtrInstanceEntry	18 }

smscRtrIosRecallQueues OBJECT-TYPE
		SYNTAX	Unsigned32
		MAX-ACCESS read-only
		STATUS current
		DESCRIPTION
			"Number of IOS recall-queues used"
	::= { rtrInstanceEntry	19 }

smscRtrLogRecallQelem OBJECT-TYPE
		SYNTAX	Unsigned32
		MAX-ACCESS read-only
		STATUS current
		DESCRIPTION
			"Number of LOG recall-queue elements used"
	::= { rtrInstanceEntry	20 }

smscRtrLogRecallQueues OBJECT-TYPE
		SYNTAX	Unsigned32
		MAX-ACCESS read-only
		STATUS current
		DESCRIPTION
			"Number of LOG recall-queues used"
	::= { rtrInstanceEntry	21 }

smscRtrTrcreqDiscarded OBJECT-TYPE
		SYNTAX	Unsigned32
		MAX-ACCESS read-only
		STATUS current
		DESCRIPTION
			"Number of trace requests discarded"
	::= { rtrInstanceEntry	22 }

smscRtrDummyStatistic OBJECT-TYPE
		SYNTAX	Unsigned32
		MAX-ACCESS read-only
		STATUS current
		DESCRIPTION
			"No statistical counters"
	::= { rtrInstanceEntry	23 }



-- end of RTR description.
-- --------------------------------------


-- --------------------------------------
-- Class RAS
-- 
smscRas OBJECT-TYPE
	SYNTAX  SEQUENCE OF RasInstanceEntry
	MAX-ACCESS  not-accessible
	STATUS  current
	DESCRIPTION
		"Mapping table for SMSC RAS entities."
   ::= { smscClassServer   11  }

rasInstanceEntry  OBJECT-TYPE
	SYNTAX RasInstanceEntry
	MAX-ACCESS  not-accessible
	STATUS  current
	DESCRIPTION
		"An entry (row) in the entityInstanceTable."
	INDEX { IMPLIED smscRasName }
   ::= { smscRas 1 }

RasInstanceEntry ::= SEQUENCE {
		smscRasName     DisplayString,
		smscRasState   INTEGER,
		smscRasLastupdate   TimeTicks,
		smscRasNode	   DisplayString, 
		smscRasMsgReceived	 Unsigned32, 
		smscRasMsgRejected	 Unsigned32, 
		smscRasMsgTransmitted	 Unsigned32, 
		smscRasMsgFailed	 Unsigned32, 
		smscRasConTot	 Unsigned32, 
		smscRasConIn	 Unsigned32, 
		smscRasConInAcc	 Unsigned32, 
		smscRasConOut	 Unsigned32, 
		smscRasConOutAcc	 Unsigned32, 
		smscRasConOutBusy	 Unsigned32, 
		smscRasConOutNoAnswer	 Unsigned32, 
		smscRasConOutOtherFail	 Unsigned32, 
		smscRasConTimeCumulative	 Unsigned32, 
		smscRasQelemUsed	 Unsigned32, 
		smscRasQelemInProcqueue	 Unsigned32, 
		smscRasQelemInExpqueue	 Unsigned32, 
		smscRasNrTimersRunning	 Unsigned32, 
		smscRasNrSystemTimers	 Unsigned32, 
		smscRasImiRecallQelem	 Unsigned32, 
		smscRasImiRecallQueues	 Unsigned32, 
		smscRasIdiRecallQelem	 Unsigned32, 
		smscRasIdiRecallQueues	 Unsigned32, 
		smscRasIosRecallQelem	 Unsigned32, 
		smscRasIosRecallQueues	 Unsigned32, 
		smscRasLogRecallQelem	 Unsigned32, 
		smscRasLogRecallQueues	 Unsigned32, 
		smscRasTrcreqDiscarded	 Unsigned32
	}

smscRasName  OBJECT-TYPE
	SYNTAX  DisplayString
	MAX-ACCESS  read-only
	STATUS   current
	DESCRIPTION
		"Identifies the name of the entity."
   ::= {rasInstanceEntry 1 }

smscRasState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { rasInstanceEntry 2 }


smscRasLastupdate OBJECT-TYPE
		SYNTAX	TimeTicks
		MAX-ACCESS read-only
		STATUS current
		DESCRIPTION
			"Value which reflects the last time the entities fields have been updated"
	::= { rasInstanceEntry	3 }

smscRasNode  OBJECT-TYPE
	SYNTAX  DisplayString
	MAX-ACCESS  read-only
	STATUS   current
	DESCRIPTION
		"Identifies the node the entity is running on."
   ::= {rasInstanceEntry 4 }

smscRasMsgReceived OBJECT-TYPE
		SYNTAX	Unsigned32
		MAX-ACCESS read-only
		STATUS current
		DESCRIPTION
			"Received messages"
	::= { rasInstanceEntry	5 }

smscRasMsgRejected OBJECT-TYPE
		SYNTAX	Unsigned32
		MAX-ACCESS read-only
		STATUS current
		DESCRIPTION
			"Received messages and rejected"
	::= { rasInstanceEntry	6 }

smscRasMsgTransmitted OBJECT-TYPE
		SYNTAX	Unsigned32
		MAX-ACCESS read-only
		STATUS current
		DESCRIPTION
			"Transmitted messages"
	::= { rasInstanceEntry	7 }

smscRasMsgFailed OBJECT-TYPE
		SYNTAX	Unsigned32
		MAX-ACCESS read-only
		STATUS current
		DESCRIPTION
			"Messages that failed on sending"
	::= { rasInstanceEntry	8 }

smscRasConTot OBJECT-TYPE
		SYNTAX	Unsigned32
		MAX-ACCESS read-only
		STATUS current
		DESCRIPTION
			"Network connections"
	::= { rasInstanceEntry	9 }

smscRasConIn OBJECT-TYPE
		SYNTAX	Unsigned32
		MAX-ACCESS read-only
		STATUS current
		DESCRIPTION
			"Received network connections"
	::= { rasInstanceEntry	10 }

smscRasConInAcc OBJECT-TYPE
		SYNTAX	Unsigned32
		MAX-ACCESS read-only
		STATUS current
		DESCRIPTION
			"Accepted received network connections"
	::= { rasInstanceEntry	11 }

smscRasConOut OBJECT-TYPE
		SYNTAX	Unsigned32
		MAX-ACCESS read-only
		STATUS current
		DESCRIPTION
			"Initiated network connections"
	::= { rasInstanceEntry	12 }

smscRasConOutAcc OBJECT-TYPE
		SYNTAX	Unsigned32
		MAX-ACCESS read-only
		STATUS current
		DESCRIPTION
			"Accepted initiated network connections"
	::= { rasInstanceEntry	13 }

smscRasConOutBusy OBJECT-TYPE
		SYNTAX	Unsigned32
		MAX-ACCESS read-only
		STATUS current
		DESCRIPTION
			"Initiated network connections resulting in busy tone"
	::= { rasInstanceEntry	14 }

smscRasConOutNoAnswer OBJECT-TYPE
		SYNTAX	Unsigned32
		MAX-ACCESS read-only
		STATUS current
		DESCRIPTION
			"Initiated network connections resulting in no answer tone"
	::= { rasInstanceEntry	15 }

smscRasConOutOtherFail OBJECT-TYPE
		SYNTAX	Unsigned32
		MAX-ACCESS read-only
		STATUS current
		DESCRIPTION
			"Initiated network connections resulting in other failures"
	::= { rasInstanceEntry	16 }

smscRasConTimeCumulative OBJECT-TYPE
		SYNTAX	Unsigned32
		MAX-ACCESS read-only
		STATUS current
		DESCRIPTION
			"Accumulated session duration time"
	::= { rasInstanceEntry	17 }

smscRasQelemUsed OBJECT-TYPE
		SYNTAX	Unsigned32
		MAX-ACCESS read-only
		STATUS current
		DESCRIPTION
			"Number of elements in internal queues"
	::= { rasInstanceEntry	18 }

smscRasQelemInProcqueue OBJECT-TYPE
		SYNTAX	Unsigned32
		MAX-ACCESS read-only
		STATUS current
		DESCRIPTION
			"Number of elements used in process queue"
	::= { rasInstanceEntry	19 }

smscRasQelemInExpqueue OBJECT-TYPE
		SYNTAX	Unsigned32
		MAX-ACCESS read-only
		STATUS current
		DESCRIPTION
			"Number of elements used in expedited queue"
	::= { rasInstanceEntry	20 }

smscRasNrTimersRunning OBJECT-TYPE
		SYNTAX	Unsigned32
		MAX-ACCESS read-only
		STATUS current
		DESCRIPTION
			"Total number of timers running"
	::= { rasInstanceEntry	21 }

smscRasNrSystemTimers OBJECT-TYPE
		SYNTAX	Unsigned32
		MAX-ACCESS read-only
		STATUS current
		DESCRIPTION
			"Number of system timers running"
	::= { rasInstanceEntry	22 }

smscRasImiRecallQelem OBJECT-TYPE
		SYNTAX	Unsigned32
		MAX-ACCESS read-only
		STATUS current
		DESCRIPTION
			"Number of IMI recall-queue elements used"
	::= { rasInstanceEntry	23 }

smscRasImiRecallQueues OBJECT-TYPE
		SYNTAX	Unsigned32
		MAX-ACCESS read-only
		STATUS current
		DESCRIPTION
			"Number of IMI-recall-queues used"
	::= { rasInstanceEntry	24 }

smscRasIdiRecallQelem OBJECT-TYPE
		SYNTAX	Unsigned32
		MAX-ACCESS read-only
		STATUS current
		DESCRIPTION
			"Number of IDI recall-queue elements used"
	::= { rasInstanceEntry	25 }

smscRasIdiRecallQueues OBJECT-TYPE
		SYNTAX	Unsigned32
		MAX-ACCESS read-only
		STATUS current
		DESCRIPTION
			"Number of IDI recall-queues used"
	::= { rasInstanceEntry	26 }

smscRasIosRecallQelem OBJECT-TYPE
		SYNTAX	Unsigned32
		MAX-ACCESS read-only
		STATUS current
		DESCRIPTION
			"Number of IOS recall-queue elements used"
	::= { rasInstanceEntry	27 }

smscRasIosRecallQueues OBJECT-TYPE
		SYNTAX	Unsigned32
		MAX-ACCESS read-only
		STATUS current
		DESCRIPTION
			"Number of IOS recall-queues used"
	::= { rasInstanceEntry	28 }

smscRasLogRecallQelem OBJECT-TYPE
		SYNTAX	Unsigned32
		MAX-ACCESS read-only
		STATUS current
		DESCRIPTION
			"Number of LOG recall-queue elements used"
	::= { rasInstanceEntry	29 }

smscRasLogRecallQueues OBJECT-TYPE
		SYNTAX	Unsigned32
		MAX-ACCESS read-only
		STATUS current
		DESCRIPTION
			"Number of LOG recall-queues used"
	::= { rasInstanceEntry	30 }

smscRasTrcreqDiscarded OBJECT-TYPE
		SYNTAX	Unsigned32
		MAX-ACCESS read-only
		STATUS current
		DESCRIPTION
			"Number of trace requests discarded"
	::= { rasInstanceEntry	31 }



-- end of RAS description.
-- --------------------------------------


-- --------------------------------------
-- Class GHLR
-- 
smscGhlr OBJECT-TYPE
	SYNTAX  SEQUENCE OF GhlrInstanceEntry
	MAX-ACCESS  not-accessible
	STATUS  current
	DESCRIPTION
		"Mapping table for SMSC GHLR entities."
   ::= { smscClassServer   12  }

ghlrInstanceEntry  OBJECT-TYPE
	SYNTAX GhlrInstanceEntry
	MAX-ACCESS  not-accessible
	STATUS  current
	DESCRIPTION
		"An entry (row) in the entityInstanceTable."
	INDEX { IMPLIED smscGhlrName }
   ::= { smscGhlr 1 }

GhlrInstanceEntry ::= SEQUENCE {
		smscGhlrName     DisplayString,
		smscGhlrState   INTEGER,
		smscGhlrLastupdate   TimeTicks,
		smscGhlrNode	   DisplayString, 
		smscGhlrMsgReceived	 Unsigned32, 
		smscGhlrMsgRejected	 Unsigned32, 
		smscGhlrMsgTransmitted	 Unsigned32, 
		smscGhlrMsgFailed	 Unsigned32, 
		smscGhlrDialogues	 Unsigned32, 
		smscGhlrSessionsPending	 Unsigned32, 
		smscGhlrDialoguesPending	 Unsigned32, 
		smscGhlrSystemFailure	 Unsigned32, 
		smscGhlrUnexpectedDataValue	 Unsigned32, 
		smscGhlrQelemUsed	 Unsigned32, 
		smscGhlrQelemInProcqueue	 Unsigned32, 
		smscGhlrQelemInExpqueue	 Unsigned32, 
		smscGhlrNrTimersRunning	 Unsigned32, 
		smscGhlrNrSystemTimers	 Unsigned32, 
		smscGhlrImiRecallQelem	 Unsigned32, 
		smscGhlrImiRecallQueues	 Unsigned32, 
		smscGhlrIdiRecallQelem	 Unsigned32, 
		smscGhlrIdiRecallQueues	 Unsigned32, 
		smscGhlrIosRecallQelem	 Unsigned32, 
		smscGhlrIosRecallQueues	 Unsigned32, 
		smscGhlrLogRecallQelem	 Unsigned32, 
		smscGhlrLogRecallQueues	 Unsigned32, 
		smscGhlrTrcreqDiscarded	 Unsigned32, 
		smscGhlrMapDiaQueueFailed	 Unsigned32, 
		smscGhlrMapDiaFree	 Unsigned32, 
		smscGhlrMapDiaInUse	 Unsigned32, 
		smscGhlrMapDiaMaxUsed	 Unsigned32, 
		smscGhlrMapOperFree	 Unsigned32, 
		smscGhlrMapOperInUse	 Unsigned32, 
		smscGhlrMapOperMaxUsed	 Unsigned32, 
		smscGhlrMapBufFree	 Unsigned32, 
		smscGhlrMapBufInUse	 Unsigned32, 
		smscGhlrMapBufMaxUsed	 Unsigned32, 
		smscGhlrRoutInfoOk	 Unsigned32, 
		smscGhlrRoutInfoFail	 Unsigned32, 
		smscGhlrDelStatOk	 Unsigned32, 
		smscGhlrDelStatFail	 Unsigned32, 
		smscGhlrMapOpenRej	 Unsigned32, 
		smscGhlrMapAbort	 Unsigned32, 
		smscGhlrDataMissing	 Unsigned32, 
		smscGhlrUnknownSubscriber	 Unsigned32, 
		smscGhlrMsgWaitingListFull	 Unsigned32, 
		smscGhlrMapDiaAllocFailed	 Unsigned32, 
		smscGhlrMapOperAllocFailed	 Unsigned32, 
		smscGhlrMapBufAllocFailed	 Unsigned32, 
		smscGhlrMapProtoErr	 Unsigned32, 
		smscGhlrMapPrvDecErr	 Unsigned32, 
		smscGhlrMapPduDecErr	 Unsigned32, 
		smscGhlrMapOpcodeErr	 Unsigned32, 
		smscGhlrMapInvokeErr	 Unsigned32, 
		smscGhlrMapInvAppCtxt	 Unsigned32, 
		smscGhlrMapAppCtxtMism	 Unsigned32, 
		smscGhlrTcapBeginRcvd	 Unsigned32, 
		smscGhlrTcapContRcvd	 Unsigned32, 
		smscGhlrTcapEndRcvd	 Unsigned32, 
		smscGhlrTcapBeginSnt	 Unsigned32, 
		smscGhlrTcapContSnt	 Unsigned32, 
		smscGhlrTcapEndSnt	 Unsigned32, 
		smscGhlrTcapFailedSent	 Unsigned32, 
		smscGhlrTcapTransDisc	 Unsigned32, 
		smscGhlrTcapMsgDisc	 Unsigned32, 
		smscGhlrTcapUnknMsgRcvd	 Unsigned32, 
		smscGhlrTcapNoticeRcvd	 Unsigned32, 
		smscGhlrTcapAbtRcvd	 Unsigned32, 
		smscGhlrTcapAbtUnrecmtRcvd	 Unsigned32, 
		smscGhlrTcapAbtTranpRcvd	 Unsigned32, 
		smscGhlrTcapAbtBftpRcvd	 Unsigned32, 
		smscGhlrTcapAbtUnrecidRcvd	 Unsigned32, 
		smscGhlrTcapAbtReslimitRcvd	 Unsigned32, 
		smscGhlrTcapAbtAbnormRcvd	 Unsigned32, 
		smscGhlrTcapAbtSnt	 Unsigned32, 
		smscGhlrTcapAbtUnrecmtSnt	 Unsigned32, 
		smscGhlrTcapAbtTranpSnt	 Unsigned32, 
		smscGhlrTcapAbtBftpSnt	 Unsigned32, 
		smscGhlrTcapAbtUnrecidSnt	 Unsigned32, 
		smscGhlrTcapAbtReslimitSnt	 Unsigned32, 
		smscGhlrTcapAbtAbnormSnt	 Unsigned32, 
		smscGhlrTcapUabtRcvd	 Unsigned32, 
		smscGhlrTcapUabtSnt	 Unsigned32, 
		smscGhlrTcapInvkRcvd	 Unsigned32, 
		smscGhlrTcapInvkSnt	 Unsigned32, 
		smscGhlrTcapResLastRcvd	 Unsigned32, 
		smscGhlrTcapResNolastRcvd	 Unsigned32, 
		smscGhlrTcapResLastSnt	 Unsigned32, 
		smscGhlrTcapResNolastSnt	 Unsigned32, 
		smscGhlrTcapErrorRcvd	 Unsigned32, 
		smscGhlrTcapErrorSnt	 Unsigned32, 
		smscGhlrTcapRjctSnt	 Unsigned32, 
		smscGhlrTcapRjctRcvd	 Unsigned32, 
		smscGhlrTcapRjctUnrecRcvd	 Unsigned32, 
		smscGhlrTcapRjctMistypeRcvd	 Unsigned32, 
		smscGhlrTcapRjctBadsRcvd	 Unsigned32, 
		smscGhlrTcapRjctUnrLidRcvd	 Unsigned32, 
		smscGhlrTcapRjctUiRrRcvd	 Unsigned32, 
		smscGhlrTcapRjctUiReRcvd	 Unsigned32, 
		smscGhlrTcapRjctUnxpRrRcvd	 Unsigned32, 
		smscGhlrTcapRjctUnxpReRcvd	 Unsigned32, 
		smscGhlrTcapRjctDupIidRcvd	 Unsigned32, 
		smscGhlrTcapPrbUnrecOpRcvd	 Unsigned32, 
		smscGhlrTcapPrbMistypeRcvd	 Unsigned32, 
		smscGhlrTcapPrbReslimitRcvd	 Unsigned32, 
		smscGhlrTcapPrbInitrelRcvd	 Unsigned32, 
		smscGhlrTcapPrbUnlRespRcvd	 Unsigned32, 
		smscGhlrTcapPrbUnlOpRcvd	 Unsigned32, 
		smscGhlrTcapPrbMtRrRcvd	 Unsigned32, 
		smscGhlrTcapPrbMtReRcvd	 Unsigned32, 
		smscGhlrTcapUserUnrecRcvd	 Unsigned32, 
		smscGhlrTcapUserUnxpRcvd	 Unsigned32, 
		smscGhlrTcapActiveDialog	 Unsigned32, 
		smscGhlrTcapInitiatedDialog	 Unsigned32, 
		smscGhlrTcapActiveDlgs	 Unsigned32, 
		smscGhlrTcapInitiatedDlgs	 Unsigned32
	}

smscGhlrName  OBJECT-TYPE
	SYNTAX  DisplayString
	MAX-ACCESS  read-only
	STATUS   current
	DESCRIPTION
		"Identifies the name of the entity."
   ::= {ghlrInstanceEntry 1 }

smscGhlrState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { ghlrInstanceEntry 2 }


smscGhlrLastupdate OBJECT-TYPE
		SYNTAX	TimeTicks
		MAX-ACCESS read-only
		STATUS current
		DESCRIPTION
			"Value which reflects the last time the entities fields have been updated"
	::= { ghlrInstanceEntry	3 }

smscGhlrNode  OBJECT-TYPE
	SYNTAX  DisplayString
	MAX-ACCESS  read-only
	STATUS   current
	DESCRIPTION
		"Identifies the node the entity is running on."
   ::= {ghlrInstanceEntry 4 }

smscGhlrMsgReceived OBJECT-TYPE
		SYNTAX	Unsigned32
		MAX-ACCESS read-only
		STATUS current
		DESCRIPTION
			"Received messages"
	::= { ghlrInstanceEntry	5 }

smscGhlrMsgRejected OBJECT-TYPE
		SYNTAX	Unsigned32
		MAX-ACCESS read-only
		STATUS current
		DESCRIPTION
			"Received messages and rejected"
	::= { ghlrInstanceEntry	6 }

smscGhlrMsgTransmitted OBJECT-TYPE
		SYNTAX	Unsigned32
		MAX-ACCESS read-only
		STATUS current
		DESCRIPTION
			"Transmitted messages"
	::= { ghlrInstanceEntry	7 }

smscGhlrMsgFailed OBJECT-TYPE
		SYNTAX	Unsigned32
		MAX-ACCESS read-only
		STATUS current
		DESCRIPTION
			"Messages that failed on sending"
	::= { ghlrInstanceEntry	8 }

smscGhlrDialogues OBJECT-TYPE
		SYNTAX	Unsigned32
		MAX-ACCESS read-only
		STATUS current
		DESCRIPTION
			"Number of dialogues"
	::= { ghlrInstanceEntry	9 }

smscGhlrSessionsPending OBJECT-TYPE
		SYNTAX	Unsigned32
		MAX-ACCESS read-only
		STATUS current
		DESCRIPTION
			"Number of sessions (currently) pending"
	::= { ghlrInstanceEntry	10 }

smscGhlrDialoguesPending OBJECT-TYPE
		SYNTAX	Unsigned32
		MAX-ACCESS read-only
		STATUS current
		DESCRIPTION
			"Number of dialogues (currently) pending"
	::= { ghlrInstanceEntry	11 }

smscGhlrSystemFailure OBJECT-TYPE
		SYNTAX	Unsigned32
		MAX-ACCESS read-only
		STATUS current
		DESCRIPTION
			"Number of System Failure errors"
	::= { ghlrInstanceEntry	12 }

smscGhlrUnexpectedDataValue OBJECT-TYPE
		SYNTAX	Unsigned32
		MAX-ACCESS read-only
		STATUS current
		DESCRIPTION
			"Number of Unexpected Data Value errors"
	::= { ghlrInstanceEntry	13 }

smscGhlrQelemUsed OBJECT-TYPE
		SYNTAX	Unsigned32
		MAX-ACCESS read-only
		STATUS current
		DESCRIPTION
			"Number of elements in internal queues"
	::= { ghlrInstanceEntry	14 }

smscGhlrQelemInProcqueue OBJECT-TYPE
		SYNTAX	Unsigned32
		MAX-ACCESS read-only
		STATUS current
		DESCRIPTION
			"Number of elements used in process queue"
	::= { ghlrInstanceEntry	15 }

smscGhlrQelemInExpqueue OBJECT-TYPE
		SYNTAX	Unsigned32
		MAX-ACCESS read-only
		STATUS current
		DESCRIPTION
			"Number of elements used in expedited queue"
	::= { ghlrInstanceEntry	16 }

smscGhlrNrTimersRunning OBJECT-TYPE
		SYNTAX	Unsigned32
		MAX-ACCESS read-only
		STATUS current
		DESCRIPTION
			"Total number of timers running"
	::= { ghlrInstanceEntry	17 }

smscGhlrNrSystemTimers OBJECT-TYPE
		SYNTAX	Unsigned32
		MAX-ACCESS read-only
		STATUS current
		DESCRIPTION
			"Number of system timers running"
	::= { ghlrInstanceEntry	18 }

smscGhlrImiRecallQelem OBJECT-TYPE
		SYNTAX	Unsigned32
		MAX-ACCESS read-only
		STATUS current
		DESCRIPTION
			"Number of IMI recall-queue elements used"
	::= { ghlrInstanceEntry	19 }

smscGhlrImiRecallQueues OBJECT-TYPE
		SYNTAX	Unsigned32
		MAX-ACCESS read-only
		STATUS current
		DESCRIPTION
			"Number of IMI-recall-queues used"
	::= { ghlrInstanceEntry	20 }

smscGhlrIdiRecallQelem OBJECT-TYPE
		SYNTAX	Unsigned32
		MAX-ACCESS read-only
		STATUS current
		DESCRIPTION
			"Number of IDI recall-queue elements used"
	::= { ghlrInstanceEntry	21 }

smscGhlrIdiRecallQueues OBJECT-TYPE
		SYNTAX	Unsigned32
		MAX-ACCESS read-only
		STATUS current
		DESCRIPTION
			"Number of IDI recall-queues used"
	::= { ghlrInstanceEntry	22 }

smscGhlrIosRecallQelem OBJECT-TYPE
		SYNTAX	Unsigned32
		MAX-ACCESS read-only
		STATUS current
		DESCRIPTION
			"Number of IOS recall-queue elements used"
	::= { ghlrInstanceEntry	23 }

smscGhlrIosRecallQueues OBJECT-TYPE
		SYNTAX	Unsigned32
		MAX-ACCESS read-only
		STATUS current
		DESCRIPTION
			"Number of IOS recall-queues used"
	::= { ghlrInstanceEntry	24 }

smscGhlrLogRecallQelem OBJECT-TYPE
		SYNTAX	Unsigned32
		MAX-ACCESS read-only
		STATUS current
		DESCRIPTION
			"Number of LOG recall-queue elements used"
	::= { ghlrInstanceEntry	25 }

smscGhlrLogRecallQueues OBJECT-TYPE
		SYNTAX	Unsigned32
		MAX-ACCESS read-only
		STATUS current
		DESCRIPTION
			"Number of LOG recall-queues used"
	::= { ghlrInstanceEntry	26 }

smscGhlrTrcreqDiscarded OBJECT-TYPE
		SYNTAX	Unsigned32
		MAX-ACCESS read-only
		STATUS current
		DESCRIPTION
			"Number of trace requests discarded"
	::= { ghlrInstanceEntry	27 }

smscGhlrMapDiaQueueFailed OBJECT-TYPE
		SYNTAX	Unsigned32
		MAX-ACCESS read-only
		STATUS current
		DESCRIPTION
			"Number of MAP dialogue queue failures"
	::= { ghlrInstanceEntry	28 }

smscGhlrMapDiaFree OBJECT-TYPE
		SYNTAX	Unsigned32
		MAX-ACCESS read-only
		STATUS current
		DESCRIPTION
			"Number of free MAP dialogues"
	::= { ghlrInstanceEntry	29 }

smscGhlrMapDiaInUse OBJECT-TYPE
		SYNTAX	Unsigned32
		MAX-ACCESS read-only
		STATUS current
		DESCRIPTION
			"Number of MAP dialogues in use"
	::= { ghlrInstanceEntry	30 }

smscGhlrMapDiaMaxUsed OBJECT-TYPE
		SYNTAX	Unsigned32
		MAX-ACCESS read-only
		STATUS current
		DESCRIPTION
			"Maximum number of MAP dialogues used"
	::= { ghlrInstanceEntry	31 }

smscGhlrMapOperFree OBJECT-TYPE
		SYNTAX	Unsigned32
		MAX-ACCESS read-only
		STATUS current
		DESCRIPTION
			"Number of free MAP operations"
	::= { ghlrInstanceEntry	32 }

smscGhlrMapOperInUse OBJECT-TYPE
		SYNTAX	Unsigned32
		MAX-ACCESS read-only
		STATUS current
		DESCRIPTION
			"Number of MAP operations in use"
	::= { ghlrInstanceEntry	33 }

smscGhlrMapOperMaxUsed OBJECT-TYPE
		SYNTAX	Unsigned32
		MAX-ACCESS read-only
		STATUS current
		DESCRIPTION
			"Maximum number of MAP operations used"
	::= { ghlrInstanceEntry	34 }

smscGhlrMapBufFree OBJECT-TYPE
		SYNTAX	Unsigned32
		MAX-ACCESS read-only
		STATUS current
		DESCRIPTION
			"Number of free MAP buffers"
	::= { ghlrInstanceEntry	35 }

smscGhlrMapBufInUse OBJECT-TYPE
		SYNTAX	Unsigned32
		MAX-ACCESS read-only
		STATUS current
		DESCRIPTION
			"Number of MAP buffers in use"
	::= { ghlrInstanceEntry	36 }

smscGhlrMapBufMaxUsed OBJECT-TYPE
		SYNTAX	Unsigned32
		MAX-ACCESS read-only
		STATUS current
		DESCRIPTION
			"Maximum number of MAP buffers used"
	::= { ghlrInstanceEntry	37 }

smscGhlrRoutInfoOk OBJECT-TYPE
		SYNTAX	Unsigned32
		MAX-ACCESS read-only
		STATUS current
		DESCRIPTION
			"Number of succesful Routing Info requests"
	::= { ghlrInstanceEntry	38 }

smscGhlrRoutInfoFail OBJECT-TYPE
		SYNTAX	Unsigned32
		MAX-ACCESS read-only
		STATUS current
		DESCRIPTION
			"Number of failed Routing Info requests"
	::= { ghlrInstanceEntry	39 }

smscGhlrDelStatOk OBJECT-TYPE
		SYNTAX	Unsigned32
		MAX-ACCESS read-only
		STATUS current
		DESCRIPTION
			"Number of successful Delivery Status Reports"
	::= { ghlrInstanceEntry	40 }

smscGhlrDelStatFail OBJECT-TYPE
		SYNTAX	Unsigned32
		MAX-ACCESS read-only
		STATUS current
		DESCRIPTION
			"Number of failed Delivery Status Reports"
	::= { ghlrInstanceEntry	41 }

smscGhlrMapOpenRej OBJECT-TYPE
		SYNTAX	Unsigned32
		MAX-ACCESS read-only
		STATUS current
		DESCRIPTION
			"Number of rejected MAP-OPEN requests"
	::= { ghlrInstanceEntry	42 }

smscGhlrMapAbort OBJECT-TYPE
		SYNTAX	Unsigned32
		MAX-ACCESS read-only
		STATUS current
		DESCRIPTION
			"Number of received MAP-ABORT indications"
	::= { ghlrInstanceEntry	43 }

smscGhlrDataMissing OBJECT-TYPE
		SYNTAX	Unsigned32
		MAX-ACCESS read-only
		STATUS current
		DESCRIPTION
			"Number of Data Missing errors"
	::= { ghlrInstanceEntry	44 }

smscGhlrUnknownSubscriber OBJECT-TYPE
		SYNTAX	Unsigned32
		MAX-ACCESS read-only
		STATUS current
		DESCRIPTION
			"Number of Unknown Subscriber errors"
	::= { ghlrInstanceEntry	45 }

smscGhlrMsgWaitingListFull OBJECT-TYPE
		SYNTAX	Unsigned32
		MAX-ACCESS read-only
		STATUS current
		DESCRIPTION
			"Number of Message Waiting List Full errors"
	::= { ghlrInstanceEntry	46 }

smscGhlrMapDiaAllocFailed OBJECT-TYPE
		SYNTAX	Unsigned32
		MAX-ACCESS read-only
		STATUS current
		DESCRIPTION
			"Number of MAP dialogue allocation failures"
	::= { ghlrInstanceEntry	47 }

smscGhlrMapOperAllocFailed OBJECT-TYPE
		SYNTAX	Unsigned32
		MAX-ACCESS read-only
		STATUS current
		DESCRIPTION
			"Number of MAP operation allocation failures"
	::= { ghlrInstanceEntry	48 }

smscGhlrMapBufAllocFailed OBJECT-TYPE
		SYNTAX	Unsigned32
		MAX-ACCESS read-only
		STATUS current
		DESCRIPTION
			"Number of MAP buffer allocation failures"
	::= { ghlrInstanceEntry	49 }

smscGhlrMapProtoErr OBJECT-TYPE
		SYNTAX	Unsigned32
		MAX-ACCESS read-only
		STATUS current
		DESCRIPTION
			"Number of MAP protocol errors"
	::= { ghlrInstanceEntry	50 }

smscGhlrMapPrvDecErr OBJECT-TYPE
		SYNTAX	Unsigned32
		MAX-ACCESS read-only
		STATUS current
		DESCRIPTION
			"Number of MAP provider decode errors"
	::= { ghlrInstanceEntry	51 }

smscGhlrMapPduDecErr OBJECT-TYPE
		SYNTAX	Unsigned32
		MAX-ACCESS read-only
		STATUS current
		DESCRIPTION
			"Number of MAP PDU decode errors"
	::= { ghlrInstanceEntry	52 }

smscGhlrMapOpcodeErr OBJECT-TYPE
		SYNTAX	Unsigned32
		MAX-ACCESS read-only
		STATUS current
		DESCRIPTION
			"Number of invalid MAP operation codes received"
	::= { ghlrInstanceEntry	53 }

smscGhlrMapInvokeErr OBJECT-TYPE
		SYNTAX	Unsigned32
		MAX-ACCESS read-only
		STATUS current
		DESCRIPTION
			"Number of invalid MAP invoke IDs received"
	::= { ghlrInstanceEntry	54 }

smscGhlrMapInvAppCtxt OBJECT-TYPE
		SYNTAX	Unsigned32
		MAX-ACCESS read-only
		STATUS current
		DESCRIPTION
			"Invalid MAP application contexts received"
	::= { ghlrInstanceEntry	55 }

smscGhlrMapAppCtxtMism OBJECT-TYPE
		SYNTAX	Unsigned32
		MAX-ACCESS read-only
		STATUS current
		DESCRIPTION
			"Non-matching MAP application contexts received"
	::= { ghlrInstanceEntry	56 }

smscGhlrTcapBeginRcvd OBJECT-TYPE
		SYNTAX	Unsigned32
		MAX-ACCESS read-only
		STATUS current
		DESCRIPTION
			"Number of Begin Dialogue transactions received"
	::= { ghlrInstanceEntry	57 }

smscGhlrTcapContRcvd OBJECT-TYPE
		SYNTAX	Unsigned32
		MAX-ACCESS read-only
		STATUS current
		DESCRIPTION
			"Number of Continue transactions received"
	::= { ghlrInstanceEntry	58 }

smscGhlrTcapEndRcvd OBJECT-TYPE
		SYNTAX	Unsigned32
		MAX-ACCESS read-only
		STATUS current
		DESCRIPTION
			"Number of End transactions received"
	::= { ghlrInstanceEntry	59 }

smscGhlrTcapBeginSnt OBJECT-TYPE
		SYNTAX	Unsigned32
		MAX-ACCESS read-only
		STATUS current
		DESCRIPTION
			"Number of Begin Dialogue transactions sent"
	::= { ghlrInstanceEntry	60 }

smscGhlrTcapContSnt OBJECT-TYPE
		SYNTAX	Unsigned32
		MAX-ACCESS read-only
		STATUS current
		DESCRIPTION
			"Number of Continue transactions sent"
	::= { ghlrInstanceEntry	61 }

smscGhlrTcapEndSnt OBJECT-TYPE
		SYNTAX	Unsigned32
		MAX-ACCESS read-only
		STATUS current
		DESCRIPTION
			"Number of End transactions sent"
	::= { ghlrInstanceEntry	62 }

smscGhlrTcapFailedSent OBJECT-TYPE
		SYNTAX	Unsigned32
		MAX-ACCESS read-only
		STATUS current
		DESCRIPTION
			"Number of Message failed to be sent"
	::= { ghlrInstanceEntry	63 }

smscGhlrTcapTransDisc OBJECT-TYPE
		SYNTAX	Unsigned32
		MAX-ACCESS read-only
		STATUS current
		DESCRIPTION
			"Number of discarded msgs due to transport problem"
	::= { ghlrInstanceEntry	64 }

smscGhlrTcapMsgDisc OBJECT-TYPE
		SYNTAX	Unsigned32
		MAX-ACCESS read-only
		STATUS current
		DESCRIPTION
			"Number of discarded TCAP messages"
	::= { ghlrInstanceEntry	65 }

smscGhlrTcapUnknMsgRcvd OBJECT-TYPE
		SYNTAX	Unsigned32
		MAX-ACCESS read-only
		STATUS current
		DESCRIPTION
			"Number of incorrect or unknown TCAP msgs received"
	::= { ghlrInstanceEntry	66 }

smscGhlrTcapNoticeRcvd OBJECT-TYPE
		SYNTAX	Unsigned32
		MAX-ACCESS read-only
		STATUS current
		DESCRIPTION
			"Number of Notice rcvd"
	::= { ghlrInstanceEntry	67 }

smscGhlrTcapAbtRcvd OBJECT-TYPE
		SYNTAX	Unsigned32
		MAX-ACCESS read-only
		STATUS current
		DESCRIPTION
			"Number of P_ABORT transacs rcvd"
	::= { ghlrInstanceEntry	68 }

smscGhlrTcapAbtUnrecmtRcvd OBJECT-TYPE
		SYNTAX	Unsigned32
		MAX-ACCESS read-only
		STATUS current
		DESCRIPTION
			"Number of P_ABORT transacs rcvd (unrec msg type)"
	::= { ghlrInstanceEntry	69 }

smscGhlrTcapAbtTranpRcvd OBJECT-TYPE
		SYNTAX	Unsigned32
		MAX-ACCESS read-only
		STATUS current
		DESCRIPTION
			"Number of P_ABORT msgs rcvd (inc trans portion)"
	::= { ghlrInstanceEntry	70 }

smscGhlrTcapAbtBftpRcvd OBJECT-TYPE
		SYNTAX	Unsigned32
		MAX-ACCESS read-only
		STATUS current
		DESCRIPTION
			"Number of P_ABORT msgs rcvd (badly formed tp)"
	::= { ghlrInstanceEntry	71 }

smscGhlrTcapAbtUnrecidRcvd OBJECT-TYPE
		SYNTAX	Unsigned32
		MAX-ACCESS read-only
		STATUS current
		DESCRIPTION
			"Number of P_ABORT msgs rcvd (unrec trans id)"
	::= { ghlrInstanceEntry	72 }

smscGhlrTcapAbtReslimitRcvd OBJECT-TYPE
		SYNTAX	Unsigned32
		MAX-ACCESS read-only
		STATUS current
		DESCRIPTION
			"Number of P_ABORT msgs rcvd (resouce limitation)"
	::= { ghlrInstanceEntry	73 }

smscGhlrTcapAbtAbnormRcvd OBJECT-TYPE
		SYNTAX	Unsigned32
		MAX-ACCESS read-only
		STATUS current
		DESCRIPTION
			"Number of P_ABORT msgs rcvd (abnormal dialog)"
	::= { ghlrInstanceEntry	74 }

smscGhlrTcapAbtSnt OBJECT-TYPE
		SYNTAX	Unsigned32
		MAX-ACCESS read-only
		STATUS current
		DESCRIPTION
			"Number of P_ABORT transacs sent"
	::= { ghlrInstanceEntry	75 }

smscGhlrTcapAbtUnrecmtSnt OBJECT-TYPE
		SYNTAX	Unsigned32
		MAX-ACCESS read-only
		STATUS current
		DESCRIPTION
			"Number of P_ABORT transacs sent (unrec msg type)"
	::= { ghlrInstanceEntry	76 }

smscGhlrTcapAbtTranpSnt OBJECT-TYPE
		SYNTAX	Unsigned32
		MAX-ACCESS read-only
		STATUS current
		DESCRIPTION
			"Number of P_ABORT transacs sent (inc trns portion)"
	::= { ghlrInstanceEntry	77 }

smscGhlrTcapAbtBftpSnt OBJECT-TYPE
		SYNTAX	Unsigned32
		MAX-ACCESS read-only
		STATUS current
		DESCRIPTION
			"Number of P_ABORT transacs sent (badly formed tp)"
	::= { ghlrInstanceEntry	78 }

smscGhlrTcapAbtUnrecidSnt OBJECT-TYPE
		SYNTAX	Unsigned32
		MAX-ACCESS read-only
		STATUS current
		DESCRIPTION
			"Number of P_ABORT transacs sent (unrec trns id)"
	::= { ghlrInstanceEntry	79 }

smscGhlrTcapAbtReslimitSnt OBJECT-TYPE
		SYNTAX	Unsigned32
		MAX-ACCESS read-only
		STATUS current
		DESCRIPTION
			"Number of P_ABORT transacs sent (res limitation)"
	::= { ghlrInstanceEntry	80 }

smscGhlrTcapAbtAbnormSnt OBJECT-TYPE
		SYNTAX	Unsigned32
		MAX-ACCESS read-only
		STATUS current
		DESCRIPTION
			"Number of P_ABORT transacs sent (abnormal dialog)"
	::= { ghlrInstanceEntry	81 }

smscGhlrTcapUabtRcvd OBJECT-TYPE
		SYNTAX	Unsigned32
		MAX-ACCESS read-only
		STATUS current
		DESCRIPTION
			"Number of U_ABORT transactions received"
	::= { ghlrInstanceEntry	82 }

smscGhlrTcapUabtSnt OBJECT-TYPE
		SYNTAX	Unsigned32
		MAX-ACCESS read-only
		STATUS current
		DESCRIPTION
			"Number of U_ABORT transactions sent"
	::= { ghlrInstanceEntry	83 }

smscGhlrTcapInvkRcvd OBJECT-TYPE
		SYNTAX	Unsigned32
		MAX-ACCESS read-only
		STATUS current
		DESCRIPTION
			"Number of Invoke components received"
	::= { ghlrInstanceEntry	84 }

smscGhlrTcapInvkSnt OBJECT-TYPE
		SYNTAX	Unsigned32
		MAX-ACCESS read-only
		STATUS current
		DESCRIPTION
			"Number of Invoke components sent"
	::= { ghlrInstanceEntry	85 }

smscGhlrTcapResLastRcvd OBJECT-TYPE
		SYNTAX	Unsigned32
		MAX-ACCESS read-only
		STATUS current
		DESCRIPTION
			"Number of Result Last components received"
	::= { ghlrInstanceEntry	86 }

smscGhlrTcapResNolastRcvd OBJECT-TYPE
		SYNTAX	Unsigned32
		MAX-ACCESS read-only
		STATUS current
		DESCRIPTION
			"Number of Result No Last components received"
	::= { ghlrInstanceEntry	87 }

smscGhlrTcapResLastSnt OBJECT-TYPE
		SYNTAX	Unsigned32
		MAX-ACCESS read-only
		STATUS current
		DESCRIPTION
			"Number of Result Last components sent"
	::= { ghlrInstanceEntry	88 }

smscGhlrTcapResNolastSnt OBJECT-TYPE
		SYNTAX	Unsigned32
		MAX-ACCESS read-only
		STATUS current
		DESCRIPTION
			"Number of Result No Last components sent"
	::= { ghlrInstanceEntry	89 }

smscGhlrTcapErrorRcvd OBJECT-TYPE
		SYNTAX	Unsigned32
		MAX-ACCESS read-only
		STATUS current
		DESCRIPTION
			"Number of Error components received"
	::= { ghlrInstanceEntry	90 }

smscGhlrTcapErrorSnt OBJECT-TYPE
		SYNTAX	Unsigned32
		MAX-ACCESS read-only
		STATUS current
		DESCRIPTION
			"Number of Error components sent"
	::= { ghlrInstanceEntry	91 }

smscGhlrTcapRjctSnt OBJECT-TYPE
		SYNTAX	Unsigned32
		MAX-ACCESS read-only
		STATUS current
		DESCRIPTION
			"Number of Reject components sent"
	::= { ghlrInstanceEntry	92 }

smscGhlrTcapRjctRcvd OBJECT-TYPE
		SYNTAX	Unsigned32
		MAX-ACCESS read-only
		STATUS current
		DESCRIPTION
			"Number of Reject components rcvd"
	::= { ghlrInstanceEntry	93 }

smscGhlrTcapRjctUnrecRcvd OBJECT-TYPE
		SYNTAX	Unsigned32
		MAX-ACCESS read-only
		STATUS current
		DESCRIPTION
			"Number of Reject components rcvd (unrecognized)"
	::= { ghlrInstanceEntry	94 }

smscGhlrTcapRjctMistypeRcvd OBJECT-TYPE
		SYNTAX	Unsigned32
		MAX-ACCESS read-only
		STATUS current
		DESCRIPTION
			"Number of Reject components rcvd (mistyped)"
	::= { ghlrInstanceEntry	95 }

smscGhlrTcapRjctBadsRcvd OBJECT-TYPE
		SYNTAX	Unsigned32
		MAX-ACCESS read-only
		STATUS current
		DESCRIPTION
			"Number of Reject components rcvd (badly struct)"
	::= { ghlrInstanceEntry	96 }

smscGhlrTcapRjctUnrLidRcvd OBJECT-TYPE
		SYNTAX	Unsigned32
		MAX-ACCESS read-only
		STATUS current
		DESCRIPTION
			"Number of Reject components rcvd (unrec link_id)"
	::= { ghlrInstanceEntry	97 }

smscGhlrTcapRjctUiRrRcvd OBJECT-TYPE
		SYNTAX	Unsigned32
		MAX-ACCESS read-only
		STATUS current
		DESCRIPTION
			"Number of Reject components rcvd (unr ivk ret res)"
	::= { ghlrInstanceEntry	98 }

smscGhlrTcapRjctUiReRcvd OBJECT-TYPE
		SYNTAX	Unsigned32
		MAX-ACCESS read-only
		STATUS current
		DESCRIPTION
			"Number of Reject components rcvd (unr ivk ret err)"
	::= { ghlrInstanceEntry	99 }

smscGhlrTcapRjctUnxpRrRcvd OBJECT-TYPE
		SYNTAX	Unsigned32
		MAX-ACCESS read-only
		STATUS current
		DESCRIPTION
			"Number of Reject components rcvd (unexp ret res)"
	::= { ghlrInstanceEntry	100 }

smscGhlrTcapRjctUnxpReRcvd OBJECT-TYPE
		SYNTAX	Unsigned32
		MAX-ACCESS read-only
		STATUS current
		DESCRIPTION
			"Number of Reject components rcvd (unexp ret err)"
	::= { ghlrInstanceEntry	101 }

smscGhlrTcapRjctDupIidRcvd OBJECT-TYPE
		SYNTAX	Unsigned32
		MAX-ACCESS read-only
		STATUS current
		DESCRIPTION
			"Number of Reject components rcvd (dupl ivk_id)"
	::= { ghlrInstanceEntry	102 }

smscGhlrTcapPrbUnrecOpRcvd OBJECT-TYPE
		SYNTAX	Unsigned32
		MAX-ACCESS read-only
		STATUS current
		DESCRIPTION
			"Number of TC user problems rcvd (unrec operations)"
	::= { ghlrInstanceEntry	103 }

smscGhlrTcapPrbMistypeRcvd OBJECT-TYPE
		SYNTAX	Unsigned32
		MAX-ACCESS read-only
		STATUS current
		DESCRIPTION
			"Number of TC user problems rcvd (mistyped param)"
	::= { ghlrInstanceEntry	104 }

smscGhlrTcapPrbReslimitRcvd OBJECT-TYPE
		SYNTAX	Unsigned32
		MAX-ACCESS read-only
		STATUS current
		DESCRIPTION
			"Number of TC user problems rcvd (res limitation)"
	::= { ghlrInstanceEntry	105 }

smscGhlrTcapPrbInitrelRcvd OBJECT-TYPE
		SYNTAX	Unsigned32
		MAX-ACCESS read-only
		STATUS current
		DESCRIPTION
			"Number of TC user problems rcvd (init release)"
	::= { ghlrInstanceEntry	106 }

smscGhlrTcapPrbUnlRespRcvd OBJECT-TYPE
		SYNTAX	Unsigned32
		MAX-ACCESS read-only
		STATUS current
		DESCRIPTION
			"Number of TC user problems rcvd (unexp link resp)"
	::= { ghlrInstanceEntry	107 }

smscGhlrTcapPrbUnlOpRcvd OBJECT-TYPE
		SYNTAX	Unsigned32
		MAX-ACCESS read-only
		STATUS current
		DESCRIPTION
			"Number of TC user problems rcvd (unexp link oper)"
	::= { ghlrInstanceEntry	108 }

smscGhlrTcapPrbMtRrRcvd OBJECT-TYPE
		SYNTAX	Unsigned32
		MAX-ACCESS read-only
		STATUS current
		DESCRIPTION
			"Number of TC user problems rcvd (mistyped ret res)"
	::= { ghlrInstanceEntry	109 }

smscGhlrTcapPrbMtReRcvd OBJECT-TYPE
		SYNTAX	Unsigned32
		MAX-ACCESS read-only
		STATUS current
		DESCRIPTION
			"Number of TC user problems rcvd (mistyped ret err)"
	::= { ghlrInstanceEntry	110 }

smscGhlrTcapUserUnrecRcvd OBJECT-TYPE
		SYNTAX	Unsigned32
		MAX-ACCESS read-only
		STATUS current
		DESCRIPTION
			"Number of TC user unrecognized errors received"
	::= { ghlrInstanceEntry	111 }

smscGhlrTcapUserUnxpRcvd OBJECT-TYPE
		SYNTAX	Unsigned32
		MAX-ACCESS read-only
		STATUS current
		DESCRIPTION
			"Number of TC user unexpected errors received"
	::= { ghlrInstanceEntry	112 }

smscGhlrTcapActiveDialog OBJECT-TYPE
		SYNTAX	Unsigned32
		MAX-ACCESS read-only
		STATUS current
		DESCRIPTION
			"Number of simultaneous active TCAP dialogues"
	::= { ghlrInstanceEntry	113 }

smscGhlrTcapInitiatedDialog OBJECT-TYPE
		SYNTAX	Unsigned32
		MAX-ACCESS read-only
		STATUS current
		DESCRIPTION
			"Number of simultaneous initiated TCAP dialogues"
	::= { ghlrInstanceEntry	114 }

smscGhlrTcapActiveDlgs OBJECT-TYPE
		SYNTAX	Unsigned32
		MAX-ACCESS read-only
		STATUS current
		DESCRIPTION
			"Number of simultaneous active TCAP dialogues"
	::= { ghlrInstanceEntry	115 }

smscGhlrTcapInitiatedDlgs OBJECT-TYPE
		SYNTAX	Unsigned32
		MAX-ACCESS read-only
		STATUS current
		DESCRIPTION
			"Number of simultaneous initiated TCAP dialogues"
	::= { ghlrInstanceEntry	116 }



-- end of GHLR description.
-- --------------------------------------


-- --------------------------------------
-- Class OTAIS41
-- 
smscOtais41 OBJECT-TYPE
	SYNTAX  SEQUENCE OF Otais41InstanceEntry
	MAX-ACCESS  not-accessible
	STATUS  current
	DESCRIPTION
		"Mapping table for SMSC OTAIS41 entities."
   ::= { smscClassServer   13  }

otais41InstanceEntry  OBJECT-TYPE
	SYNTAX Otais41InstanceEntry
	MAX-ACCESS  not-accessible
	STATUS  current
	DESCRIPTION
		"An entry (row) in the entityInstanceTable."
	INDEX { IMPLIED smscOtais41Name }
   ::= { smscOtais41 1 }

Otais41InstanceEntry ::= SEQUENCE {
		smscOtais41Name     DisplayString,
		smscOtais41State   INTEGER,
		smscOtais41Lastupdate   TimeTicks,
		smscOtais41Node	   DisplayString, 
		smscOtais41MsgReceived	 Unsigned32, 
		smscOtais41MsgRejected	 Unsigned32, 
		smscOtais41MsgTransmitted	 Unsigned32, 
		smscOtais41MsgFailed	 Unsigned32, 
		smscOtais41SessionsPending	 Unsigned32, 
		smscOtais41DialoguesPending	 Unsigned32, 
		smscOtais41QelemUsed	 Unsigned32, 
		smscOtais41QelemInProcqueue	 Unsigned32, 
		smscOtais41QelemInExpqueue	 Unsigned32, 
		smscOtais41NrTimersRunning	 Unsigned32, 
		smscOtais41NrSystemTimers	 Unsigned32, 
		smscOtais41ImiRecallQelem	 Unsigned32, 
		smscOtais41ImiRecallQueues	 Unsigned32, 
		smscOtais41IdiRecallQelem	 Unsigned32, 
		smscOtais41IdiRecallQueues	 Unsigned32, 
		smscOtais41IosRecallQelem	 Unsigned32, 
		smscOtais41IosRecallQueues	 Unsigned32, 
		smscOtais41LogRecallQelem	 Unsigned32, 
		smscOtais41LogRecallQueues	 Unsigned32, 
		smscOtais41TrcreqDiscarded	 Unsigned32, 
		smscOtais41MtSmsOk	 Unsigned32, 
		smscOtais41MtSmsFail	 Unsigned32, 
		smscOtais41MoSmsAccepted	 Unsigned32, 
		smscOtais41MoSmsRejected	 Unsigned32, 
		smscOtais41SmsRequestOk	 Unsigned32, 
		smscOtais41SmsRequestFail	 Unsigned32, 
		smscOtais41SmsNotifAccepted	 Unsigned32, 
		smscOtais41SmsNotifRejected	 Unsigned32, 
		smscOtais41OtaspReqOk	 Unsigned32, 
		smscOtais41OtaspReqFail	 Unsigned32, 
		smscOtais41SccpAddrErrors	 Unsigned32, 
		smscOtais41TcapErrors	 Unsigned32, 
		smscOtais41TimeOuts	 Unsigned32, 
		smscOtais41SmsAddrProblem	 Unsigned32, 
		smscOtais41SmsInvalidServiceId	 Unsigned32, 
		smscOtais41SmsNetworkProblem	 Unsigned32, 
		smscOtais41SmsTerminalProblem	 Unsigned32, 
		smscOtais41SmsRadioProblem	 Unsigned32, 
		smscOtais41SmsEncodingProblem	 Unsigned32, 
		smscOtais41SmsMissingParameter	 Unsigned32, 
		smscOtais41SmsParamValueErr	 Unsigned32, 
		smscOtais41SmsGeneralProblem	 Unsigned32, 
		smscOtais41AbsentSubscriber	 Unsigned32, 
		smscOtais41SmsDestBusy	 Unsigned32, 
		smscOtais41SmsDestResourceShort	 Unsigned32, 
		smscOtais41SmsSvcDenied	 Unsigned32, 
		smscOtais41MsInvalid	 Unsigned32, 
		smscOtais41MsUnreachable	 Unsigned32, 
		smscOtais41MsUnavailable	 Unsigned32, 
		smscOtais41NoPageResponse	 Unsigned32, 
		smscOtais41DeliveryPostponed	 Unsigned32, 
		smscOtais41DestLeftAddr	 Unsigned32, 
		smscOtais41Dialogues	 Unsigned32, 
		smscOtais41TcapBeginRcvd	 Unsigned32, 
		smscOtais41TcapContRcvd	 Unsigned32, 
		smscOtais41TcapEndRcvd	 Unsigned32, 
		smscOtais41TcapBeginSnt	 Unsigned32, 
		smscOtais41TcapEndSnt	 Unsigned32, 
		smscOtais41TcapFailedSent	 Unsigned32, 
		smscOtais41TcapTransDisc	 Unsigned32, 
		smscOtais41TcapMsgDisc	 Unsigned32, 
		smscOtais41TcapAbtRcvd	 Unsigned32, 
		smscOtais41TcapAbtUnrecmtRcvd	 Unsigned32, 
		smscOtais41TcapAbtTranpRcvd	 Unsigned32, 
		smscOtais41TcapAbtBftpRcvd	 Unsigned32, 
		smscOtais41TcapAbtUnrecidRcvd	 Unsigned32, 
		smscOtais41TcapAbtReslimitRcvd	 Unsigned32, 
		smscOtais41TcapAbtAbnormRcvd	 Unsigned32, 
		smscOtais41TcapUabtRcvd	 Unsigned32, 
		smscOtais41TcapInvkRcvd	 Unsigned32, 
		smscOtais41TcapInvknlRcvd	 Unsigned32, 
		smscOtais41TcapInvkSnt	 Unsigned32, 
		smscOtais41TcapResLastRcvd	 Unsigned32, 
		smscOtais41TcapResNolastRcvd	 Unsigned32, 
		smscOtais41TcapResLastSnt	 Unsigned32, 
		smscOtais41TcapErrorRcvd	 Unsigned32, 
		smscOtais41TcapErrorSnt	 Unsigned32, 
		smscOtais41TcapRejectSnt	 Unsigned32, 
		smscOtais41TcapRejectRcvd	 Unsigned32, 
		smscOtais41TcapRjctUnrecRcvd	 Unsigned32, 
		smscOtais41TcapRjctIcpRcvd	 Unsigned32, 
		smscOtais41TcapRjctBadsRcvd	 Unsigned32, 
		smscOtais41TcapRjctIccRcvd	 Unsigned32, 
		smscOtais41TcapRjctDupIidRcvd	 Unsigned32, 
		smscOtais41TcapPrbUnrecOpRcvd	 Unsigned32, 
		smscOtais41TcapPrbMistypeRcvd	 Unsigned32, 
		smscOtais41TcapRjctUnrLidRcvd	 Unsigned32, 
		smscOtais41TcapRjctRruciRcvd	 Unsigned32, 
		smscOtais41TcapRjctUnxpRrRcvd	 Unsigned32, 
		smscOtais41TcapPrbMtRrRcvd	 Unsigned32, 
		smscOtais41TcapRjctReuciRcvd	 Unsigned32, 
		smscOtais41TcapRjctUnxpReRcvd	 Unsigned32, 
		smscOtais41TcapUserUnrecRcvd	 Unsigned32, 
		smscOtais41TcapUserUnxpRcvd	 Unsigned32, 
		smscOtais41TcapPrbMtReRcvd	 Unsigned32, 
		smscOtais41TcapRjtUnrecmtRcvd	 Unsigned32, 
		smscOtais41TcapRjtTranpRcvd	 Unsigned32, 
		smscOtais41TcapRjtBftpRcvd	 Unsigned32, 
		smscOtais41TcapRjtUnrecidRcvd	 Unsigned32, 
		smscOtais41TcapRjctTp2rRcvd	 Unsigned32, 
		smscOtais41TcapPrbReslimitRcvd	 Unsigned32, 
		smscOtais41TcapAbtUnrecmtSnt	 Unsigned32, 
		smscOtais41TcapAbtTranpSnt	 Unsigned32, 
		smscOtais41TcapAbtBftpSnt	 Unsigned32, 
		smscOtais41TcapAbtUnrecidSnt	 Unsigned32, 
		smscOtais41TcapRjctTp2rSnt	 Unsigned32, 
		smscOtais41TcapAbtReslimitSnt	 Unsigned32, 
		smscOtais41TcapRjctUctSnt	 Unsigned32, 
		smscOtais41TcapRjctIcpSnt	 Unsigned32, 
		smscOtais41TcapRjctBscpSnt	 Unsigned32, 
		smscOtais41TcapRjctIccSnt	 Unsigned32, 
		smscOtais41TcapRjctIvdidSnt	 Unsigned32, 
		smscOtais41TcapRjctIvuocSnt	 Unsigned32, 
		smscOtais41TcapRjctIviparSnt	 Unsigned32, 
		smscOtais41TcapRjctUcidSnt	 Unsigned32, 
		smscOtais41TcapRjctRruciSnt	 Unsigned32, 
		smscOtais41TcapRjctRrurrSnt	 Unsigned32, 
		smscOtais41TcapRjctRripSnt	 Unsigned32, 
		smscOtais41TcapRjctEruciSnt	 Unsigned32, 
		smscOtais41TcapRjctErureSnt	 Unsigned32, 
		smscOtais41TcapRjctErueSnt	 Unsigned32, 
		smscOtais41TcapRjctErunxSnt	 Unsigned32, 
		smscOtais41TcapRjctEripSnt	 Unsigned32, 
		smscOtais41TcapActiveDialog	 Unsigned32, 
		smscOtais41TcapInitiatedDialog	 Unsigned32, 
		smscOtais41TcapUnknMsgRcvd	 Unsigned32, 
		smscOtais41TcapNoticeRcvd	 Unsigned32
	}

smscOtais41Name  OBJECT-TYPE
	SYNTAX  DisplayString
	MAX-ACCESS  read-only
	STATUS   current
	DESCRIPTION
		"Identifies the name of the entity."
   ::= {otais41InstanceEntry 1 }

smscOtais41State  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { otais41InstanceEntry 2 }


smscOtais41Lastupdate OBJECT-TYPE
		SYNTAX	TimeTicks
		MAX-ACCESS read-only
		STATUS current
		DESCRIPTION
			"Value which reflects the last time the entities fields have been updated"
	::= { otais41InstanceEntry	3 }

smscOtais41Node  OBJECT-TYPE
	SYNTAX  DisplayString
	MAX-ACCESS  read-only
	STATUS   current
	DESCRIPTION
		"Identifies the node the entity is running on."
   ::= {otais41InstanceEntry 4 }

smscOtais41MsgReceived OBJECT-TYPE
		SYNTAX	Unsigned32
		MAX-ACCESS read-only
		STATUS current
		DESCRIPTION
			"Received messages"
	::= { otais41InstanceEntry	5 }

smscOtais41MsgRejected OBJECT-TYPE
		SYNTAX	Unsigned32
		MAX-ACCESS read-only
		STATUS current
		DESCRIPTION
			"Received messages and rejected"
	::= { otais41InstanceEntry	6 }

smscOtais41MsgTransmitted OBJECT-TYPE
		SYNTAX	Unsigned32
		MAX-ACCESS read-only
		STATUS current
		DESCRIPTION
			"Transmitted messages"
	::= { otais41InstanceEntry	7 }

smscOtais41MsgFailed OBJECT-TYPE
		SYNTAX	Unsigned32
		MAX-ACCESS read-only
		STATUS current
		DESCRIPTION
			"Messages that failed on sending"
	::= { otais41InstanceEntry	8 }

smscOtais41SessionsPending OBJECT-TYPE
		SYNTAX	Unsigned32
		MAX-ACCESS read-only
		STATUS current
		DESCRIPTION
			"Number of sessions (currently) pending"
	::= { otais41InstanceEntry	9 }

smscOtais41DialoguesPending OBJECT-TYPE
		SYNTAX	Unsigned32
		MAX-ACCESS read-only
		STATUS current
		DESCRIPTION
			"Number of dialogues (currently) pending"
	::= { otais41InstanceEntry	10 }

smscOtais41QelemUsed OBJECT-TYPE
		SYNTAX	Unsigned32
		MAX-ACCESS read-only
		STATUS current
		DESCRIPTION
			"Number of elements in internal queues"
	::= { otais41InstanceEntry	11 }

smscOtais41QelemInProcqueue OBJECT-TYPE
		SYNTAX	Unsigned32
		MAX-ACCESS read-only
		STATUS current
		DESCRIPTION
			"Number of elements used in process queue"
	::= { otais41InstanceEntry	12 }

smscOtais41QelemInExpqueue OBJECT-TYPE
		SYNTAX	Unsigned32
		MAX-ACCESS read-only
		STATUS current
		DESCRIPTION
			"Number of elements used in expedited queue"
	::= { otais41InstanceEntry	13 }

smscOtais41NrTimersRunning OBJECT-TYPE
		SYNTAX	Unsigned32
		MAX-ACCESS read-only
		STATUS current
		DESCRIPTION
			"Total number of timers running"
	::= { otais41InstanceEntry	14 }

smscOtais41NrSystemTimers OBJECT-TYPE
		SYNTAX	Unsigned32
		MAX-ACCESS read-only
		STATUS current
		DESCRIPTION
			"Number of system timers running"
	::= { otais41InstanceEntry	15 }

smscOtais41ImiRecallQelem OBJECT-TYPE
		SYNTAX	Unsigned32
		MAX-ACCESS read-only
		STATUS current
		DESCRIPTION
			"Number of IMI recall-queue elements used"
	::= { otais41InstanceEntry	16 }

smscOtais41ImiRecallQueues OBJECT-TYPE
		SYNTAX	Unsigned32
		MAX-ACCESS read-only
		STATUS current
		DESCRIPTION
			"Number of IMI-recall-queues used"
	::= { otais41InstanceEntry	17 }

smscOtais41IdiRecallQelem OBJECT-TYPE
		SYNTAX	Unsigned32
		MAX-ACCESS read-only
		STATUS current
		DESCRIPTION
			"Number of IDI recall-queue elements used"
	::= { otais41InstanceEntry	18 }

smscOtais41IdiRecallQueues OBJECT-TYPE
		SYNTAX	Unsigned32
		MAX-ACCESS read-only
		STATUS current
		DESCRIPTION
			"Number of IDI recall-queues used"
	::= { otais41InstanceEntry	19 }

smscOtais41IosRecallQelem OBJECT-TYPE
		SYNTAX	Unsigned32
		MAX-ACCESS read-only
		STATUS current
		DESCRIPTION
			"Number of IOS recall-queue elements used"
	::= { otais41InstanceEntry	20 }

smscOtais41IosRecallQueues OBJECT-TYPE
		SYNTAX	Unsigned32
		MAX-ACCESS read-only
		STATUS current
		DESCRIPTION
			"Number of IOS recall-queues used"
	::= { otais41InstanceEntry	21 }

smscOtais41LogRecallQelem OBJECT-TYPE
		SYNTAX	Unsigned32
		MAX-ACCESS read-only
		STATUS current
		DESCRIPTION
			"Number of LOG recall-queue elements used"
	::= { otais41InstanceEntry	22 }

smscOtais41LogRecallQueues OBJECT-TYPE
		SYNTAX	Unsigned32
		MAX-ACCESS read-only
		STATUS current
		DESCRIPTION
			"Number of LOG recall-queues used"
	::= { otais41InstanceEntry	23 }

smscOtais41TrcreqDiscarded OBJECT-TYPE
		SYNTAX	Unsigned32
		MAX-ACCESS read-only
		STATUS current
		DESCRIPTION
			"Number of trace requests discarded"
	::= { otais41InstanceEntry	24 }

smscOtais41MtSmsOk OBJECT-TYPE
		SYNTAX	Unsigned32
		MAX-ACCESS read-only
		STATUS current
		DESCRIPTION
			"Number of delivered Mobile Terminated SM"
	::= { otais41InstanceEntry	25 }

smscOtais41MtSmsFail OBJECT-TYPE
		SYNTAX	Unsigned32
		MAX-ACCESS read-only
		STATUS current
		DESCRIPTION
			"Number of failed Mobile Terminated SM"
	::= { otais41InstanceEntry	26 }

smscOtais41MoSmsAccepted OBJECT-TYPE
		SYNTAX	Unsigned32
		MAX-ACCESS read-only
		STATUS current
		DESCRIPTION
			"Number of accepted Mobile Originated SM"
	::= { otais41InstanceEntry	27 }

smscOtais41MoSmsRejected OBJECT-TYPE
		SYNTAX	Unsigned32
		MAX-ACCESS read-only
		STATUS current
		DESCRIPTION
			"Number of rejected Mobile Originated SM"
	::= { otais41InstanceEntry	28 }

smscOtais41SmsRequestOk OBJECT-TYPE
		SYNTAX	Unsigned32
		MAX-ACCESS read-only
		STATUS current
		DESCRIPTION
			"Number of successful SMSRequest operations"
	::= { otais41InstanceEntry	29 }

smscOtais41SmsRequestFail OBJECT-TYPE
		SYNTAX	Unsigned32
		MAX-ACCESS read-only
		STATUS current
		DESCRIPTION
			"Number of failed SMSRequest operations"
	::= { otais41InstanceEntry	30 }

smscOtais41SmsNotifAccepted OBJECT-TYPE
		SYNTAX	Unsigned32
		MAX-ACCESS read-only
		STATUS current
		DESCRIPTION
			"Number of accepted SMSNotification operations"
	::= { otais41InstanceEntry	31 }

smscOtais41SmsNotifRejected OBJECT-TYPE
		SYNTAX	Unsigned32
		MAX-ACCESS read-only
		STATUS current
		DESCRIPTION
			"Number of rejected SMSNotification operations"
	::= { otais41InstanceEntry	32 }

smscOtais41OtaspReqOk OBJECT-TYPE
		SYNTAX	Unsigned32
		MAX-ACCESS read-only
		STATUS current
		DESCRIPTION
			"Number successful OTASPRequest operations"
	::= { otais41InstanceEntry	33 }

smscOtais41OtaspReqFail OBJECT-TYPE
		SYNTAX	Unsigned32
		MAX-ACCESS read-only
		STATUS current
		DESCRIPTION
			"Number failed OTASPRequest operations"
	::= { otais41InstanceEntry	34 }

smscOtais41SccpAddrErrors OBJECT-TYPE
		SYNTAX	Unsigned32
		MAX-ACCESS read-only
		STATUS current
		DESCRIPTION
			"Number of SCCP address errors"
	::= { otais41InstanceEntry	35 }

smscOtais41TcapErrors OBJECT-TYPE
		SYNTAX	Unsigned32
		MAX-ACCESS read-only
		STATUS current
		DESCRIPTION
			"Number of TCAP errors/problems"
	::= { otais41InstanceEntry	36 }

smscOtais41TimeOuts OBJECT-TYPE
		SYNTAX	Unsigned32
		MAX-ACCESS read-only
		STATUS current
		DESCRIPTION
			"Number of IS-41 Network or Server time-outs"
	::= { otais41InstanceEntry	37 }

smscOtais41SmsAddrProblem OBJECT-TYPE
		SYNTAX	Unsigned32
		MAX-ACCESS read-only
		STATUS current
		DESCRIPTION
			"Number of SMS Address errors"
	::= { otais41InstanceEntry	38 }

smscOtais41SmsInvalidServiceId OBJECT-TYPE
		SYNTAX	Unsigned32
		MAX-ACCESS read-only
		STATUS current
		DESCRIPTION
			"Number of SMS Invalid Teleservice ID errors"
	::= { otais41InstanceEntry	39 }

smscOtais41SmsNetworkProblem OBJECT-TYPE
		SYNTAX	Unsigned32
		MAX-ACCESS read-only
		STATUS current
		DESCRIPTION
			"Number of SMS Network Problem errors"
	::= { otais41InstanceEntry	40 }

smscOtais41SmsTerminalProblem OBJECT-TYPE
		SYNTAX	Unsigned32
		MAX-ACCESS read-only
		STATUS current
		DESCRIPTION
			"Number of SMS Terminal Problem errors"
	::= { otais41InstanceEntry	41 }

smscOtais41SmsRadioProblem OBJECT-TYPE
		SYNTAX	Unsigned32
		MAX-ACCESS read-only
		STATUS current
		DESCRIPTION
			"Number of SMS Radio Interface Problem errors"
	::= { otais41InstanceEntry	42 }

smscOtais41SmsEncodingProblem OBJECT-TYPE
		SYNTAX	Unsigned32
		MAX-ACCESS read-only
		STATUS current
		DESCRIPTION
			"SMS Encoding Problem (parameter size) errors"
	::= { otais41InstanceEntry	43 }

smscOtais41SmsMissingParameter OBJECT-TYPE
		SYNTAX	Unsigned32
		MAX-ACCESS read-only
		STATUS current
		DESCRIPTION
			"Number of SMS Missing Parameter errors"
	::= { otais41InstanceEntry	44 }

smscOtais41SmsParamValueErr OBJECT-TYPE
		SYNTAX	Unsigned32
		MAX-ACCESS read-only
		STATUS current
		DESCRIPTION
			"Number of SMS Parameter Value errors"
	::= { otais41InstanceEntry	45 }

smscOtais41SmsGeneralProblem OBJECT-TYPE
		SYNTAX	Unsigned32
		MAX-ACCESS read-only
		STATUS current
		DESCRIPTION
			"Number of SMS General Problem errors"
	::= { otais41InstanceEntry	46 }

smscOtais41AbsentSubscriber OBJECT-TYPE
		SYNTAX	Unsigned32
		MAX-ACCESS read-only
		STATUS current
		DESCRIPTION
			"Number of Absent Subscriber errors"
	::= { otais41InstanceEntry	47 }

smscOtais41SmsDestBusy OBJECT-TYPE
		SYNTAX	Unsigned32
		MAX-ACCESS read-only
		STATUS current
		DESCRIPTION
			"Number of Destination Busy errors"
	::= { otais41InstanceEntry	48 }

smscOtais41SmsDestResourceShort OBJECT-TYPE
		SYNTAX	Unsigned32
		MAX-ACCESS read-only
		STATUS current
		DESCRIPTION
			"Number of Destination Resource Shortage errors"
	::= { otais41InstanceEntry	49 }

smscOtais41SmsSvcDenied OBJECT-TYPE
		SYNTAX	Unsigned32
		MAX-ACCESS read-only
		STATUS current
		DESCRIPTION
			"Number of Service Denied Errors"
	::= { otais41InstanceEntry	50 }

smscOtais41MsInvalid OBJECT-TYPE
		SYNTAX	Unsigned32
		MAX-ACCESS read-only
		STATUS current
		DESCRIPTION
			"Number of MS Invalid (HLR Denied) errors"
	::= { otais41InstanceEntry	51 }

smscOtais41MsUnreachable OBJECT-TYPE
		SYNTAX	Unsigned32
		MAX-ACCESS read-only
		STATUS current
		DESCRIPTION
			"Number of MS Unreachable (HLR Postponed) errors"
	::= { otais41InstanceEntry	52 }

smscOtais41MsUnavailable OBJECT-TYPE
		SYNTAX	Unsigned32
		MAX-ACCESS read-only
		STATUS current
		DESCRIPTION
			"Number of MS Unavailable (HLR Unavailable) errors"
	::= { otais41InstanceEntry	53 }

smscOtais41NoPageResponse OBJECT-TYPE
		SYNTAX	Unsigned32
		MAX-ACCESS read-only
		STATUS current
		DESCRIPTION
			"Number of No Page Response errors"
	::= { otais41InstanceEntry	54 }

smscOtais41DeliveryPostponed OBJECT-TYPE
		SYNTAX	Unsigned32
		MAX-ACCESS read-only
		STATUS current
		DESCRIPTION
			"Number of MSC Delivery Postponed errors"
	::= { otais41InstanceEntry	55 }

smscOtais41DestLeftAddr OBJECT-TYPE
		SYNTAX	Unsigned32
		MAX-ACCESS read-only
		STATUS current
		DESCRIPTION
			"Number of Destination Left Address errors"
	::= { otais41InstanceEntry	56 }

smscOtais41Dialogues OBJECT-TYPE
		SYNTAX	Unsigned32
		MAX-ACCESS read-only
		STATUS current
		DESCRIPTION
			"Number of dialogues"
	::= { otais41InstanceEntry	57 }

smscOtais41TcapBeginRcvd OBJECT-TYPE
		SYNTAX	Unsigned32
		MAX-ACCESS read-only
		STATUS current
		DESCRIPTION
			"Number of Begin Dialogue transactions received"
	::= { otais41InstanceEntry	58 }

smscOtais41TcapContRcvd OBJECT-TYPE
		SYNTAX	Unsigned32
		MAX-ACCESS read-only
		STATUS current
		DESCRIPTION
			"Number of Continue transactions received"
	::= { otais41InstanceEntry	59 }

smscOtais41TcapEndRcvd OBJECT-TYPE
		SYNTAX	Unsigned32
		MAX-ACCESS read-only
		STATUS current
		DESCRIPTION
			"Number of End transactions received"
	::= { otais41InstanceEntry	60 }

smscOtais41TcapBeginSnt OBJECT-TYPE
		SYNTAX	Unsigned32
		MAX-ACCESS read-only
		STATUS current
		DESCRIPTION
			"Number of Begin Dialogue transactions sent"
	::= { otais41InstanceEntry	61 }

smscOtais41TcapEndSnt OBJECT-TYPE
		SYNTAX	Unsigned32
		MAX-ACCESS read-only
		STATUS current
		DESCRIPTION
			"Number of End transactions sent"
	::= { otais41InstanceEntry	62 }

smscOtais41TcapFailedSent OBJECT-TYPE
		SYNTAX	Unsigned32
		MAX-ACCESS read-only
		STATUS current
		DESCRIPTION
			"Number of Message failed to be sent"
	::= { otais41InstanceEntry	63 }

smscOtais41TcapTransDisc OBJECT-TYPE
		SYNTAX	Unsigned32
		MAX-ACCESS read-only
		STATUS current
		DESCRIPTION
			"Number of discarded msgs due to transport problem"
	::= { otais41InstanceEntry	64 }

smscOtais41TcapMsgDisc OBJECT-TYPE
		SYNTAX	Unsigned32
		MAX-ACCESS read-only
		STATUS current
		DESCRIPTION
			"Number of discarded TCAP messages"
	::= { otais41InstanceEntry	65 }

smscOtais41TcapAbtRcvd OBJECT-TYPE
		SYNTAX	Unsigned32
		MAX-ACCESS read-only
		STATUS current
		DESCRIPTION
			"Number of P_ABORT transacs rcvd"
	::= { otais41InstanceEntry	66 }

smscOtais41TcapAbtUnrecmtRcvd OBJECT-TYPE
		SYNTAX	Unsigned32
		MAX-ACCESS read-only
		STATUS current
		DESCRIPTION
			"Number of P_ABORT transacs rcvd (unrec msg type)"
	::= { otais41InstanceEntry	67 }

smscOtais41TcapAbtTranpRcvd OBJECT-TYPE
		SYNTAX	Unsigned32
		MAX-ACCESS read-only
		STATUS current
		DESCRIPTION
			"Number of P_ABORT msgs rcvd (inc trans portion)"
	::= { otais41InstanceEntry	68 }

smscOtais41TcapAbtBftpRcvd OBJECT-TYPE
		SYNTAX	Unsigned32
		MAX-ACCESS read-only
		STATUS current
		DESCRIPTION
			"Number of P_ABORT msgs rcvd (badly formed tp)"
	::= { otais41InstanceEntry	69 }

smscOtais41TcapAbtUnrecidRcvd OBJECT-TYPE
		SYNTAX	Unsigned32
		MAX-ACCESS read-only
		STATUS current
		DESCRIPTION
			"Number of P_ABORT msgs rcvd (unrec trans id)"
	::= { otais41InstanceEntry	70 }

smscOtais41TcapAbtReslimitRcvd OBJECT-TYPE
		SYNTAX	Unsigned32
		MAX-ACCESS read-only
		STATUS current
		DESCRIPTION
			"Number of P_ABORT msgs rcvd (resouce limitation)"
	::= { otais41InstanceEntry	71 }

smscOtais41TcapAbtAbnormRcvd OBJECT-TYPE
		SYNTAX	Unsigned32
		MAX-ACCESS read-only
		STATUS current
		DESCRIPTION
			"Number of P_ABORT msgs rcvd (abnormal dialog)"
	::= { otais41InstanceEntry	72 }

smscOtais41TcapUabtRcvd OBJECT-TYPE
		SYNTAX	Unsigned32
		MAX-ACCESS read-only
		STATUS current
		DESCRIPTION
			"Number of U_ABORT transactions received"
	::= { otais41InstanceEntry	73 }

smscOtais41TcapInvkRcvd OBJECT-TYPE
		SYNTAX	Unsigned32
		MAX-ACCESS read-only
		STATUS current
		DESCRIPTION
			"Number of Invoke Last components received"
	::= { otais41InstanceEntry	74 }

smscOtais41TcapInvknlRcvd OBJECT-TYPE
		SYNTAX	Unsigned32
		MAX-ACCESS read-only
		STATUS current
		DESCRIPTION
			"Number of Invoke Not Last components received"
	::= { otais41InstanceEntry	75 }

smscOtais41TcapInvkSnt OBJECT-TYPE
		SYNTAX	Unsigned32
		MAX-ACCESS read-only
		STATUS current
		DESCRIPTION
			"Number of Invoke Last components sent"
	::= { otais41InstanceEntry	76 }

smscOtais41TcapResLastRcvd OBJECT-TYPE
		SYNTAX	Unsigned32
		MAX-ACCESS read-only
		STATUS current
		DESCRIPTION
			"Number of Result Last components received"
	::= { otais41InstanceEntry	77 }

smscOtais41TcapResNolastRcvd OBJECT-TYPE
		SYNTAX	Unsigned32
		MAX-ACCESS read-only
		STATUS current
		DESCRIPTION
			"Number of Result No Last components received"
	::= { otais41InstanceEntry	78 }

smscOtais41TcapResLastSnt OBJECT-TYPE
		SYNTAX	Unsigned32
		MAX-ACCESS read-only
		STATUS current
		DESCRIPTION
			"Number of Result Last components sent"
	::= { otais41InstanceEntry	79 }

smscOtais41TcapErrorRcvd OBJECT-TYPE
		SYNTAX	Unsigned32
		MAX-ACCESS read-only
		STATUS current
		DESCRIPTION
			"Number of Error components received"
	::= { otais41InstanceEntry	80 }

smscOtais41TcapErrorSnt OBJECT-TYPE
		SYNTAX	Unsigned32
		MAX-ACCESS read-only
		STATUS current
		DESCRIPTION
			"Number of Error components sent"
	::= { otais41InstanceEntry	81 }

smscOtais41TcapRejectSnt OBJECT-TYPE
		SYNTAX	Unsigned32
		MAX-ACCESS read-only
		STATUS current
		DESCRIPTION
			"Number of Reject components sent"
	::= { otais41InstanceEntry	82 }

smscOtais41TcapRejectRcvd OBJECT-TYPE
		SYNTAX	Unsigned32
		MAX-ACCESS read-only
		STATUS current
		DESCRIPTION
			"Number of Reject components rcvd"
	::= { otais41InstanceEntry	83 }

smscOtais41TcapRjctUnrecRcvd OBJECT-TYPE
		SYNTAX	Unsigned32
		MAX-ACCESS read-only
		STATUS current
		DESCRIPTION
			"Number of Reject components rcvd (unrec comp type)"
	::= { otais41InstanceEntry	84 }

smscOtais41TcapRjctIcpRcvd OBJECT-TYPE
		SYNTAX	Unsigned32
		MAX-ACCESS read-only
		STATUS current
		DESCRIPTION
			"Number of Reject components rcvd (incor comp por)"
	::= { otais41InstanceEntry	85 }

smscOtais41TcapRjctBadsRcvd OBJECT-TYPE
		SYNTAX	Unsigned32
		MAX-ACCESS read-only
		STATUS current
		DESCRIPTION
			"Number of Reject components rcvd(badly struct comp)"
	::= { otais41InstanceEntry	86 }

smscOtais41TcapRjctIccRcvd OBJECT-TYPE
		SYNTAX	Unsigned32
		MAX-ACCESS read-only
		STATUS current
		DESCRIPTION
			"Number of Reject components rcvd(incorr comp coding)"
	::= { otais41InstanceEntry	87 }

smscOtais41TcapRjctDupIidRcvd OBJECT-TYPE
		SYNTAX	Unsigned32
		MAX-ACCESS read-only
		STATUS current
		DESCRIPTION
			"Number of Rejects rcvd (invoke dup id)"
	::= { otais41InstanceEntry	88 }

smscOtais41TcapPrbUnrecOpRcvd OBJECT-TYPE
		SYNTAX	Unsigned32
		MAX-ACCESS read-only
		STATUS current
		DESCRIPTION
			"Number of Rejects rcvd (invoke unrec oper)"
	::= { otais41InstanceEntry	89 }

smscOtais41TcapPrbMistypeRcvd OBJECT-TYPE
		SYNTAX	Unsigned32
		MAX-ACCESS read-only
		STATUS current
		DESCRIPTION
			"Number of Rejects rcvd (incor param)"
	::= { otais41InstanceEntry	90 }

smscOtais41TcapRjctUnrLidRcvd OBJECT-TYPE
		SYNTAX	Unsigned32
		MAX-ACCESS read-only
		STATUS current
		DESCRIPTION
			"Number of Rejects rcvd (invoke unrec corr ID)"
	::= { otais41InstanceEntry	91 }

smscOtais41TcapRjctRruciRcvd OBJECT-TYPE
		SYNTAX	Unsigned32
		MAX-ACCESS read-only
		STATUS current
		DESCRIPTION
			"Number of Rejects rcvd (result unass corr ID)"
	::= { otais41InstanceEntry	92 }

smscOtais41TcapRjctUnxpRrRcvd OBJECT-TYPE
		SYNTAX	Unsigned32
		MAX-ACCESS read-only
		STATUS current
		DESCRIPTION
			"Number of Rejects rcvd (result unexpected)"
	::= { otais41InstanceEntry	93 }

smscOtais41TcapPrbMtRrRcvd OBJECT-TYPE
		SYNTAX	Unsigned32
		MAX-ACCESS read-only
		STATUS current
		DESCRIPTION
			"Number of Rejects rcvd (result inc par)"
	::= { otais41InstanceEntry	94 }

smscOtais41TcapRjctReuciRcvd OBJECT-TYPE
		SYNTAX	Unsigned32
		MAX-ACCESS read-only
		STATUS current
		DESCRIPTION
			"Number of Rejects rcvd (error unass corr ID)"
	::= { otais41InstanceEntry	95 }

smscOtais41TcapRjctUnxpReRcvd OBJECT-TYPE
		SYNTAX	Unsigned32
		MAX-ACCESS read-only
		STATUS current
		DESCRIPTION
			"Number of Rejects rcvd (error unexp ret err)"
	::= { otais41InstanceEntry	96 }

smscOtais41TcapUserUnrecRcvd OBJECT-TYPE
		SYNTAX	Unsigned32
		MAX-ACCESS read-only
		STATUS current
		DESCRIPTION
			"Number of Rejects rcvd (error unrec err)"
	::= { otais41InstanceEntry	97 }

smscOtais41TcapUserUnxpRcvd OBJECT-TYPE
		SYNTAX	Unsigned32
		MAX-ACCESS read-only
		STATUS current
		DESCRIPTION
			"Number of Rejects rcvd (error unexpected)"
	::= { otais41InstanceEntry	98 }

smscOtais41TcapPrbMtReRcvd OBJECT-TYPE
		SYNTAX	Unsigned32
		MAX-ACCESS read-only
		STATUS current
		DESCRIPTION
			"Number of Rejects rcvd (error inc param)"
	::= { otais41InstanceEntry	99 }

smscOtais41TcapRjtUnrecmtRcvd OBJECT-TYPE
		SYNTAX	Unsigned32
		MAX-ACCESS read-only
		STATUS current
		DESCRIPTION
			"Number of Rejects rcvd (trans unrec package)"
	::= { otais41InstanceEntry	100 }

smscOtais41TcapRjtTranpRcvd OBJECT-TYPE
		SYNTAX	Unsigned32
		MAX-ACCESS read-only
		STATUS current
		DESCRIPTION
			"Number of Rejects rcvd (trans inc trans portion)"
	::= { otais41InstanceEntry	101 }

smscOtais41TcapRjtBftpRcvd OBJECT-TYPE
		SYNTAX	Unsigned32
		MAX-ACCESS read-only
		STATUS current
		DESCRIPTION
			"Number of Rejects rcvd (trans badly formed tp)"
	::= { otais41InstanceEntry	102 }

smscOtais41TcapRjtUnrecidRcvd OBJECT-TYPE
		SYNTAX	Unsigned32
		MAX-ACCESS read-only
		STATUS current
		DESCRIPTION
			"Number of Rejects rcvd (trans unassigned TID)"
	::= { otais41InstanceEntry	103 }

smscOtais41TcapRjctTp2rRcvd OBJECT-TYPE
		SYNTAX	Unsigned32
		MAX-ACCESS read-only
		STATUS current
		DESCRIPTION
			"Number of Rejects rcvd (trans permiss to rel)"
	::= { otais41InstanceEntry	104 }

smscOtais41TcapPrbReslimitRcvd OBJECT-TYPE
		SYNTAX	Unsigned32
		MAX-ACCESS read-only
		STATUS current
		DESCRIPTION
			"Number of Rejects rcvd (trans resource limit)"
	::= { otais41InstanceEntry	105 }

smscOtais41TcapAbtUnrecmtSnt OBJECT-TYPE
		SYNTAX	Unsigned32
		MAX-ACCESS read-only
		STATUS current
		DESCRIPTION
			"Number of Rejects sent (trans unrec msg type)"
	::= { otais41InstanceEntry	106 }

smscOtais41TcapAbtTranpSnt OBJECT-TYPE
		SYNTAX	Unsigned32
		MAX-ACCESS read-only
		STATUS current
		DESCRIPTION
			"Number of Rejects sent (trans inc trns portion)"
	::= { otais41InstanceEntry	107 }

smscOtais41TcapAbtBftpSnt OBJECT-TYPE
		SYNTAX	Unsigned32
		MAX-ACCESS read-only
		STATUS current
		DESCRIPTION
			"Number of Rejects sent (trans badly formed tp)"
	::= { otais41InstanceEntry	108 }

smscOtais41TcapAbtUnrecidSnt OBJECT-TYPE
		SYNTAX	Unsigned32
		MAX-ACCESS read-only
		STATUS current
		DESCRIPTION
			"Number of Rejects sent (unrec trns ID)"
	::= { otais41InstanceEntry	109 }

smscOtais41TcapRjctTp2rSnt OBJECT-TYPE
		SYNTAX	Unsigned32
		MAX-ACCESS read-only
		STATUS current
		DESCRIPTION
			"Number of Rejects sent (trans perm to release)"
	::= { otais41InstanceEntry	110 }

smscOtais41TcapAbtReslimitSnt OBJECT-TYPE
		SYNTAX	Unsigned32
		MAX-ACCESS read-only
		STATUS current
		DESCRIPTION
			"Number of Rejects sent (trans res lim)"
	::= { otais41InstanceEntry	111 }

smscOtais41TcapRjctUctSnt OBJECT-TYPE
		SYNTAX	Unsigned32
		MAX-ACCESS read-only
		STATUS current
		DESCRIPTION
			"Number of Rejects sent (unrec comp type)"
	::= { otais41InstanceEntry	112 }

smscOtais41TcapRjctIcpSnt OBJECT-TYPE
		SYNTAX	Unsigned32
		MAX-ACCESS read-only
		STATUS current
		DESCRIPTION
			"Number of Rejects sent (inc comp portion)"
	::= { otais41InstanceEntry	113 }

smscOtais41TcapRjctBscpSnt OBJECT-TYPE
		SYNTAX	Unsigned32
		MAX-ACCESS read-only
		STATUS current
		DESCRIPTION
			"Number of Rejects sent (badly str comp)"
	::= { otais41InstanceEntry	114 }

smscOtais41TcapRjctIccSnt OBJECT-TYPE
		SYNTAX	Unsigned32
		MAX-ACCESS read-only
		STATUS current
		DESCRIPTION
			"Number of Rejects sent (inc comp coding)"
	::= { otais41InstanceEntry	115 }

smscOtais41TcapRjctIvdidSnt OBJECT-TYPE
		SYNTAX	Unsigned32
		MAX-ACCESS read-only
		STATUS current
		DESCRIPTION
			"Number of Rejects sent (inv dup invk ID)"
	::= { otais41InstanceEntry	116 }

smscOtais41TcapRjctIvuocSnt OBJECT-TYPE
		SYNTAX	Unsigned32
		MAX-ACCESS read-only
		STATUS current
		DESCRIPTION
			"Number of Rejects sent (inv unrec oper)"
	::= { otais41InstanceEntry	117 }

smscOtais41TcapRjctIviparSnt OBJECT-TYPE
		SYNTAX	Unsigned32
		MAX-ACCESS read-only
		STATUS current
		DESCRIPTION
			"Number of Rejects sent (inv inc param)"
	::= { otais41InstanceEntry	118 }

smscOtais41TcapRjctUcidSnt OBJECT-TYPE
		SYNTAX	Unsigned32
		MAX-ACCESS read-only
		STATUS current
		DESCRIPTION
			"Number of Rejects sent (inv unrec corr ID)"
	::= { otais41InstanceEntry	119 }

smscOtais41TcapRjctRruciSnt OBJECT-TYPE
		SYNTAX	Unsigned32
		MAX-ACCESS read-only
		STATUS current
		DESCRIPTION
			"Number of Rejects sent (result unass corr ID)"
	::= { otais41InstanceEntry	120 }

smscOtais41TcapRjctRrurrSnt OBJECT-TYPE
		SYNTAX	Unsigned32
		MAX-ACCESS read-only
		STATUS current
		DESCRIPTION
			"Number of Rejects sent (result unexp result)"
	::= { otais41InstanceEntry	121 }

smscOtais41TcapRjctRripSnt OBJECT-TYPE
		SYNTAX	Unsigned32
		MAX-ACCESS read-only
		STATUS current
		DESCRIPTION
			"Number of Rejects sent (result inc param)"
	::= { otais41InstanceEntry	122 }

smscOtais41TcapRjctEruciSnt OBJECT-TYPE
		SYNTAX	Unsigned32
		MAX-ACCESS read-only
		STATUS current
		DESCRIPTION
			"Number of Rejects sent (error unass corr ID)"
	::= { otais41InstanceEntry	123 }

smscOtais41TcapRjctErureSnt OBJECT-TYPE
		SYNTAX	Unsigned32
		MAX-ACCESS read-only
		STATUS current
		DESCRIPTION
			"Number of Rejects sent (error unexp ret error)"
	::= { otais41InstanceEntry	124 }

smscOtais41TcapRjctErueSnt OBJECT-TYPE
		SYNTAX	Unsigned32
		MAX-ACCESS read-only
		STATUS current
		DESCRIPTION
			"Number of Rejects sent (error unrec error)"
	::= { otais41InstanceEntry	125 }

smscOtais41TcapRjctErunxSnt OBJECT-TYPE
		SYNTAX	Unsigned32
		MAX-ACCESS read-only
		STATUS current
		DESCRIPTION
			"Number of Rejects sent (error unexp error)"
	::= { otais41InstanceEntry	126 }

smscOtais41TcapRjctEripSnt OBJECT-TYPE
		SYNTAX	Unsigned32
		MAX-ACCESS read-only
		STATUS current
		DESCRIPTION
			"Number of Rejects sent (error inc param)"
	::= { otais41InstanceEntry	127 }

smscOtais41TcapActiveDialog OBJECT-TYPE
		SYNTAX	Unsigned32
		MAX-ACCESS read-only
		STATUS current
		DESCRIPTION
			"Number of simultaneous active TCAP dialogues"
	::= { otais41InstanceEntry	128 }

smscOtais41TcapInitiatedDialog OBJECT-TYPE
		SYNTAX	Unsigned32
		MAX-ACCESS read-only
		STATUS current
		DESCRIPTION
			"Number of simultaneous initiated TCAP dialogues"
	::= { otais41InstanceEntry	129 }

smscOtais41TcapUnknMsgRcvd OBJECT-TYPE
		SYNTAX	Unsigned32
		MAX-ACCESS read-only
		STATUS current
		DESCRIPTION
			"Number of incorrect or unknown TCAP msgs received"
	::= { otais41InstanceEntry	130 }

smscOtais41TcapNoticeRcvd OBJECT-TYPE
		SYNTAX	Unsigned32
		MAX-ACCESS read-only
		STATUS current
		DESCRIPTION
			"Number of Notice rcvd"
	::= { otais41InstanceEntry	131 }



-- end of OTAIS41 description.
-- --------------------------------------


-- --------------------------------------
-- Class PHLR
-- 
smscPhlr OBJECT-TYPE
	SYNTAX  SEQUENCE OF PhlrInstanceEntry
	MAX-ACCESS  not-accessible
	STATUS  current
	DESCRIPTION
		"Mapping table for SMSC PHLR entities."
   ::= { smscClassServer   14  }

phlrInstanceEntry  OBJECT-TYPE
	SYNTAX PhlrInstanceEntry
	MAX-ACCESS  not-accessible
	STATUS  current
	DESCRIPTION
		"An entry (row) in the entityInstanceTable."
	INDEX { IMPLIED smscPhlrName }
   ::= { smscPhlr 1 }

PhlrInstanceEntry ::= SEQUENCE {
		smscPhlrName     DisplayString,
		smscPhlrState   INTEGER,
		smscPhlrLastupdate   TimeTicks,
		smscPhlrNode	   DisplayString, 
		smscPhlrMsgReceived	 Unsigned32, 
		smscPhlrMsgRejected	 Unsigned32, 
		smscPhlrMsgTransmitted	 Unsigned32, 
		smscPhlrMsgFailed	 Unsigned32, 
		smscPhlrQelemUsed	 Unsigned32, 
		smscPhlrQelemInProcqueue	 Unsigned32, 
		smscPhlrQelemInExpqueue	 Unsigned32, 
		smscPhlrNrTimersRunning	 Unsigned32, 
		smscPhlrNrSystemTimers	 Unsigned32, 
		smscPhlrImiRecallQelem	 Unsigned32, 
		smscPhlrImiRecallQueues	 Unsigned32, 
		smscPhlrIdiRecallQelem	 Unsigned32, 
		smscPhlrIdiRecallQueues	 Unsigned32, 
		smscPhlrIosRecallQelem	 Unsigned32, 
		smscPhlrIosRecallQueues	 Unsigned32, 
		smscPhlrLogRecallQelem	 Unsigned32, 
		smscPhlrLogRecallQueues	 Unsigned32, 
		smscPhlrTrcreqDiscarded	 Unsigned32, 
		smscPhlrRegnotAccepted	 Unsigned32, 
		smscPhlrRegnotRejected	 Unsigned32, 
		smscPhlrRegcancAccepted	 Unsigned32, 
		smscPhlrRegcancRejected	 Unsigned32, 
		smscPhlrMsinactAccepted	 Unsigned32, 
		smscPhlrMsinactRejected	 Unsigned32, 
		smscPhlrOrreqAccepted	 Unsigned32, 
		smscPhlrOrreqRejected	 Unsigned32, 
		smscPhlrSmsnotOk	 Unsigned32, 
		smscPhlrSmsnotFail	 Unsigned32, 
		smscPhlrSmsreqAccepted	 Unsigned32, 
		smscPhlrSmsreqRejected	 Unsigned32, 
		smscPhlrDialogues	 Unsigned32, 
		smscPhlrDialoguesPending	 Unsigned32, 
		smscPhlrSessionsPending	 Unsigned32, 
		smscPhlrTcapErrors	 Unsigned32, 
		smscPhlrTcapBeginRcvd	 Unsigned32, 
		smscPhlrTcapContRcvd	 Unsigned32, 
		smscPhlrTcapEndRcvd	 Unsigned32, 
		smscPhlrTcapBeginSnt	 Unsigned32, 
		smscPhlrTcapEndSnt	 Unsigned32, 
		smscPhlrTcapFailedSent	 Unsigned32, 
		smscPhlrTcapTransDisc	 Unsigned32, 
		smscPhlrTcapMsgDisc	 Unsigned32, 
		smscPhlrTcapAbtRcvd	 Unsigned32, 
		smscPhlrTcapAbtUnrecmtRcvd	 Unsigned32, 
		smscPhlrTcapAbtTranpRcvd	 Unsigned32, 
		smscPhlrTcapAbtBftpRcvd	 Unsigned32, 
		smscPhlrTcapAbtUnrecidRcvd	 Unsigned32, 
		smscPhlrTcapAbtReslimitRcvd	 Unsigned32, 
		smscPhlrTcapAbtAbnormRcvd	 Unsigned32, 
		smscPhlrTcapUabtRcvd	 Unsigned32, 
		smscPhlrTcapInvkRcvd	 Unsigned32, 
		smscPhlrTcapInvknlRcvd	 Unsigned32, 
		smscPhlrTcapInvkSnt	 Unsigned32, 
		smscPhlrTcapResLastRcvd	 Unsigned32, 
		smscPhlrTcapResNolastRcvd	 Unsigned32, 
		smscPhlrTcapResLastSnt	 Unsigned32, 
		smscPhlrTcapErrorRcvd	 Unsigned32, 
		smscPhlrTcapErrorSnt	 Unsigned32, 
		smscPhlrTcapRejectSnt	 Unsigned32, 
		smscPhlrTcapRejectRcvd	 Unsigned32, 
		smscPhlrTcapRjctUnrecRcvd	 Unsigned32, 
		smscPhlrTcapRjctIcpRcvd	 Unsigned32, 
		smscPhlrTcapRjctBadsRcvd	 Unsigned32, 
		smscPhlrTcapRjctIccRcvd	 Unsigned32, 
		smscPhlrTcapRjctDupIidRcvd	 Unsigned32, 
		smscPhlrTcapPrbUnrecOpRcvd	 Unsigned32, 
		smscPhlrTcapPrbMistypeRcvd	 Unsigned32, 
		smscPhlrTcapRjctUnrLidRcvd	 Unsigned32, 
		smscPhlrTcapRjctRruciRcvd	 Unsigned32, 
		smscPhlrTcapRjctUnxpRrRcvd	 Unsigned32, 
		smscPhlrTcapPrbMtRrRcvd	 Unsigned32, 
		smscPhlrTcapRjctReuciRcvd	 Unsigned32, 
		smscPhlrTcapRjctUnxpReRcvd	 Unsigned32, 
		smscPhlrTcapUserUnrecRcvd	 Unsigned32, 
		smscPhlrTcapUserUnxpRcvd	 Unsigned32, 
		smscPhlrTcapPrbMtReRcvd	 Unsigned32, 
		smscPhlrTcapRjtUnrecmtRcvd	 Unsigned32, 
		smscPhlrTcapRjtTranpRcvd	 Unsigned32, 
		smscPhlrTcapRjtBftpRcvd	 Unsigned32, 
		smscPhlrTcapRjtUnrecidRcvd	 Unsigned32, 
		smscPhlrTcapRjctTp2rRcvd	 Unsigned32, 
		smscPhlrTcapPrbReslimitRcvd	 Unsigned32, 
		smscPhlrTcapAbtUnrecmtSnt	 Unsigned32, 
		smscPhlrTcapAbtTranpSnt	 Unsigned32, 
		smscPhlrTcapAbtBftpSnt	 Unsigned32, 
		smscPhlrTcapAbtUnrecidSnt	 Unsigned32, 
		smscPhlrTcapRjctTp2rSnt	 Unsigned32, 
		smscPhlrTcapAbtReslimitSnt	 Unsigned32, 
		smscPhlrTcapRjctUctSnt	 Unsigned32, 
		smscPhlrTcapRjctIcpSnt	 Unsigned32, 
		smscPhlrTcapRjctBscpSnt	 Unsigned32, 
		smscPhlrTcapRjctIccSnt	 Unsigned32, 
		smscPhlrTcapRjctIvdidSnt	 Unsigned32, 
		smscPhlrTcapRjctIvuocSnt	 Unsigned32, 
		smscPhlrTcapRjctIviparSnt	 Unsigned32, 
		smscPhlrTcapRjctUcidSnt	 Unsigned32, 
		smscPhlrTcapRjctRruciSnt	 Unsigned32, 
		smscPhlrTcapRjctRrurrSnt	 Unsigned32, 
		smscPhlrTcapRjctRripSnt	 Unsigned32, 
		smscPhlrTcapRjctEruciSnt	 Unsigned32, 
		smscPhlrTcapRjctErureSnt	 Unsigned32, 
		smscPhlrTcapRjctErueSnt	 Unsigned32, 
		smscPhlrTcapRjctErunxSnt	 Unsigned32, 
		smscPhlrTcapRjctEripSnt	 Unsigned32, 
		smscPhlrTcapActiveDialog	 Unsigned32, 
		smscPhlrTcapInitiatedDialog	 Unsigned32, 
		smscPhlrTcapUnknMsgRcvd	 Unsigned32, 
		smscPhlrTcapNoticeRcvd	 Unsigned32
	}

smscPhlrName  OBJECT-TYPE
	SYNTAX  DisplayString
	MAX-ACCESS  read-only
	STATUS   current
	DESCRIPTION
		"Identifies the name of the entity."
   ::= {phlrInstanceEntry 1 }

smscPhlrState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { phlrInstanceEntry 2 }


smscPhlrLastupdate OBJECT-TYPE
		SYNTAX	TimeTicks
		MAX-ACCESS read-only
		STATUS current
		DESCRIPTION
			"Value which reflects the last time the entities fields have been updated"
	::= { phlrInstanceEntry	3 }

smscPhlrNode  OBJECT-TYPE
	SYNTAX  DisplayString
	MAX-ACCESS  read-only
	STATUS   current
	DESCRIPTION
		"Identifies the node the entity is running on."
   ::= {phlrInstanceEntry 4 }

smscPhlrMsgReceived OBJECT-TYPE
		SYNTAX	Unsigned32
		MAX-ACCESS read-only
		STATUS current
		DESCRIPTION
			"Received messages"
	::= { phlrInstanceEntry	5 }

smscPhlrMsgRejected OBJECT-TYPE
		SYNTAX	Unsigned32
		MAX-ACCESS read-only
		STATUS current
		DESCRIPTION
			"Received messages and rejected"
	::= { phlrInstanceEntry	6 }

smscPhlrMsgTransmitted OBJECT-TYPE
		SYNTAX	Unsigned32
		MAX-ACCESS read-only
		STATUS current
		DESCRIPTION
			"Transmitted messages"
	::= { phlrInstanceEntry	7 }

smscPhlrMsgFailed OBJECT-TYPE
		SYNTAX	Unsigned32
		MAX-ACCESS read-only
		STATUS current
		DESCRIPTION
			"Messages that failed on sending"
	::= { phlrInstanceEntry	8 }

smscPhlrQelemUsed OBJECT-TYPE
		SYNTAX	Unsigned32
		MAX-ACCESS read-only
		STATUS current
		DESCRIPTION
			"Number of elements in internal queues"
	::= { phlrInstanceEntry	9 }

smscPhlrQelemInProcqueue OBJECT-TYPE
		SYNTAX	Unsigned32
		MAX-ACCESS read-only
		STATUS current
		DESCRIPTION
			"Number of elements used in process queue"
	::= { phlrInstanceEntry	10 }

smscPhlrQelemInExpqueue OBJECT-TYPE
		SYNTAX	Unsigned32
		MAX-ACCESS read-only
		STATUS current
		DESCRIPTION
			"Number of elements used in expedited queue"
	::= { phlrInstanceEntry	11 }

smscPhlrNrTimersRunning OBJECT-TYPE
		SYNTAX	Unsigned32
		MAX-ACCESS read-only
		STATUS current
		DESCRIPTION
			"Total number of timers running"
	::= { phlrInstanceEntry	12 }

smscPhlrNrSystemTimers OBJECT-TYPE
		SYNTAX	Unsigned32
		MAX-ACCESS read-only
		STATUS current
		DESCRIPTION
			"Number of system timers running"
	::= { phlrInstanceEntry	13 }

smscPhlrImiRecallQelem OBJECT-TYPE
		SYNTAX	Unsigned32
		MAX-ACCESS read-only
		STATUS current
		DESCRIPTION
			"Number of IMI recall-queue elements used"
	::= { phlrInstanceEntry	14 }

smscPhlrImiRecallQueues OBJECT-TYPE
		SYNTAX	Unsigned32
		MAX-ACCESS read-only
		STATUS current
		DESCRIPTION
			"Number of IMI-recall-queues used"
	::= { phlrInstanceEntry	15 }

smscPhlrIdiRecallQelem OBJECT-TYPE
		SYNTAX	Unsigned32
		MAX-ACCESS read-only
		STATUS current
		DESCRIPTION
			"Number of IDI recall-queue elements used"
	::= { phlrInstanceEntry	16 }

smscPhlrIdiRecallQueues OBJECT-TYPE
		SYNTAX	Unsigned32
		MAX-ACCESS read-only
		STATUS current
		DESCRIPTION
			"Number of IDI recall-queues used"
	::= { phlrInstanceEntry	17 }

smscPhlrIosRecallQelem OBJECT-TYPE
		SYNTAX	Unsigned32
		MAX-ACCESS read-only
		STATUS current
		DESCRIPTION
			"Number of IOS recall-queue elements used"
	::= { phlrInstanceEntry	18 }

smscPhlrIosRecallQueues OBJECT-TYPE
		SYNTAX	Unsigned32
		MAX-ACCESS read-only
		STATUS current
		DESCRIPTION
			"Number of IOS recall-queues used"
	::= { phlrInstanceEntry	19 }

smscPhlrLogRecallQelem OBJECT-TYPE
		SYNTAX	Unsigned32
		MAX-ACCESS read-only
		STATUS current
		DESCRIPTION
			"Number of LOG recall-queue elements used"
	::= { phlrInstanceEntry	20 }

smscPhlrLogRecallQueues OBJECT-TYPE
		SYNTAX	Unsigned32
		MAX-ACCESS read-only
		STATUS current
		DESCRIPTION
			"Number of LOG recall-queues used"
	::= { phlrInstanceEntry	21 }

smscPhlrTrcreqDiscarded OBJECT-TYPE
		SYNTAX	Unsigned32
		MAX-ACCESS read-only
		STATUS current
		DESCRIPTION
			"Number of trace requests discarded"
	::= { phlrInstanceEntry	22 }

smscPhlrRegnotAccepted OBJECT-TYPE
		SYNTAX	Unsigned32
		MAX-ACCESS read-only
		STATUS current
		DESCRIPTION
			"Number of accepted Registration-Notifications"
	::= { phlrInstanceEntry	23 }

smscPhlrRegnotRejected OBJECT-TYPE
		SYNTAX	Unsigned32
		MAX-ACCESS read-only
		STATUS current
		DESCRIPTION
			"Number of rejected Registration-Notifications"
	::= { phlrInstanceEntry	24 }

smscPhlrRegcancAccepted OBJECT-TYPE
		SYNTAX	Unsigned32
		MAX-ACCESS read-only
		STATUS current
		DESCRIPTION
			"Number of accepted Registration-Cancels"
	::= { phlrInstanceEntry	25 }

smscPhlrRegcancRejected OBJECT-TYPE
		SYNTAX	Unsigned32
		MAX-ACCESS read-only
		STATUS current
		DESCRIPTION
			"Number of rejected Registration-Cancels"
	::= { phlrInstanceEntry	26 }

smscPhlrMsinactAccepted OBJECT-TYPE
		SYNTAX	Unsigned32
		MAX-ACCESS read-only
		STATUS current
		DESCRIPTION
			"Number of accepted MS-Inactives"
	::= { phlrInstanceEntry	27 }

smscPhlrMsinactRejected OBJECT-TYPE
		SYNTAX	Unsigned32
		MAX-ACCESS read-only
		STATUS current
		DESCRIPTION
			"Number of rejected MS-Inactives"
	::= { phlrInstanceEntry	28 }

smscPhlrOrreqAccepted OBJECT-TYPE
		SYNTAX	Unsigned32
		MAX-ACCESS read-only
		STATUS current
		DESCRIPTION
			"Number of accepted Origination Requests"
	::= { phlrInstanceEntry	29 }

smscPhlrOrreqRejected OBJECT-TYPE
		SYNTAX	Unsigned32
		MAX-ACCESS read-only
		STATUS current
		DESCRIPTION
			"Number of rejected Origination Requests"
	::= { phlrInstanceEntry	30 }

smscPhlrSmsnotOk OBJECT-TYPE
		SYNTAX	Unsigned32
		MAX-ACCESS read-only
		STATUS current
		DESCRIPTION
			"Number of delivered SMS-Notifications"
	::= { phlrInstanceEntry	31 }

smscPhlrSmsnotFail OBJECT-TYPE
		SYNTAX	Unsigned32
		MAX-ACCESS read-only
		STATUS current
		DESCRIPTION
			"Number of failed SMS-Notifications"
	::= { phlrInstanceEntry	32 }

smscPhlrSmsreqAccepted OBJECT-TYPE
		SYNTAX	Unsigned32
		MAX-ACCESS read-only
		STATUS current
		DESCRIPTION
			"Number of accepted SMS-Requests"
	::= { phlrInstanceEntry	33 }

smscPhlrSmsreqRejected OBJECT-TYPE
		SYNTAX	Unsigned32
		MAX-ACCESS read-only
		STATUS current
		DESCRIPTION
			"Number of rejected SMS-Requests"
	::= { phlrInstanceEntry	34 }

smscPhlrDialogues OBJECT-TYPE
		SYNTAX	Unsigned32
		MAX-ACCESS read-only
		STATUS current
		DESCRIPTION
			"Number of dialogues"
	::= { phlrInstanceEntry	35 }

smscPhlrDialoguesPending OBJECT-TYPE
		SYNTAX	Unsigned32
		MAX-ACCESS read-only
		STATUS current
		DESCRIPTION
			"Number of dialogues (currently) pending"
	::= { phlrInstanceEntry	36 }

smscPhlrSessionsPending OBJECT-TYPE
		SYNTAX	Unsigned32
		MAX-ACCESS read-only
		STATUS current
		DESCRIPTION
			"Number of sessions (currently) pending"
	::= { phlrInstanceEntry	37 }

smscPhlrTcapErrors OBJECT-TYPE
		SYNTAX	Unsigned32
		MAX-ACCESS read-only
		STATUS current
		DESCRIPTION
			"Number of TCAP errors/problems"
	::= { phlrInstanceEntry	38 }

smscPhlrTcapBeginRcvd OBJECT-TYPE
		SYNTAX	Unsigned32
		MAX-ACCESS read-only
		STATUS current
		DESCRIPTION
			"Number of Begin Dialogue transactions received"
	::= { phlrInstanceEntry	39 }

smscPhlrTcapContRcvd OBJECT-TYPE
		SYNTAX	Unsigned32
		MAX-ACCESS read-only
		STATUS current
		DESCRIPTION
			"Number of Continue transactions received"
	::= { phlrInstanceEntry	40 }

smscPhlrTcapEndRcvd OBJECT-TYPE
		SYNTAX	Unsigned32
		MAX-ACCESS read-only
		STATUS current
		DESCRIPTION
			"Number of End transactions received"
	::= { phlrInstanceEntry	41 }

smscPhlrTcapBeginSnt OBJECT-TYPE
		SYNTAX	Unsigned32
		MAX-ACCESS read-only
		STATUS current
		DESCRIPTION
			"Number of Begin Dialogue transactions sent"
	::= { phlrInstanceEntry	42 }

smscPhlrTcapEndSnt OBJECT-TYPE
		SYNTAX	Unsigned32
		MAX-ACCESS read-only
		STATUS current
		DESCRIPTION
			"Number of End transactions sent"
	::= { phlrInstanceEntry	43 }

smscPhlrTcapFailedSent OBJECT-TYPE
		SYNTAX	Unsigned32
		MAX-ACCESS read-only
		STATUS current
		DESCRIPTION
			"Number of Message failed to be sent"
	::= { phlrInstanceEntry	44 }

smscPhlrTcapTransDisc OBJECT-TYPE
		SYNTAX	Unsigned32
		MAX-ACCESS read-only
		STATUS current
		DESCRIPTION
			"Number of discarded msgs due to transport problem"
	::= { phlrInstanceEntry	45 }

smscPhlrTcapMsgDisc OBJECT-TYPE
		SYNTAX	Unsigned32
		MAX-ACCESS read-only
		STATUS current
		DESCRIPTION
			"Number of discarded TCAP messages"
	::= { phlrInstanceEntry	46 }

smscPhlrTcapAbtRcvd OBJECT-TYPE
		SYNTAX	Unsigned32
		MAX-ACCESS read-only
		STATUS current
		DESCRIPTION
			"Number of P_ABORT transacs rcvd"
	::= { phlrInstanceEntry	47 }

smscPhlrTcapAbtUnrecmtRcvd OBJECT-TYPE
		SYNTAX	Unsigned32
		MAX-ACCESS read-only
		STATUS current
		DESCRIPTION
			"Number of P_ABORT transacs rcvd (unrec msg type)"
	::= { phlrInstanceEntry	48 }

smscPhlrTcapAbtTranpRcvd OBJECT-TYPE
		SYNTAX	Unsigned32
		MAX-ACCESS read-only
		STATUS current
		DESCRIPTION
			"Number of P_ABORT msgs rcvd (inc trans portion)"
	::= { phlrInstanceEntry	49 }

smscPhlrTcapAbtBftpRcvd OBJECT-TYPE
		SYNTAX	Unsigned32
		MAX-ACCESS read-only
		STATUS current
		DESCRIPTION
			"Number of P_ABORT msgs rcvd (badly formed tp)"
	::= { phlrInstanceEntry	50 }

smscPhlrTcapAbtUnrecidRcvd OBJECT-TYPE
		SYNTAX	Unsigned32
		MAX-ACCESS read-only
		STATUS current
		DESCRIPTION
			"Number of P_ABORT msgs rcvd (unrec trans id)"
	::= { phlrInstanceEntry	51 }

smscPhlrTcapAbtReslimitRcvd OBJECT-TYPE
		SYNTAX	Unsigned32
		MAX-ACCESS read-only
		STATUS current
		DESCRIPTION
			"Number of P_ABORT msgs rcvd (resouce limitation)"
	::= { phlrInstanceEntry	52 }

smscPhlrTcapAbtAbnormRcvd OBJECT-TYPE
		SYNTAX	Unsigned32
		MAX-ACCESS read-only
		STATUS current
		DESCRIPTION
			"Number of P_ABORT msgs rcvd (abnormal dialog)"
	::= { phlrInstanceEntry	53 }

smscPhlrTcapUabtRcvd OBJECT-TYPE
		SYNTAX	Unsigned32
		MAX-ACCESS read-only
		STATUS current
		DESCRIPTION
			"Number of U_ABORT transactions received"
	::= { phlrInstanceEntry	54 }

smscPhlrTcapInvkRcvd OBJECT-TYPE
		SYNTAX	Unsigned32
		MAX-ACCESS read-only
		STATUS current
		DESCRIPTION
			"Number of Invoke Last components received"
	::= { phlrInstanceEntry	55 }

smscPhlrTcapInvknlRcvd OBJECT-TYPE
		SYNTAX	Unsigned32
		MAX-ACCESS read-only
		STATUS current
		DESCRIPTION
			"Number of Invoke Not Last components received"
	::= { phlrInstanceEntry	56 }

smscPhlrTcapInvkSnt OBJECT-TYPE
		SYNTAX	Unsigned32
		MAX-ACCESS read-only
		STATUS current
		DESCRIPTION
			"Number of Invoke Last components sent"
	::= { phlrInstanceEntry	57 }

smscPhlrTcapResLastRcvd OBJECT-TYPE
		SYNTAX	Unsigned32
		MAX-ACCESS read-only
		STATUS current
		DESCRIPTION
			"Number of Result Last components received"
	::= { phlrInstanceEntry	58 }

smscPhlrTcapResNolastRcvd OBJECT-TYPE
		SYNTAX	Unsigned32
		MAX-ACCESS read-only
		STATUS current
		DESCRIPTION
			"Number of Result No Last components received"
	::= { phlrInstanceEntry	59 }

smscPhlrTcapResLastSnt OBJECT-TYPE
		SYNTAX	Unsigned32
		MAX-ACCESS read-only
		STATUS current
		DESCRIPTION
			"Number of Result Last components sent"
	::= { phlrInstanceEntry	60 }

smscPhlrTcapErrorRcvd OBJECT-TYPE
		SYNTAX	Unsigned32
		MAX-ACCESS read-only
		STATUS current
		DESCRIPTION
			"Number of Error components received"
	::= { phlrInstanceEntry	61 }

smscPhlrTcapErrorSnt OBJECT-TYPE
		SYNTAX	Unsigned32
		MAX-ACCESS read-only
		STATUS current
		DESCRIPTION
			"Number of Error components sent"
	::= { phlrInstanceEntry	62 }

smscPhlrTcapRejectSnt OBJECT-TYPE
		SYNTAX	Unsigned32
		MAX-ACCESS read-only
		STATUS current
		DESCRIPTION
			"Number of Reject components sent"
	::= { phlrInstanceEntry	63 }

smscPhlrTcapRejectRcvd OBJECT-TYPE
		SYNTAX	Unsigned32
		MAX-ACCESS read-only
		STATUS current
		DESCRIPTION
			"Number of Reject components rcvd"
	::= { phlrInstanceEntry	64 }

smscPhlrTcapRjctUnrecRcvd OBJECT-TYPE
		SYNTAX	Unsigned32
		MAX-ACCESS read-only
		STATUS current
		DESCRIPTION
			"Number of Reject components rcvd (unrec comp type)"
	::= { phlrInstanceEntry	65 }

smscPhlrTcapRjctIcpRcvd OBJECT-TYPE
		SYNTAX	Unsigned32
		MAX-ACCESS read-only
		STATUS current
		DESCRIPTION
			"Number of Reject components rcvd (incor comp por)"
	::= { phlrInstanceEntry	66 }

smscPhlrTcapRjctBadsRcvd OBJECT-TYPE
		SYNTAX	Unsigned32
		MAX-ACCESS read-only
		STATUS current
		DESCRIPTION
			"Number of Reject components rcvd(badly struct comp)"
	::= { phlrInstanceEntry	67 }

smscPhlrTcapRjctIccRcvd OBJECT-TYPE
		SYNTAX	Unsigned32
		MAX-ACCESS read-only
		STATUS current
		DESCRIPTION
			"Number of Reject components rcvd(incorr comp codding)"
	::= { phlrInstanceEntry	68 }

smscPhlrTcapRjctDupIidRcvd OBJECT-TYPE
		SYNTAX	Unsigned32
		MAX-ACCESS read-only
		STATUS current
		DESCRIPTION
			"Number of Rejects rcvd (invoke dup id)"
	::= { phlrInstanceEntry	69 }

smscPhlrTcapPrbUnrecOpRcvd OBJECT-TYPE
		SYNTAX	Unsigned32
		MAX-ACCESS read-only
		STATUS current
		DESCRIPTION
			"Number of Rejects rcvd (invoke unrec oper)"
	::= { phlrInstanceEntry	70 }

smscPhlrTcapPrbMistypeRcvd OBJECT-TYPE
		SYNTAX	Unsigned32
		MAX-ACCESS read-only
		STATUS current
		DESCRIPTION
			"Number of Rejects rcvd (incor param)"
	::= { phlrInstanceEntry	71 }

smscPhlrTcapRjctUnrLidRcvd OBJECT-TYPE
		SYNTAX	Unsigned32
		MAX-ACCESS read-only
		STATUS current
		DESCRIPTION
			"Number of Rejects rcvd (invoke unrec corr ID)"
	::= { phlrInstanceEntry	72 }

smscPhlrTcapRjctRruciRcvd OBJECT-TYPE
		SYNTAX	Unsigned32
		MAX-ACCESS read-only
		STATUS current
		DESCRIPTION
			"Number of Rejects rcvd (result unass corr ID)"
	::= { phlrInstanceEntry	73 }

smscPhlrTcapRjctUnxpRrRcvd OBJECT-TYPE
		SYNTAX	Unsigned32
		MAX-ACCESS read-only
		STATUS current
		DESCRIPTION
			"Number of Rejects rcvd (result unexpected)"
	::= { phlrInstanceEntry	74 }

smscPhlrTcapPrbMtRrRcvd OBJECT-TYPE
		SYNTAX	Unsigned32
		MAX-ACCESS read-only
		STATUS current
		DESCRIPTION
			"Number of Rejects rcvd (result inc par)"
	::= { phlrInstanceEntry	75 }

smscPhlrTcapRjctReuciRcvd OBJECT-TYPE
		SYNTAX	Unsigned32
		MAX-ACCESS read-only
		STATUS current
		DESCRIPTION
			"Number of Rejects rcvd (error unass corr ID)"
	::= { phlrInstanceEntry	76 }

smscPhlrTcapRjctUnxpReRcvd OBJECT-TYPE
		SYNTAX	Unsigned32
		MAX-ACCESS read-only
		STATUS current
		DESCRIPTION
			"Number of Rejects rcvd (error unexp ret err)"
	::= { phlrInstanceEntry	77 }

smscPhlrTcapUserUnrecRcvd OBJECT-TYPE
		SYNTAX	Unsigned32
		MAX-ACCESS read-only
		STATUS current
		DESCRIPTION
			"Number of Rejects rcvd (error unrec err)"
	::= { phlrInstanceEntry	78 }

smscPhlrTcapUserUnxpRcvd OBJECT-TYPE
		SYNTAX	Unsigned32
		MAX-ACCESS read-only
		STATUS current
		DESCRIPTION
			"Number of Rejects rcvd (error unexpected)"
	::= { phlrInstanceEntry	79 }

smscPhlrTcapPrbMtReRcvd OBJECT-TYPE
		SYNTAX	Unsigned32
		MAX-ACCESS read-only
		STATUS current
		DESCRIPTION
			"Number of Rejects rcvd (error inc param)"
	::= { phlrInstanceEntry	80 }

smscPhlrTcapRjtUnrecmtRcvd OBJECT-TYPE
		SYNTAX	Unsigned32
		MAX-ACCESS read-only
		STATUS current
		DESCRIPTION
			"Number of Rejects rcvd (trans unrec package)"
	::= { phlrInstanceEntry	81 }

smscPhlrTcapRjtTranpRcvd OBJECT-TYPE
		SYNTAX	Unsigned32
		MAX-ACCESS read-only
		STATUS current
		DESCRIPTION
			"Number of Rejects rcvd (trans inc trans portion)"
	::= { phlrInstanceEntry	82 }

smscPhlrTcapRjtBftpRcvd OBJECT-TYPE
		SYNTAX	Unsigned32
		MAX-ACCESS read-only
		STATUS current
		DESCRIPTION
			"Number of Rejects rcvd (trans badly formed tp)"
	::= { phlrInstanceEntry	83 }

smscPhlrTcapRjtUnrecidRcvd OBJECT-TYPE
		SYNTAX	Unsigned32
		MAX-ACCESS read-only
		STATUS current
		DESCRIPTION
			"Number of Rejects rcvd (trans unassigned TID)"
	::= { phlrInstanceEntry	84 }

smscPhlrTcapRjctTp2rRcvd OBJECT-TYPE
		SYNTAX	Unsigned32
		MAX-ACCESS read-only
		STATUS current
		DESCRIPTION
			"Number of Rejects rcvd (trans permiss to rel)"
	::= { phlrInstanceEntry	85 }

smscPhlrTcapPrbReslimitRcvd OBJECT-TYPE
		SYNTAX	Unsigned32
		MAX-ACCESS read-only
		STATUS current
		DESCRIPTION
			"Number of Rejects rcvd (trans resource limit)"
	::= { phlrInstanceEntry	86 }

smscPhlrTcapAbtUnrecmtSnt OBJECT-TYPE
		SYNTAX	Unsigned32
		MAX-ACCESS read-only
		STATUS current
		DESCRIPTION
			"Number of Rejects sent (trans unrec msg type)"
	::= { phlrInstanceEntry	87 }

smscPhlrTcapAbtTranpSnt OBJECT-TYPE
		SYNTAX	Unsigned32
		MAX-ACCESS read-only
		STATUS current
		DESCRIPTION
			"Number of Rejects sent (trans inc trns portion)"
	::= { phlrInstanceEntry	88 }

smscPhlrTcapAbtBftpSnt OBJECT-TYPE
		SYNTAX	Unsigned32
		MAX-ACCESS read-only
		STATUS current
		DESCRIPTION
			"Number of Rejects sent (trans badly formed tp)"
	::= { phlrInstanceEntry	89 }

smscPhlrTcapAbtUnrecidSnt OBJECT-TYPE
		SYNTAX	Unsigned32
		MAX-ACCESS read-only
		STATUS current
		DESCRIPTION
			"Number of Rejects sent (unrec trns ID)"
	::= { phlrInstanceEntry	90 }

smscPhlrTcapRjctTp2rSnt OBJECT-TYPE
		SYNTAX	Unsigned32
		MAX-ACCESS read-only
		STATUS current
		DESCRIPTION
			"Number of Rejects sent (trans perm to release)"
	::= { phlrInstanceEntry	91 }

smscPhlrTcapAbtReslimitSnt OBJECT-TYPE
		SYNTAX	Unsigned32
		MAX-ACCESS read-only
		STATUS current
		DESCRIPTION
			"Number of Rejects sent (trans res lim)"
	::= { phlrInstanceEntry	92 }

smscPhlrTcapRjctUctSnt OBJECT-TYPE
		SYNTAX	Unsigned32
		MAX-ACCESS read-only
		STATUS current
		DESCRIPTION
			"Number of Rejects sent (unrec comp type)"
	::= { phlrInstanceEntry	93 }

smscPhlrTcapRjctIcpSnt OBJECT-TYPE
		SYNTAX	Unsigned32
		MAX-ACCESS read-only
		STATUS current
		DESCRIPTION
			"Number of Rejects sent (inc comp portion)"
	::= { phlrInstanceEntry	94 }

smscPhlrTcapRjctBscpSnt OBJECT-TYPE
		SYNTAX	Unsigned32
		MAX-ACCESS read-only
		STATUS current
		DESCRIPTION
			"Number of Rejects sent (badly str comp)"
	::= { phlrInstanceEntry	95 }

smscPhlrTcapRjctIccSnt OBJECT-TYPE
		SYNTAX	Unsigned32
		MAX-ACCESS read-only
		STATUS current
		DESCRIPTION
			"Number of Rejects sent (inc comp codding)"
	::= { phlrInstanceEntry	96 }

smscPhlrTcapRjctIvdidSnt OBJECT-TYPE
		SYNTAX	Unsigned32
		MAX-ACCESS read-only
		STATUS current
		DESCRIPTION
			"Number of Rejects sent (inv dup invk ID)"
	::= { phlrInstanceEntry	97 }

smscPhlrTcapRjctIvuocSnt OBJECT-TYPE
		SYNTAX	Unsigned32
		MAX-ACCESS read-only
		STATUS current
		DESCRIPTION
			"Number of Rejects sent (inv unrec oper)"
	::= { phlrInstanceEntry	98 }

smscPhlrTcapRjctIviparSnt OBJECT-TYPE
		SYNTAX	Unsigned32
		MAX-ACCESS read-only
		STATUS current
		DESCRIPTION
			"Number of Rejects sent (inv inc param)"
	::= { phlrInstanceEntry	99 }

smscPhlrTcapRjctUcidSnt OBJECT-TYPE
		SYNTAX	Unsigned32
		MAX-ACCESS read-only
		STATUS current
		DESCRIPTION
			"Number of Rejects sent (inv unrec corr ID)"
	::= { phlrInstanceEntry	100 }

smscPhlrTcapRjctRruciSnt OBJECT-TYPE
		SYNTAX	Unsigned32
		MAX-ACCESS read-only
		STATUS current
		DESCRIPTION
			"Number of Rejects sent (result unass corr ID)"
	::= { phlrInstanceEntry	101 }

smscPhlrTcapRjctRrurrSnt OBJECT-TYPE
		SYNTAX	Unsigned32
		MAX-ACCESS read-only
		STATUS current
		DESCRIPTION
			"Number of Rejects sent (result unexp result)"
	::= { phlrInstanceEntry	102 }

smscPhlrTcapRjctRripSnt OBJECT-TYPE
		SYNTAX	Unsigned32
		MAX-ACCESS read-only
		STATUS current
		DESCRIPTION
			"Number of Rejects sent (result inc param)"
	::= { phlrInstanceEntry	103 }

smscPhlrTcapRjctEruciSnt OBJECT-TYPE
		SYNTAX	Unsigned32
		MAX-ACCESS read-only
		STATUS current
		DESCRIPTION
			"Number of Rejects sent (error unass corr ID)"
	::= { phlrInstanceEntry	104 }

smscPhlrTcapRjctErureSnt OBJECT-TYPE
		SYNTAX	Unsigned32
		MAX-ACCESS read-only
		STATUS current
		DESCRIPTION
			"Number of Rejects sent (error unexp ret error)"
	::= { phlrInstanceEntry	105 }

smscPhlrTcapRjctErueSnt OBJECT-TYPE
		SYNTAX	Unsigned32
		MAX-ACCESS read-only
		STATUS current
		DESCRIPTION
			"Number of Rejects sent (error unrec error)"
	::= { phlrInstanceEntry	106 }

smscPhlrTcapRjctErunxSnt OBJECT-TYPE
		SYNTAX	Unsigned32
		MAX-ACCESS read-only
		STATUS current
		DESCRIPTION
			"Number of Rejects sent (error unexp error)"
	::= { phlrInstanceEntry	107 }

smscPhlrTcapRjctEripSnt OBJECT-TYPE
		SYNTAX	Unsigned32
		MAX-ACCESS read-only
		STATUS current
		DESCRIPTION
			"Number of Rejects sent (error inc param)"
	::= { phlrInstanceEntry	108 }

smscPhlrTcapActiveDialog OBJECT-TYPE
		SYNTAX	Unsigned32
		MAX-ACCESS read-only
		STATUS current
		DESCRIPTION
			"Number of simultaneous active TCAP dialogues"
	::= { phlrInstanceEntry	109 }

smscPhlrTcapInitiatedDialog OBJECT-TYPE
		SYNTAX	Unsigned32
		MAX-ACCESS read-only
		STATUS current
		DESCRIPTION
			"Number of simultaneous initiated TCAP dialogues"
	::= { phlrInstanceEntry	110 }

smscPhlrTcapUnknMsgRcvd OBJECT-TYPE
		SYNTAX	Unsigned32
		MAX-ACCESS read-only
		STATUS current
		DESCRIPTION
			"Number of incorrect or unknown TCAP msgs received"
	::= { phlrInstanceEntry	111 }

smscPhlrTcapNoticeRcvd OBJECT-TYPE
		SYNTAX	Unsigned32
		MAX-ACCESS read-only
		STATUS current
		DESCRIPTION
			"Number of Notice rcvd"
	::= { phlrInstanceEntry	112 }



-- end of PHLR description.
-- --------------------------------------


-- --------------------------------------
-- Class EIR
-- 
smscEir OBJECT-TYPE
	SYNTAX  SEQUENCE OF EirInstanceEntry
	MAX-ACCESS  not-accessible
	STATUS  current
	DESCRIPTION
		"Mapping table for SMSC EIR entities."
   ::= { smscClassOther   1  }

eirInstanceEntry  OBJECT-TYPE
	SYNTAX EirInstanceEntry
	MAX-ACCESS  not-accessible
	STATUS  current
	DESCRIPTION
		"An entry (row) in the entityInstanceTable."
	INDEX { IMPLIED smscEirName }
   ::= { smscEir 1 }

EirInstanceEntry ::= SEQUENCE {
		smscEirName     DisplayString,
		smscEirState   INTEGER,
		smscEirLastupdate   TimeTicks,
		smscEirNode	   DisplayString, 
		smscEirMsgReceived	 Unsigned32, 
		smscEirMsgRejected	 Unsigned32, 
		smscEirMsgTransmitted	 Unsigned32, 
		smscEirMsgFailed	 Unsigned32, 
		smscEirDialogues	 Unsigned32, 
		smscEirSessionsPending	 Unsigned32, 
		smscEirDialoguesPending	 Unsigned32, 
		smscEirSystemFailure	 Unsigned32, 
		smscEirUnexpectedDataValue	 Unsigned32, 
		smscEirQelemUsed	 Unsigned32, 
		smscEirQelemInProcqueue	 Unsigned32, 
		smscEirQelemInExpqueue	 Unsigned32, 
		smscEirNrTimersRunning	 Unsigned32, 
		smscEirNrSystemTimers	 Unsigned32, 
		smscEirImiRecallQelem	 Unsigned32, 
		smscEirImiRecallQueues	 Unsigned32, 
		smscEirIdiRecallQelem	 Unsigned32, 
		smscEirIdiRecallQueues	 Unsigned32, 
		smscEirIosRecallQelem	 Unsigned32, 
		smscEirIosRecallQueues	 Unsigned32, 
		smscEirLogRecallQelem	 Unsigned32, 
		smscEirLogRecallQueues	 Unsigned32, 
		smscEirTrcreqDiscarded	 Unsigned32, 
		smscEirUnknownTotal	 Unsigned32, 
		smscEirWhiteTotal	 Unsigned32, 
		smscEirGreyTotal	 Unsigned32, 
		smscEirBlackTotal	 Unsigned32, 
		smscEirUnknownRequested	 Unsigned32, 
		smscEirWhiteRequested	 Unsigned32, 
		smscEirGreyRequested	 Unsigned32, 
		smscEirBlackRequested	 Unsigned32, 
		smscEirLicenseLimitReached	 Unsigned32, 
		smscEirMapDiaQueueFailed	 Unsigned32, 
		smscEirMapDiaFree	 Unsigned32, 
		smscEirMapDiaInUse	 Unsigned32, 
		smscEirMapDiaMaxUsed	 Unsigned32, 
		smscEirMapDiaAllocFailed	 Unsigned32, 
		smscEirMapOperFree	 Unsigned32, 
		smscEirMapOperInUse	 Unsigned32, 
		smscEirMapOperMaxUsed	 Unsigned32, 
		smscEirMapOperAllocFailed	 Unsigned32, 
		smscEirMapBufFree	 Unsigned32, 
		smscEirMapBufInUse	 Unsigned32, 
		smscEirMapBufMaxUsed	 Unsigned32, 
		smscEirMapBufAllocFailed	 Unsigned32, 
		smscEirMapProtoErr	 Unsigned32, 
		smscEirMapPrvDecErr	 Unsigned32, 
		smscEirMapPduDecErr	 Unsigned32, 
		smscEirMapOpcodeErr	 Unsigned32, 
		smscEirMapInvokeErr	 Unsigned32, 
		smscEirMapInvAppCtxt	 Unsigned32, 
		smscEirMapAppCtxtMism	 Unsigned32, 
		smscEirTcapBeginRcvd	 Unsigned32, 
		smscEirTcapContRcvd	 Unsigned32, 
		smscEirTcapEndRcvd	 Unsigned32, 
		smscEirTcapBeginSnt	 Unsigned32, 
		smscEirTcapContSnt	 Unsigned32, 
		smscEirTcapEndSnt	 Unsigned32, 
		smscEirTcapFailedSent	 Unsigned32, 
		smscEirTcapTransDisc	 Unsigned32, 
		smscEirTcapMsgDisc	 Unsigned32, 
		smscEirTcapUnknMsgRcvd	 Unsigned32, 
		smscEirTcapNoticeRcvd	 Unsigned32, 
		smscEirTcapAbtRcvd	 Unsigned32, 
		smscEirTcapAbtUnrecmtRcvd	 Unsigned32, 
		smscEirTcapAbtTranpRcvd	 Unsigned32, 
		smscEirTcapAbtBftpRcvd	 Unsigned32, 
		smscEirTcapAbtUnrecidRcvd	 Unsigned32, 
		smscEirTcapAbtReslimitRcvd	 Unsigned32, 
		smscEirTcapAbtAbnormRcvd	 Unsigned32, 
		smscEirTcapAbtSnt	 Unsigned32, 
		smscEirTcapAbtUnrecmtSnt	 Unsigned32, 
		smscEirTcapAbtTranpSnt	 Unsigned32, 
		smscEirTcapAbtBftpSnt	 Unsigned32, 
		smscEirTcapAbtUnrecidSnt	 Unsigned32, 
		smscEirTcapAbtReslimitSnt	 Unsigned32, 
		smscEirTcapAbtAbnormSnt	 Unsigned32, 
		smscEirTcapUabtRcvd	 Unsigned32, 
		smscEirTcapUabtSnt	 Unsigned32, 
		smscEirTcapInvkRcvd	 Unsigned32, 
		smscEirTcapInvkSnt	 Unsigned32, 
		smscEirTcapResLastRcvd	 Unsigned32, 
		smscEirTcapResNolastRcvd	 Unsigned32, 
		smscEirTcapResLastSnt	 Unsigned32, 
		smscEirTcapResNolastSnt	 Unsigned32, 
		smscEirTcapErrorRcvd	 Unsigned32, 
		smscEirTcapErrorSnt	 Unsigned32, 
		smscEirTcapRjctSnt	 Unsigned32, 
		smscEirTcapRjctRcvd	 Unsigned32, 
		smscEirTcapRjctUnrecRcvd	 Unsigned32, 
		smscEirTcapRjctMistypeRcvd	 Unsigned32, 
		smscEirTcapRjctBadsRcvd	 Unsigned32, 
		smscEirTcapRjctUnrLidRcvd	 Unsigned32, 
		smscEirTcapRjctUiRrRcvd	 Unsigned32, 
		smscEirTcapRjctUiReRcvd	 Unsigned32, 
		smscEirTcapRjctUnxpRrRcvd	 Unsigned32, 
		smscEirTcapRjctUnxpReRcvd	 Unsigned32, 
		smscEirTcapRjctDupIidRcvd	 Unsigned32, 
		smscEirTcapPrbUnrecOpRcvd	 Unsigned32, 
		smscEirTcapPrbMistypeRcvd	 Unsigned32, 
		smscEirTcapPrbReslimitRcvd	 Unsigned32, 
		smscEirTcapPrbInitrelRcvd	 Unsigned32, 
		smscEirTcapPrbUnlRespRcvd	 Unsigned32, 
		smscEirTcapPrbUnlOpRcvd	 Unsigned32, 
		smscEirTcapPrbMtRrRcvd	 Unsigned32, 
		smscEirTcapPrbMtReRcvd	 Unsigned32, 
		smscEirTcapUserUnrecRcvd	 Unsigned32, 
		smscEirTcapUserUnxpRcvd	 Unsigned32, 
		smscEirTcapActiveDialog	 Unsigned32, 
		smscEirTcapInitiatedDialog	 Unsigned32, 
		smscEirTcapActiveDlgs	 Unsigned32, 
		smscEirTcapInitiatedDlgs	 Unsigned32
	}

smscEirName  OBJECT-TYPE
	SYNTAX  DisplayString
	MAX-ACCESS  read-only
	STATUS   current
	DESCRIPTION
		"Identifies the name of the entity."
   ::= {eirInstanceEntry 1 }

smscEirState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { eirInstanceEntry 2 }


smscEirLastupdate OBJECT-TYPE
		SYNTAX	TimeTicks
		MAX-ACCESS read-only
		STATUS current
		DESCRIPTION
			"Value which reflects the last time the entities fields have been updated"
	::= { eirInstanceEntry	3 }

smscEirNode  OBJECT-TYPE
	SYNTAX  DisplayString
	MAX-ACCESS  read-only
	STATUS   current
	DESCRIPTION
		"Identifies the node the entity is running on."
   ::= {eirInstanceEntry 4 }

smscEirMsgReceived OBJECT-TYPE
		SYNTAX	Unsigned32
		MAX-ACCESS read-only
		STATUS current
		DESCRIPTION
			"Received messages"
	::= { eirInstanceEntry	5 }

smscEirMsgRejected OBJECT-TYPE
		SYNTAX	Unsigned32
		MAX-ACCESS read-only
		STATUS current
		DESCRIPTION
			"Received messages and rejected"
	::= { eirInstanceEntry	6 }

smscEirMsgTransmitted OBJECT-TYPE
		SYNTAX	Unsigned32
		MAX-ACCESS read-only
		STATUS current
		DESCRIPTION
			"Transmitted messages"
	::= { eirInstanceEntry	7 }

smscEirMsgFailed OBJECT-TYPE
		SYNTAX	Unsigned32
		MAX-ACCESS read-only
		STATUS current
		DESCRIPTION
			"Messages that failed on sending"
	::= { eirInstanceEntry	8 }

smscEirDialogues OBJECT-TYPE
		SYNTAX	Unsigned32
		MAX-ACCESS read-only
		STATUS current
		DESCRIPTION
			"Number of dialogues"
	::= { eirInstanceEntry	9 }

smscEirSessionsPending OBJECT-TYPE
		SYNTAX	Unsigned32
		MAX-ACCESS read-only
		STATUS current
		DESCRIPTION
			"Number of sessions (currently) pending"
	::= { eirInstanceEntry	10 }

smscEirDialoguesPending OBJECT-TYPE
		SYNTAX	Unsigned32
		MAX-ACCESS read-only
		STATUS current
		DESCRIPTION
			"Number of dialogues (currently) pending"
	::= { eirInstanceEntry	11 }

smscEirSystemFailure OBJECT-TYPE
		SYNTAX	Unsigned32
		MAX-ACCESS read-only
		STATUS current
		DESCRIPTION
			"Number of System Failure errors"
	::= { eirInstanceEntry	12 }

smscEirUnexpectedDataValue OBJECT-TYPE
		SYNTAX	Unsigned32
		MAX-ACCESS read-only
		STATUS current
		DESCRIPTION
			"Number of Unexpected Data Value errors"
	::= { eirInstanceEntry	13 }

smscEirQelemUsed OBJECT-TYPE
		SYNTAX	Unsigned32
		MAX-ACCESS read-only
		STATUS current
		DESCRIPTION
			"Number of elements in internal queues"
	::= { eirInstanceEntry	14 }

smscEirQelemInProcqueue OBJECT-TYPE
		SYNTAX	Unsigned32
		MAX-ACCESS read-only
		STATUS current
		DESCRIPTION
			"Number of elements used in process queue"
	::= { eirInstanceEntry	15 }

smscEirQelemInExpqueue OBJECT-TYPE
		SYNTAX	Unsigned32
		MAX-ACCESS read-only
		STATUS current
		DESCRIPTION
			"Number of elements used in expedited queue"
	::= { eirInstanceEntry	16 }

smscEirNrTimersRunning OBJECT-TYPE
		SYNTAX	Unsigned32
		MAX-ACCESS read-only
		STATUS current
		DESCRIPTION
			"Total number of timers running"
	::= { eirInstanceEntry	17 }

smscEirNrSystemTimers OBJECT-TYPE
		SYNTAX	Unsigned32
		MAX-ACCESS read-only
		STATUS current
		DESCRIPTION
			"Number of system timers running"
	::= { eirInstanceEntry	18 }

smscEirImiRecallQelem OBJECT-TYPE
		SYNTAX	Unsigned32
		MAX-ACCESS read-only
		STATUS current
		DESCRIPTION
			"Number of IMI recall-queue elements used"
	::= { eirInstanceEntry	19 }

smscEirImiRecallQueues OBJECT-TYPE
		SYNTAX	Unsigned32
		MAX-ACCESS read-only
		STATUS current
		DESCRIPTION
			"Number of IMI-recall-queues used"
	::= { eirInstanceEntry	20 }

smscEirIdiRecallQelem OBJECT-TYPE
		SYNTAX	Unsigned32
		MAX-ACCESS read-only
		STATUS current
		DESCRIPTION
			"Number of IDI recall-queue elements used"
	::= { eirInstanceEntry	21 }

smscEirIdiRecallQueues OBJECT-TYPE
		SYNTAX	Unsigned32
		MAX-ACCESS read-only
		STATUS current
		DESCRIPTION
			"Number of IDI recall-queues used"
	::= { eirInstanceEntry	22 }

smscEirIosRecallQelem OBJECT-TYPE
		SYNTAX	Unsigned32
		MAX-ACCESS read-only
		STATUS current
		DESCRIPTION
			"Number of IOS recall-queue elements used"
	::= { eirInstanceEntry	23 }

smscEirIosRecallQueues OBJECT-TYPE
		SYNTAX	Unsigned32
		MAX-ACCESS read-only
		STATUS current
		DESCRIPTION
			"Number of IOS recall-queues used"
	::= { eirInstanceEntry	24 }

smscEirLogRecallQelem OBJECT-TYPE
		SYNTAX	Unsigned32
		MAX-ACCESS read-only
		STATUS current
		DESCRIPTION
			"Number of LOG recall-queue elements used"
	::= { eirInstanceEntry	25 }

smscEirLogRecallQueues OBJECT-TYPE
		SYNTAX	Unsigned32
		MAX-ACCESS read-only
		STATUS current
		DESCRIPTION
			"Number of LOG recall-queues used"
	::= { eirInstanceEntry	26 }

smscEirTrcreqDiscarded OBJECT-TYPE
		SYNTAX	Unsigned32
		MAX-ACCESS read-only
		STATUS current
		DESCRIPTION
			"Number of trace requests discarded"
	::= { eirInstanceEntry	27 }

smscEirUnknownTotal OBJECT-TYPE
		SYNTAX	Unsigned32
		MAX-ACCESS read-only
		STATUS current
		DESCRIPTION
			"Numberof CheckIMEI resulting in UnknownEquipment"
	::= { eirInstanceEntry	28 }

smscEirWhiteTotal OBJECT-TYPE
		SYNTAX	Unsigned32
		MAX-ACCESS read-only
		STATUS current
		DESCRIPTION
			"Number of CheckIMEI resulting in White listed"
	::= { eirInstanceEntry	29 }

smscEirGreyTotal OBJECT-TYPE
		SYNTAX	Unsigned32
		MAX-ACCESS read-only
		STATUS current
		DESCRIPTION
			"Number of CheckIMEI resulting in Grey listed"
	::= { eirInstanceEntry	30 }

smscEirBlackTotal OBJECT-TYPE
		SYNTAX	Unsigned32
		MAX-ACCESS read-only
		STATUS current
		DESCRIPTION
			"Number of CheckIMEI resulting in Black listed"
	::= { eirInstanceEntry	31 }

smscEirUnknownRequested OBJECT-TYPE
		SYNTAX	Unsigned32
		MAX-ACCESS read-only
		STATUS current
		DESCRIPTION
			"Number of check IMEI resulting in Unknown Equipment"
	::= { eirInstanceEntry	32 }

smscEirWhiteRequested OBJECT-TYPE
		SYNTAX	Unsigned32
		MAX-ACCESS read-only
		STATUS current
		DESCRIPTION
			"Number of check IMEI resulting in White listed"
	::= { eirInstanceEntry	33 }

smscEirGreyRequested OBJECT-TYPE
		SYNTAX	Unsigned32
		MAX-ACCESS read-only
		STATUS current
		DESCRIPTION
			"Number of check IMEI resulting in Grey listed"
	::= { eirInstanceEntry	34 }

smscEirBlackRequested OBJECT-TYPE
		SYNTAX	Unsigned32
		MAX-ACCESS read-only
		STATUS current
		DESCRIPTION
			"Number of check IMEI resulting in Black listed"
	::= { eirInstanceEntry	35 }

smscEirLicenseLimitReached OBJECT-TYPE
		SYNTAX	Unsigned32
		MAX-ACCESS read-only
		STATUS current
		DESCRIPTION
			"Number of times the license-limit was reached"
	::= { eirInstanceEntry	36 }

smscEirMapDiaQueueFailed OBJECT-TYPE
		SYNTAX	Unsigned32
		MAX-ACCESS read-only
		STATUS current
		DESCRIPTION
			"Number of MAP dialog queue failures"
	::= { eirInstanceEntry	37 }

smscEirMapDiaFree OBJECT-TYPE
		SYNTAX	Unsigned32
		MAX-ACCESS read-only
		STATUS current
		DESCRIPTION
			"Number of MAP dialogs free"
	::= { eirInstanceEntry	38 }

smscEirMapDiaInUse OBJECT-TYPE
		SYNTAX	Unsigned32
		MAX-ACCESS read-only
		STATUS current
		DESCRIPTION
			"Number of MAP dialogs in use"
	::= { eirInstanceEntry	39 }

smscEirMapDiaMaxUsed OBJECT-TYPE
		SYNTAX	Unsigned32
		MAX-ACCESS read-only
		STATUS current
		DESCRIPTION
			"Maximum number of MAP dialogs used"
	::= { eirInstanceEntry	40 }

smscEirMapDiaAllocFailed OBJECT-TYPE
		SYNTAX	Unsigned32
		MAX-ACCESS read-only
		STATUS current
		DESCRIPTION
			"Number of MAP dialog allocation failures"
	::= { eirInstanceEntry	41 }

smscEirMapOperFree OBJECT-TYPE
		SYNTAX	Unsigned32
		MAX-ACCESS read-only
		STATUS current
		DESCRIPTION
			"Number of MAP operations free"
	::= { eirInstanceEntry	42 }

smscEirMapOperInUse OBJECT-TYPE
		SYNTAX	Unsigned32
		MAX-ACCESS read-only
		STATUS current
		DESCRIPTION
			"Number of MAP operations in use"
	::= { eirInstanceEntry	43 }

smscEirMapOperMaxUsed OBJECT-TYPE
		SYNTAX	Unsigned32
		MAX-ACCESS read-only
		STATUS current
		DESCRIPTION
			"Maximum number of MAP operations used"
	::= { eirInstanceEntry	44 }

smscEirMapOperAllocFailed OBJECT-TYPE
		SYNTAX	Unsigned32
		MAX-ACCESS read-only
		STATUS current
		DESCRIPTION
			"Number of MAP operation allocation failures"
	::= { eirInstanceEntry	45 }

smscEirMapBufFree OBJECT-TYPE
		SYNTAX	Unsigned32
		MAX-ACCESS read-only
		STATUS current
		DESCRIPTION
			"Number of MAP buffers free"
	::= { eirInstanceEntry	46 }

smscEirMapBufInUse OBJECT-TYPE
		SYNTAX	Unsigned32
		MAX-ACCESS read-only
		STATUS current
		DESCRIPTION
			"Number of MAP buffers in use"
	::= { eirInstanceEntry	47 }

smscEirMapBufMaxUsed OBJECT-TYPE
		SYNTAX	Unsigned32
		MAX-ACCESS read-only
		STATUS current
		DESCRIPTION
			"Maximum number of MAP buffers used"
	::= { eirInstanceEntry	48 }

smscEirMapBufAllocFailed OBJECT-TYPE
		SYNTAX	Unsigned32
		MAX-ACCESS read-only
		STATUS current
		DESCRIPTION
			"Number of MAP buffer allocation failures"
	::= { eirInstanceEntry	49 }

smscEirMapProtoErr OBJECT-TYPE
		SYNTAX	Unsigned32
		MAX-ACCESS read-only
		STATUS current
		DESCRIPTION
			"Number of MAP protocol errors"
	::= { eirInstanceEntry	50 }

smscEirMapPrvDecErr OBJECT-TYPE
		SYNTAX	Unsigned32
		MAX-ACCESS read-only
		STATUS current
		DESCRIPTION
			"Number of MAP provider decode errors"
	::= { eirInstanceEntry	51 }

smscEirMapPduDecErr OBJECT-TYPE
		SYNTAX	Unsigned32
		MAX-ACCESS read-only
		STATUS current
		DESCRIPTION
			"Number of MAP PDU decode errors"
	::= { eirInstanceEntry	52 }

smscEirMapOpcodeErr OBJECT-TYPE
		SYNTAX	Unsigned32
		MAX-ACCESS read-only
		STATUS current
		DESCRIPTION
			"Number of invalid MAP opcodes received"
	::= { eirInstanceEntry	53 }

smscEirMapInvokeErr OBJECT-TYPE
		SYNTAX	Unsigned32
		MAX-ACCESS read-only
		STATUS current
		DESCRIPTION
			"Number of invalid MAP invoke IDs received"
	::= { eirInstanceEntry	54 }

smscEirMapInvAppCtxt OBJECT-TYPE
		SYNTAX	Unsigned32
		MAX-ACCESS read-only
		STATUS current
		DESCRIPTION
			"Invalid MAP application contexts received"
	::= { eirInstanceEntry	55 }

smscEirMapAppCtxtMism OBJECT-TYPE
		SYNTAX	Unsigned32
		MAX-ACCESS read-only
		STATUS current
		DESCRIPTION
			"Not matching MAP application contexts received"
	::= { eirInstanceEntry	56 }

smscEirTcapBeginRcvd OBJECT-TYPE
		SYNTAX	Unsigned32
		MAX-ACCESS read-only
		STATUS current
		DESCRIPTION
			"Number of Begin Dialogue transactions received"
	::= { eirInstanceEntry	57 }

smscEirTcapContRcvd OBJECT-TYPE
		SYNTAX	Unsigned32
		MAX-ACCESS read-only
		STATUS current
		DESCRIPTION
			"Number of Continue transactions received"
	::= { eirInstanceEntry	58 }

smscEirTcapEndRcvd OBJECT-TYPE
		SYNTAX	Unsigned32
		MAX-ACCESS read-only
		STATUS current
		DESCRIPTION
			"Number of End transactions received"
	::= { eirInstanceEntry	59 }

smscEirTcapBeginSnt OBJECT-TYPE
		SYNTAX	Unsigned32
		MAX-ACCESS read-only
		STATUS current
		DESCRIPTION
			"Number of Begin Dialogue transactions sent"
	::= { eirInstanceEntry	60 }

smscEirTcapContSnt OBJECT-TYPE
		SYNTAX	Unsigned32
		MAX-ACCESS read-only
		STATUS current
		DESCRIPTION
			"Number of Continue transactions sent"
	::= { eirInstanceEntry	61 }

smscEirTcapEndSnt OBJECT-TYPE
		SYNTAX	Unsigned32
		MAX-ACCESS read-only
		STATUS current
		DESCRIPTION
			"Number of End transactions sent"
	::= { eirInstanceEntry	62 }

smscEirTcapFailedSent OBJECT-TYPE
		SYNTAX	Unsigned32
		MAX-ACCESS read-only
		STATUS current
		DESCRIPTION
			"Number of Message failed to be sent"
	::= { eirInstanceEntry	63 }

smscEirTcapTransDisc OBJECT-TYPE
		SYNTAX	Unsigned32
		MAX-ACCESS read-only
		STATUS current
		DESCRIPTION
			"Number of discarded msgs due to transport problem"
	::= { eirInstanceEntry	64 }

smscEirTcapMsgDisc OBJECT-TYPE
		SYNTAX	Unsigned32
		MAX-ACCESS read-only
		STATUS current
		DESCRIPTION
			"Number of discarded TCAP messages"
	::= { eirInstanceEntry	65 }

smscEirTcapUnknMsgRcvd OBJECT-TYPE
		SYNTAX	Unsigned32
		MAX-ACCESS read-only
		STATUS current
		DESCRIPTION
			"Number of incorrect or unknown TCAP msgs received"
	::= { eirInstanceEntry	66 }

smscEirTcapNoticeRcvd OBJECT-TYPE
		SYNTAX	Unsigned32
		MAX-ACCESS read-only
		STATUS current
		DESCRIPTION
			"Number of Notice rcvd"
	::= { eirInstanceEntry	67 }

smscEirTcapAbtRcvd OBJECT-TYPE
		SYNTAX	Unsigned32
		MAX-ACCESS read-only
		STATUS current
		DESCRIPTION
			"Number of P_ABORT transacs rcvd"
	::= { eirInstanceEntry	68 }

smscEirTcapAbtUnrecmtRcvd OBJECT-TYPE
		SYNTAX	Unsigned32
		MAX-ACCESS read-only
		STATUS current
		DESCRIPTION
			"Number of P_ABORT transacs rcvd (unrec msg type)"
	::= { eirInstanceEntry	69 }

smscEirTcapAbtTranpRcvd OBJECT-TYPE
		SYNTAX	Unsigned32
		MAX-ACCESS read-only
		STATUS current
		DESCRIPTION
			"Number of P_ABORT msgs rcvd (inc trans portion)"
	::= { eirInstanceEntry	70 }

smscEirTcapAbtBftpRcvd OBJECT-TYPE
		SYNTAX	Unsigned32
		MAX-ACCESS read-only
		STATUS current
		DESCRIPTION
			"Number of P_ABORT msgs rcvd (badly formed tp)"
	::= { eirInstanceEntry	71 }

smscEirTcapAbtUnrecidRcvd OBJECT-TYPE
		SYNTAX	Unsigned32
		MAX-ACCESS read-only
		STATUS current
		DESCRIPTION
			"Number of P_ABORT msgs rcvd (unrec trans id)"
	::= { eirInstanceEntry	72 }

smscEirTcapAbtReslimitRcvd OBJECT-TYPE
		SYNTAX	Unsigned32
		MAX-ACCESS read-only
		STATUS current
		DESCRIPTION
			"Number of P_ABORT msgs rcvd (resouce limitation)"
	::= { eirInstanceEntry	73 }

smscEirTcapAbtAbnormRcvd OBJECT-TYPE
		SYNTAX	Unsigned32
		MAX-ACCESS read-only
		STATUS current
		DESCRIPTION
			"Number of P_ABORT msgs rcvd (abnormal dialog)"
	::= { eirInstanceEntry	74 }

smscEirTcapAbtSnt OBJECT-TYPE
		SYNTAX	Unsigned32
		MAX-ACCESS read-only
		STATUS current
		DESCRIPTION
			"Number of P_ABORT transacs sent"
	::= { eirInstanceEntry	75 }

smscEirTcapAbtUnrecmtSnt OBJECT-TYPE
		SYNTAX	Unsigned32
		MAX-ACCESS read-only
		STATUS current
		DESCRIPTION
			"Number of P_ABORT transacs sent (unrec msg type)"
	::= { eirInstanceEntry	76 }

smscEirTcapAbtTranpSnt OBJECT-TYPE
		SYNTAX	Unsigned32
		MAX-ACCESS read-only
		STATUS current
		DESCRIPTION
			"Number of P_ABORT transacs sent (inc trns portion)"
	::= { eirInstanceEntry	77 }

smscEirTcapAbtBftpSnt OBJECT-TYPE
		SYNTAX	Unsigned32
		MAX-ACCESS read-only
		STATUS current
		DESCRIPTION
			"Number of P_ABORT transacs sent (badly formed tp)"
	::= { eirInstanceEntry	78 }

smscEirTcapAbtUnrecidSnt OBJECT-TYPE
		SYNTAX	Unsigned32
		MAX-ACCESS read-only
		STATUS current
		DESCRIPTION
			"Number of P_ABORT transacs sent (unrec trns id)"
	::= { eirInstanceEntry	79 }

smscEirTcapAbtReslimitSnt OBJECT-TYPE
		SYNTAX	Unsigned32
		MAX-ACCESS read-only
		STATUS current
		DESCRIPTION
			"Number of P_ABORT transacs sent (res limitation)"
	::= { eirInstanceEntry	80 }

smscEirTcapAbtAbnormSnt OBJECT-TYPE
		SYNTAX	Unsigned32
		MAX-ACCESS read-only
		STATUS current
		DESCRIPTION
			"Number of P_ABORT transacs sent (abnormal dialog)"
	::= { eirInstanceEntry	81 }

smscEirTcapUabtRcvd OBJECT-TYPE
		SYNTAX	Unsigned32
		MAX-ACCESS read-only
		STATUS current
		DESCRIPTION
			"Number of U_ABORT transactions received"
	::= { eirInstanceEntry	82 }

smscEirTcapUabtSnt OBJECT-TYPE
		SYNTAX	Unsigned32
		MAX-ACCESS read-only
		STATUS current
		DESCRIPTION
			"Number of U_ABORT transactions sent"
	::= { eirInstanceEntry	83 }

smscEirTcapInvkRcvd OBJECT-TYPE
		SYNTAX	Unsigned32
		MAX-ACCESS read-only
		STATUS current
		DESCRIPTION
			"Number of Invoke components received"
	::= { eirInstanceEntry	84 }

smscEirTcapInvkSnt OBJECT-TYPE
		SYNTAX	Unsigned32
		MAX-ACCESS read-only
		STATUS current
		DESCRIPTION
			"Number of Invoke components sent"
	::= { eirInstanceEntry	85 }

smscEirTcapResLastRcvd OBJECT-TYPE
		SYNTAX	Unsigned32
		MAX-ACCESS read-only
		STATUS current
		DESCRIPTION
			"Number of Result Last components received"
	::= { eirInstanceEntry	86 }

smscEirTcapResNolastRcvd OBJECT-TYPE
		SYNTAX	Unsigned32
		MAX-ACCESS read-only
		STATUS current
		DESCRIPTION
			"Number of Result No Last components received"
	::= { eirInstanceEntry	87 }

smscEirTcapResLastSnt OBJECT-TYPE
		SYNTAX	Unsigned32
		MAX-ACCESS read-only
		STATUS current
		DESCRIPTION
			"Number of Result Last components sent"
	::= { eirInstanceEntry	88 }

smscEirTcapResNolastSnt OBJECT-TYPE
		SYNTAX	Unsigned32
		MAX-ACCESS read-only
		STATUS current
		DESCRIPTION
			"Number of Result No Last components sent"
	::= { eirInstanceEntry	89 }

smscEirTcapErrorRcvd OBJECT-TYPE
		SYNTAX	Unsigned32
		MAX-ACCESS read-only
		STATUS current
		DESCRIPTION
			"Number of Error components received"
	::= { eirInstanceEntry	90 }

smscEirTcapErrorSnt OBJECT-TYPE
		SYNTAX	Unsigned32
		MAX-ACCESS read-only
		STATUS current
		DESCRIPTION
			"Number of Error components sent"
	::= { eirInstanceEntry	91 }

smscEirTcapRjctSnt OBJECT-TYPE
		SYNTAX	Unsigned32
		MAX-ACCESS read-only
		STATUS current
		DESCRIPTION
			"Number of Reject components sent"
	::= { eirInstanceEntry	92 }

smscEirTcapRjctRcvd OBJECT-TYPE
		SYNTAX	Unsigned32
		MAX-ACCESS read-only
		STATUS current
		DESCRIPTION
			"Number of Reject components rcvd"
	::= { eirInstanceEntry	93 }

smscEirTcapRjctUnrecRcvd OBJECT-TYPE
		SYNTAX	Unsigned32
		MAX-ACCESS read-only
		STATUS current
		DESCRIPTION
			"Number of Reject components rcvd (unrecognized)"
	::= { eirInstanceEntry	94 }

smscEirTcapRjctMistypeRcvd OBJECT-TYPE
		SYNTAX	Unsigned32
		MAX-ACCESS read-only
		STATUS current
		DESCRIPTION
			"Number of Reject components rcvd (mistyped)"
	::= { eirInstanceEntry	95 }

smscEirTcapRjctBadsRcvd OBJECT-TYPE
		SYNTAX	Unsigned32
		MAX-ACCESS read-only
		STATUS current
		DESCRIPTION
			"Number of Reject components rcvd (badly struct)"
	::= { eirInstanceEntry	96 }

smscEirTcapRjctUnrLidRcvd OBJECT-TYPE
		SYNTAX	Unsigned32
		MAX-ACCESS read-only
		STATUS current
		DESCRIPTION
			"Number of Reject components rcvd (unrec link_id)"
	::= { eirInstanceEntry	97 }

smscEirTcapRjctUiRrRcvd OBJECT-TYPE
		SYNTAX	Unsigned32
		MAX-ACCESS read-only
		STATUS current
		DESCRIPTION
			"Number of Reject components rcvd (unr ivk ret res)"
	::= { eirInstanceEntry	98 }

smscEirTcapRjctUiReRcvd OBJECT-TYPE
		SYNTAX	Unsigned32
		MAX-ACCESS read-only
		STATUS current
		DESCRIPTION
			"Number of Reject components rcvd (unr ivk ret err)"
	::= { eirInstanceEntry	99 }

smscEirTcapRjctUnxpRrRcvd OBJECT-TYPE
		SYNTAX	Unsigned32
		MAX-ACCESS read-only
		STATUS current
		DESCRIPTION
			"Number of Reject components rcvd (unexp ret res)"
	::= { eirInstanceEntry	100 }

smscEirTcapRjctUnxpReRcvd OBJECT-TYPE
		SYNTAX	Unsigned32
		MAX-ACCESS read-only
		STATUS current
		DESCRIPTION
			"Number of Reject components rcvd (unexp ret err)"
	::= { eirInstanceEntry	101 }

smscEirTcapRjctDupIidRcvd OBJECT-TYPE
		SYNTAX	Unsigned32
		MAX-ACCESS read-only
		STATUS current
		DESCRIPTION
			"Number of Reject components rcvd (dupl ivk_id)"
	::= { eirInstanceEntry	102 }

smscEirTcapPrbUnrecOpRcvd OBJECT-TYPE
		SYNTAX	Unsigned32
		MAX-ACCESS read-only
		STATUS current
		DESCRIPTION
			"Number of TC user problems rcvd (unrec operations)"
	::= { eirInstanceEntry	103 }

smscEirTcapPrbMistypeRcvd OBJECT-TYPE
		SYNTAX	Unsigned32
		MAX-ACCESS read-only
		STATUS current
		DESCRIPTION
			"Number of TC user problems rcvd (mistyped param)"
	::= { eirInstanceEntry	104 }

smscEirTcapPrbReslimitRcvd OBJECT-TYPE
		SYNTAX	Unsigned32
		MAX-ACCESS read-only
		STATUS current
		DESCRIPTION
			"Number of TC user problems rcvd (res limitation)"
	::= { eirInstanceEntry	105 }

smscEirTcapPrbInitrelRcvd OBJECT-TYPE
		SYNTAX	Unsigned32
		MAX-ACCESS read-only
		STATUS current
		DESCRIPTION
			"Number of TC user problems rcvd (init release)"
	::= { eirInstanceEntry	106 }

smscEirTcapPrbUnlRespRcvd OBJECT-TYPE
		SYNTAX	Unsigned32
		MAX-ACCESS read-only
		STATUS current
		DESCRIPTION
			"Number of TC user problems rcvd (unexp link resp)"
	::= { eirInstanceEntry	107 }

smscEirTcapPrbUnlOpRcvd OBJECT-TYPE
		SYNTAX	Unsigned32
		MAX-ACCESS read-only
		STATUS current
		DESCRIPTION
			"Number of TC user problems rcvd (unexp link oper)"
	::= { eirInstanceEntry	108 }

smscEirTcapPrbMtRrRcvd OBJECT-TYPE
		SYNTAX	Unsigned32
		MAX-ACCESS read-only
		STATUS current
		DESCRIPTION
			"Number of TC user problems rcvd (mistyped ret res)"
	::= { eirInstanceEntry	109 }

smscEirTcapPrbMtReRcvd OBJECT-TYPE
		SYNTAX	Unsigned32
		MAX-ACCESS read-only
		STATUS current
		DESCRIPTION
			"Number of TC user problems rcvd (mistyped ret err)"
	::= { eirInstanceEntry	110 }

smscEirTcapUserUnrecRcvd OBJECT-TYPE
		SYNTAX	Unsigned32
		MAX-ACCESS read-only
		STATUS current
		DESCRIPTION
			"Number of TC user unrecognized errors received"
	::= { eirInstanceEntry	111 }

smscEirTcapUserUnxpRcvd OBJECT-TYPE
		SYNTAX	Unsigned32
		MAX-ACCESS read-only
		STATUS current
		DESCRIPTION
			"Number of TC user unexpected errors received"
	::= { eirInstanceEntry	112 }

smscEirTcapActiveDialog OBJECT-TYPE
		SYNTAX	Unsigned32
		MAX-ACCESS read-only
		STATUS current
		DESCRIPTION
			"Number of simultaneous active TCAP dialogues"
	::= { eirInstanceEntry	113 }

smscEirTcapInitiatedDialog OBJECT-TYPE
		SYNTAX	Unsigned32
		MAX-ACCESS read-only
		STATUS current
		DESCRIPTION
			"Number of simultaneous initiated TCAP dialogues"
	::= { eirInstanceEntry	114 }

smscEirTcapActiveDlgs OBJECT-TYPE
		SYNTAX	Unsigned32
		MAX-ACCESS read-only
		STATUS current
		DESCRIPTION
			"Number of simultaneous active TCAP dialogues"
	::= { eirInstanceEntry	115 }

smscEirTcapInitiatedDlgs OBJECT-TYPE
		SYNTAX	Unsigned32
		MAX-ACCESS read-only
		STATUS current
		DESCRIPTION
			"Number of simultaneous initiated TCAP dialogues"
	::= { eirInstanceEntry	116 }



-- end of EIR description.
-- --------------------------------------


-- --------------------------------------
-- Class DLH
-- 
smscDlh OBJECT-TYPE
	SYNTAX  SEQUENCE OF DlhInstanceEntry
	MAX-ACCESS  not-accessible
	STATUS  current
	DESCRIPTION
		"Mapping table for SMSC DLH entities."
   ::= { smscClassOther   2  }

dlhInstanceEntry  OBJECT-TYPE
	SYNTAX DlhInstanceEntry
	MAX-ACCESS  not-accessible
	STATUS  current
	DESCRIPTION
		"An entry (row) in the entityInstanceTable."
	INDEX { IMPLIED smscDlhName }
   ::= { smscDlh 1 }

DlhInstanceEntry ::= SEQUENCE {
		smscDlhName     DisplayString,
		smscDlhState   INTEGER,
		smscDlhLastupdate   TimeTicks,
		smscDlhNode	   DisplayString, 
		smscDlhMsgReceived	 Unsigned32, 
		smscDlhMsgRejected	 Unsigned32, 
		smscDlhMsgTransmitted	 Unsigned32, 
		smscDlhMsgFailed	 Unsigned32, 
		smscDlhQelemUsed	 Unsigned32, 
		smscDlhQelemInProcqueue	 Unsigned32, 
		smscDlhQelemInExpqueue	 Unsigned32, 
		smscDlhNrTimersRunning	 Unsigned32, 
		smscDlhNrSystemTimers	 Unsigned32, 
		smscDlhImiRecallQelem	 Unsigned32, 
		smscDlhImiRecallQueues	 Unsigned32, 
		smscDlhIdiRecallQelem	 Unsigned32, 
		smscDlhIdiRecallQueues	 Unsigned32, 
		smscDlhIosRecallQelem	 Unsigned32, 
		smscDlhIosRecallQueues	 Unsigned32, 
		smscDlhLogRecallQelem	 Unsigned32, 
		smscDlhLogRecallQueues	 Unsigned32, 
		smscDlhTrcreqDiscarded	 Unsigned32, 
		smscDlhDummyStatistic	 Unsigned32
	}

smscDlhName  OBJECT-TYPE
	SYNTAX  DisplayString
	MAX-ACCESS  read-only
	STATUS   current
	DESCRIPTION
		"Identifies the name of the entity."
   ::= {dlhInstanceEntry 1 }

smscDlhState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { dlhInstanceEntry 2 }


smscDlhLastupdate OBJECT-TYPE
		SYNTAX	TimeTicks
		MAX-ACCESS read-only
		STATUS current
		DESCRIPTION
			"Value which reflects the last time the entities fields have been updated"
	::= { dlhInstanceEntry	3 }

smscDlhNode  OBJECT-TYPE
	SYNTAX  DisplayString
	MAX-ACCESS  read-only
	STATUS   current
	DESCRIPTION
		"Identifies the node the entity is running on."
   ::= {dlhInstanceEntry 4 }

smscDlhMsgReceived OBJECT-TYPE
		SYNTAX	Unsigned32
		MAX-ACCESS read-only
		STATUS current
		DESCRIPTION
			"Received messages"
	::= { dlhInstanceEntry	5 }

smscDlhMsgRejected OBJECT-TYPE
		SYNTAX	Unsigned32
		MAX-ACCESS read-only
		STATUS current
		DESCRIPTION
			"Received messages and rejected"
	::= { dlhInstanceEntry	6 }

smscDlhMsgTransmitted OBJECT-TYPE
		SYNTAX	Unsigned32
		MAX-ACCESS read-only
		STATUS current
		DESCRIPTION
			"Transmitted messages"
	::= { dlhInstanceEntry	7 }

smscDlhMsgFailed OBJECT-TYPE
		SYNTAX	Unsigned32
		MAX-ACCESS read-only
		STATUS current
		DESCRIPTION
			"Messages that failed on sending"
	::= { dlhInstanceEntry	8 }

smscDlhQelemUsed OBJECT-TYPE
		SYNTAX	Unsigned32
		MAX-ACCESS read-only
		STATUS current
		DESCRIPTION
			"Number of elements in internal queues"
	::= { dlhInstanceEntry	9 }

smscDlhQelemInProcqueue OBJECT-TYPE
		SYNTAX	Unsigned32
		MAX-ACCESS read-only
		STATUS current
		DESCRIPTION
			"Number of elements used in process queue"
	::= { dlhInstanceEntry	10 }

smscDlhQelemInExpqueue OBJECT-TYPE
		SYNTAX	Unsigned32
		MAX-ACCESS read-only
		STATUS current
		DESCRIPTION
			"Number of elements used in expedited queue"
	::= { dlhInstanceEntry	11 }

smscDlhNrTimersRunning OBJECT-TYPE
		SYNTAX	Unsigned32
		MAX-ACCESS read-only
		STATUS current
		DESCRIPTION
			"Total number of timers running"
	::= { dlhInstanceEntry	12 }

smscDlhNrSystemTimers OBJECT-TYPE
		SYNTAX	Unsigned32
		MAX-ACCESS read-only
		STATUS current
		DESCRIPTION
			"Number of system timers running"
	::= { dlhInstanceEntry	13 }

smscDlhImiRecallQelem OBJECT-TYPE
		SYNTAX	Unsigned32
		MAX-ACCESS read-only
		STATUS current
		DESCRIPTION
			"Number of IMI recall-queue elements used"
	::= { dlhInstanceEntry	14 }

smscDlhImiRecallQueues OBJECT-TYPE
		SYNTAX	Unsigned32
		MAX-ACCESS read-only
		STATUS current
		DESCRIPTION
			"Number of IMI-recall-queues used"
	::= { dlhInstanceEntry	15 }

smscDlhIdiRecallQelem OBJECT-TYPE
		SYNTAX	Unsigned32
		MAX-ACCESS read-only
		STATUS current
		DESCRIPTION
			"Number of IDI recall-queue elements used"
	::= { dlhInstanceEntry	16 }

smscDlhIdiRecallQueues OBJECT-TYPE
		SYNTAX	Unsigned32
		MAX-ACCESS read-only
		STATUS current
		DESCRIPTION
			"Number of IDI recall-queues used"
	::= { dlhInstanceEntry	17 }

smscDlhIosRecallQelem OBJECT-TYPE
		SYNTAX	Unsigned32
		MAX-ACCESS read-only
		STATUS current
		DESCRIPTION
			"Number of IOS recall-queue elements used"
	::= { dlhInstanceEntry	18 }

smscDlhIosRecallQueues OBJECT-TYPE
		SYNTAX	Unsigned32
		MAX-ACCESS read-only
		STATUS current
		DESCRIPTION
			"Number of IOS recall-queues used"
	::= { dlhInstanceEntry	19 }

smscDlhLogRecallQelem OBJECT-TYPE
		SYNTAX	Unsigned32
		MAX-ACCESS read-only
		STATUS current
		DESCRIPTION
			"Number of LOG recall-queue elements used"
	::= { dlhInstanceEntry	20 }

smscDlhLogRecallQueues OBJECT-TYPE
		SYNTAX	Unsigned32
		MAX-ACCESS read-only
		STATUS current
		DESCRIPTION
			"Number of LOG recall-queues used"
	::= { dlhInstanceEntry	21 }

smscDlhTrcreqDiscarded OBJECT-TYPE
		SYNTAX	Unsigned32
		MAX-ACCESS read-only
		STATUS current
		DESCRIPTION
			"Number of trace requests discarded"
	::= { dlhInstanceEntry	22 }

smscDlhDummyStatistic OBJECT-TYPE
		SYNTAX	Unsigned32
		MAX-ACCESS read-only
		STATUS current
		DESCRIPTION
			"No statistical counters"
	::= { dlhInstanceEntry	23 }



-- end of DLH description.
-- --------------------------------------


-- --------------------------------------
-- Class SSD
-- 
smscSsd OBJECT-TYPE
	SYNTAX  SEQUENCE OF SsdInstanceEntry
	MAX-ACCESS  not-accessible
	STATUS  current
	DESCRIPTION
		"Mapping table for SMSC SSD entities."
   ::= { smscClassOther   3  }

ssdInstanceEntry  OBJECT-TYPE
	SYNTAX SsdInstanceEntry
	MAX-ACCESS  not-accessible
	STATUS  current
	DESCRIPTION
		"An entry (row) in the entityInstanceTable."
	INDEX { IMPLIED smscSsdName }
   ::= { smscSsd 1 }

SsdInstanceEntry ::= SEQUENCE {
		smscSsdName     DisplayString,
		smscSsdState   INTEGER,
		smscSsdLastupdate   TimeTicks,
		smscSsdNode	   DisplayString, 
		smscSsdMsgReceived	 Unsigned32, 
		smscSsdMsgRejected	 Unsigned32, 
		smscSsdMsgTransmitted	 Unsigned32, 
		smscSsdMsgFailed	 Unsigned32, 
		smscSsdQelemUsed	 Unsigned32, 
		smscSsdQelemInProcqueue	 Unsigned32, 
		smscSsdQelemInExpqueue	 Unsigned32, 
		smscSsdNrTimersRunning	 Unsigned32, 
		smscSsdNrSystemTimers	 Unsigned32, 
		smscSsdImiRecallQelem	 Unsigned32, 
		smscSsdImiRecallQueues	 Unsigned32, 
		smscSsdIdiRecallQelem	 Unsigned32, 
		smscSsdIdiRecallQueues	 Unsigned32, 
		smscSsdIosRecallQelem	 Unsigned32, 
		smscSsdIosRecallQueues	 Unsigned32, 
		smscSsdLogRecallQelem	 Unsigned32, 
		smscSsdLogRecallQueues	 Unsigned32, 
		smscSsdTrcreqDiscarded	 Unsigned32, 
		smscSsdDummyStatistic	 Unsigned32
	}

smscSsdName  OBJECT-TYPE
	SYNTAX  DisplayString
	MAX-ACCESS  read-only
	STATUS   current
	DESCRIPTION
		"Identifies the name of the entity."
   ::= {ssdInstanceEntry 1 }

smscSsdState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { ssdInstanceEntry 2 }


smscSsdLastupdate OBJECT-TYPE
		SYNTAX	TimeTicks
		MAX-ACCESS read-only
		STATUS current
		DESCRIPTION
			"Value which reflects the last time the entities fields have been updated"
	::= { ssdInstanceEntry	3 }

smscSsdNode  OBJECT-TYPE
	SYNTAX  DisplayString
	MAX-ACCESS  read-only
	STATUS   current
	DESCRIPTION
		"Identifies the node the entity is running on."
   ::= {ssdInstanceEntry 4 }

smscSsdMsgReceived OBJECT-TYPE
		SYNTAX	Unsigned32
		MAX-ACCESS read-only
		STATUS current
		DESCRIPTION
			"Received messages"
	::= { ssdInstanceEntry	5 }

smscSsdMsgRejected OBJECT-TYPE
		SYNTAX	Unsigned32
		MAX-ACCESS read-only
		STATUS current
		DESCRIPTION
			"Received messages and rejected"
	::= { ssdInstanceEntry	6 }

smscSsdMsgTransmitted OBJECT-TYPE
		SYNTAX	Unsigned32
		MAX-ACCESS read-only
		STATUS current
		DESCRIPTION
			"Transmitted messages"
	::= { ssdInstanceEntry	7 }

smscSsdMsgFailed OBJECT-TYPE
		SYNTAX	Unsigned32
		MAX-ACCESS read-only
		STATUS current
		DESCRIPTION
			"Messages that failed on sending"
	::= { ssdInstanceEntry	8 }

smscSsdQelemUsed OBJECT-TYPE
		SYNTAX	Unsigned32
		MAX-ACCESS read-only
		STATUS current
		DESCRIPTION
			"Number of elements in internal queues"
	::= { ssdInstanceEntry	9 }

smscSsdQelemInProcqueue OBJECT-TYPE
		SYNTAX	Unsigned32
		MAX-ACCESS read-only
		STATUS current
		DESCRIPTION
			"Number of elements used in process queue"
	::= { ssdInstanceEntry	10 }

smscSsdQelemInExpqueue OBJECT-TYPE
		SYNTAX	Unsigned32
		MAX-ACCESS read-only
		STATUS current
		DESCRIPTION
			"Number of elements used in expedited queue"
	::= { ssdInstanceEntry	11 }

smscSsdNrTimersRunning OBJECT-TYPE
		SYNTAX	Unsigned32
		MAX-ACCESS read-only
		STATUS current
		DESCRIPTION
			"Total number of timers running"
	::= { ssdInstanceEntry	12 }

smscSsdNrSystemTimers OBJECT-TYPE
		SYNTAX	Unsigned32
		MAX-ACCESS read-only
		STATUS current
		DESCRIPTION
			"Number of system timers running"
	::= { ssdInstanceEntry	13 }

smscSsdImiRecallQelem OBJECT-TYPE
		SYNTAX	Unsigned32
		MAX-ACCESS read-only
		STATUS current
		DESCRIPTION
			"Number of IMI recall-queue elements used"
	::= { ssdInstanceEntry	14 }

smscSsdImiRecallQueues OBJECT-TYPE
		SYNTAX	Unsigned32
		MAX-ACCESS read-only
		STATUS current
		DESCRIPTION
			"Number of IMI-recall-queues used"
	::= { ssdInstanceEntry	15 }

smscSsdIdiRecallQelem OBJECT-TYPE
		SYNTAX	Unsigned32
		MAX-ACCESS read-only
		STATUS current
		DESCRIPTION
			"Number of IDI recall-queue elements used"
	::= { ssdInstanceEntry	16 }

smscSsdIdiRecallQueues OBJECT-TYPE
		SYNTAX	Unsigned32
		MAX-ACCESS read-only
		STATUS current
		DESCRIPTION
			"Number of IDI recall-queues used"
	::= { ssdInstanceEntry	17 }

smscSsdIosRecallQelem OBJECT-TYPE
		SYNTAX	Unsigned32
		MAX-ACCESS read-only
		STATUS current
		DESCRIPTION
			"Number of IOS recall-queue elements used"
	::= { ssdInstanceEntry	18 }

smscSsdIosRecallQueues OBJECT-TYPE
		SYNTAX	Unsigned32
		MAX-ACCESS read-only
		STATUS current
		DESCRIPTION
			"Number of IOS recall-queues used"
	::= { ssdInstanceEntry	19 }

smscSsdLogRecallQelem OBJECT-TYPE
		SYNTAX	Unsigned32
		MAX-ACCESS read-only
		STATUS current
		DESCRIPTION
			"Number of LOG recall-queue elements used"
	::= { ssdInstanceEntry	20 }

smscSsdLogRecallQueues OBJECT-TYPE
		SYNTAX	Unsigned32
		MAX-ACCESS read-only
		STATUS current
		DESCRIPTION
			"Number of LOG recall-queues used"
	::= { ssdInstanceEntry	21 }

smscSsdTrcreqDiscarded OBJECT-TYPE
		SYNTAX	Unsigned32
		MAX-ACCESS read-only
		STATUS current
		DESCRIPTION
			"Number of trace requests discarded"
	::= { ssdInstanceEntry	22 }

smscSsdDummyStatistic OBJECT-TYPE
		SYNTAX	Unsigned32
		MAX-ACCESS read-only
		STATUS current
		DESCRIPTION
			"No statistical counters"
	::= { ssdInstanceEntry	23 }



-- end of SSD description.
-- --------------------------------------


-- --------------------------------------
-- Class PRH
-- 
smscPrh OBJECT-TYPE
	SYNTAX  SEQUENCE OF PrhInstanceEntry
	MAX-ACCESS  not-accessible
	STATUS  current
	DESCRIPTION
		"Mapping table for SMSC PRH entities."
   ::= { smscClassOther   4  }

prhInstanceEntry  OBJECT-TYPE
	SYNTAX PrhInstanceEntry
	MAX-ACCESS  not-accessible
	STATUS  current
	DESCRIPTION
		"An entry (row) in the entityInstanceTable."
	INDEX { IMPLIED smscPrhName }
   ::= { smscPrh 1 }

PrhInstanceEntry ::= SEQUENCE {
		smscPrhName     DisplayString,
		smscPrhState   INTEGER,
		smscPrhLastupdate   TimeTicks,
		smscPrhNode	   DisplayString, 
		smscPrhMsgReceived	 Unsigned32, 
		smscPrhMsgRejected	 Unsigned32, 
		smscPrhMsgTransmitted	 Unsigned32, 
		smscPrhMsgFailed	 Unsigned32, 
		smscPrhQelemUsed	 Unsigned32, 
		smscPrhQelemInProcqueue	 Unsigned32, 
		smscPrhQelemInExpqueue	 Unsigned32, 
		smscPrhNrTimersRunning	 Unsigned32, 
		smscPrhNrSystemTimers	 Unsigned32, 
		smscPrhImiRecallQelem	 Unsigned32, 
		smscPrhImiRecallQueues	 Unsigned32, 
		smscPrhIdiRecallQelem	 Unsigned32, 
		smscPrhIdiRecallQueues	 Unsigned32, 
		smscPrhIosRecallQelem	 Unsigned32, 
		smscPrhIosRecallQueues	 Unsigned32, 
		smscPrhLogRecallQelem	 Unsigned32, 
		smscPrhLogRecallQueues	 Unsigned32, 
		smscPrhTrcreqDiscarded	 Unsigned32, 
		smscPrhDummyStatistic	 Unsigned32, 
		smscPrhSappCacheHits	 Unsigned32, 
		smscPrhSappCacheMisses	 Unsigned32
	}

smscPrhName  OBJECT-TYPE
	SYNTAX  DisplayString
	MAX-ACCESS  read-only
	STATUS   current
	DESCRIPTION
		"Identifies the name of the entity."
   ::= {prhInstanceEntry 1 }

smscPrhState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { prhInstanceEntry 2 }


smscPrhLastupdate OBJECT-TYPE
		SYNTAX	TimeTicks
		MAX-ACCESS read-only
		STATUS current
		DESCRIPTION
			"Value which reflects the last time the entities fields have been updated"
	::= { prhInstanceEntry	3 }

smscPrhNode  OBJECT-TYPE
	SYNTAX  DisplayString
	MAX-ACCESS  read-only
	STATUS   current
	DESCRIPTION
		"Identifies the node the entity is running on."
   ::= {prhInstanceEntry 4 }

smscPrhMsgReceived OBJECT-TYPE
		SYNTAX	Unsigned32
		MAX-ACCESS read-only
		STATUS current
		DESCRIPTION
			"Received messages"
	::= { prhInstanceEntry	5 }

smscPrhMsgRejected OBJECT-TYPE
		SYNTAX	Unsigned32
		MAX-ACCESS read-only
		STATUS current
		DESCRIPTION
			"Received messages and rejected"
	::= { prhInstanceEntry	6 }

smscPrhMsgTransmitted OBJECT-TYPE
		SYNTAX	Unsigned32
		MAX-ACCESS read-only
		STATUS current
		DESCRIPTION
			"Transmitted messages"
	::= { prhInstanceEntry	7 }

smscPrhMsgFailed OBJECT-TYPE
		SYNTAX	Unsigned32
		MAX-ACCESS read-only
		STATUS current
		DESCRIPTION
			"Messages that failed on sending"
	::= { prhInstanceEntry	8 }

smscPrhQelemUsed OBJECT-TYPE
		SYNTAX	Unsigned32
		MAX-ACCESS read-only
		STATUS current
		DESCRIPTION
			"Number of elements in internal queues"
	::= { prhInstanceEntry	9 }

smscPrhQelemInProcqueue OBJECT-TYPE
		SYNTAX	Unsigned32
		MAX-ACCESS read-only
		STATUS current
		DESCRIPTION
			"Number of elements used in process queue"
	::= { prhInstanceEntry	10 }

smscPrhQelemInExpqueue OBJECT-TYPE
		SYNTAX	Unsigned32
		MAX-ACCESS read-only
		STATUS current
		DESCRIPTION
			"Number of elements used in expedited queue"
	::= { prhInstanceEntry	11 }

smscPrhNrTimersRunning OBJECT-TYPE
		SYNTAX	Unsigned32
		MAX-ACCESS read-only
		STATUS current
		DESCRIPTION
			"Total number of timers running"
	::= { prhInstanceEntry	12 }

smscPrhNrSystemTimers OBJECT-TYPE
		SYNTAX	Unsigned32
		MAX-ACCESS read-only
		STATUS current
		DESCRIPTION
			"Number of system timers running"
	::= { prhInstanceEntry	13 }

smscPrhImiRecallQelem OBJECT-TYPE
		SYNTAX	Unsigned32
		MAX-ACCESS read-only
		STATUS current
		DESCRIPTION
			"Number of IMI recall-queue elements used"
	::= { prhInstanceEntry	14 }

smscPrhImiRecallQueues OBJECT-TYPE
		SYNTAX	Unsigned32
		MAX-ACCESS read-only
		STATUS current
		DESCRIPTION
			"Number of IMI-recall-queues used"
	::= { prhInstanceEntry	15 }

smscPrhIdiRecallQelem OBJECT-TYPE
		SYNTAX	Unsigned32
		MAX-ACCESS read-only
		STATUS current
		DESCRIPTION
			"Number of IDI recall-queue elements used"
	::= { prhInstanceEntry	16 }

smscPrhIdiRecallQueues OBJECT-TYPE
		SYNTAX	Unsigned32
		MAX-ACCESS read-only
		STATUS current
		DESCRIPTION
			"Number of IDI recall-queues used"
	::= { prhInstanceEntry	17 }

smscPrhIosRecallQelem OBJECT-TYPE
		SYNTAX	Unsigned32
		MAX-ACCESS read-only
		STATUS current
		DESCRIPTION
			"Number of IOS recall-queue elements used"
	::= { prhInstanceEntry	18 }

smscPrhIosRecallQueues OBJECT-TYPE
		SYNTAX	Unsigned32
		MAX-ACCESS read-only
		STATUS current
		DESCRIPTION
			"Number of IOS recall-queues used"
	::= { prhInstanceEntry	19 }

smscPrhLogRecallQelem OBJECT-TYPE
		SYNTAX	Unsigned32
		MAX-ACCESS read-only
		STATUS current
		DESCRIPTION
			"Number of LOG recall-queue elements used"
	::= { prhInstanceEntry	20 }

smscPrhLogRecallQueues OBJECT-TYPE
		SYNTAX	Unsigned32
		MAX-ACCESS read-only
		STATUS current
		DESCRIPTION
			"Number of LOG recall-queues used"
	::= { prhInstanceEntry	21 }

smscPrhTrcreqDiscarded OBJECT-TYPE
		SYNTAX	Unsigned32
		MAX-ACCESS read-only
		STATUS current
		DESCRIPTION
			"Number of trace requests discarded"
	::= { prhInstanceEntry	22 }

smscPrhDummyStatistic OBJECT-TYPE
		SYNTAX	Unsigned32
		MAX-ACCESS read-only
		STATUS current
		DESCRIPTION
			"No statistical counters"
	::= { prhInstanceEntry	23 }

smscPrhSappCacheHits OBJECT-TYPE
		SYNTAX	Unsigned32
		MAX-ACCESS read-only
		STATUS current
		DESCRIPTION
			"SAPP message cache hits"
	::= { prhInstanceEntry	24 }

smscPrhSappCacheMisses OBJECT-TYPE
		SYNTAX	Unsigned32
		MAX-ACCESS read-only
		STATUS current
		DESCRIPTION
			"SAPP message cache misses"
	::= { prhInstanceEntry	25 }



-- end of PRH description.
-- --------------------------------------


-- --------------------------------------
-- Class FRH
-- 
smscFrh OBJECT-TYPE
	SYNTAX  SEQUENCE OF FrhInstanceEntry
	MAX-ACCESS  not-accessible
	STATUS  current
	DESCRIPTION
		"Mapping table for SMSC FRH entities."
   ::= { smscClassOther   5  }

frhInstanceEntry  OBJECT-TYPE
	SYNTAX FrhInstanceEntry
	MAX-ACCESS  not-accessible
	STATUS  current
	DESCRIPTION
		"An entry (row) in the entityInstanceTable."
	INDEX { IMPLIED smscFrhName }
   ::= { smscFrh 1 }

FrhInstanceEntry ::= SEQUENCE {
		smscFrhName     DisplayString,
		smscFrhState   INTEGER,
		smscFrhLastupdate   TimeTicks,
		smscFrhNode	   DisplayString, 
		smscFrhMsgReceived	 Unsigned32, 
		smscFrhMsgRejected	 Unsigned32, 
		smscFrhMsgTransmitted	 Unsigned32, 
		smscFrhMsgFailed	 Unsigned32, 
		smscFrhQelemUsed	 Unsigned32, 
		smscFrhQelemInProcqueue	 Unsigned32, 
		smscFrhQelemInExpqueue	 Unsigned32, 
		smscFrhNrTimersRunning	 Unsigned32, 
		smscFrhNrSystemTimers	 Unsigned32, 
		smscFrhImiRecallQelem	 Unsigned32, 
		smscFrhImiRecallQueues	 Unsigned32, 
		smscFrhIdiRecallQelem	 Unsigned32, 
		smscFrhIdiRecallQueues	 Unsigned32, 
		smscFrhIosRecallQelem	 Unsigned32, 
		smscFrhIosRecallQueues	 Unsigned32, 
		smscFrhLogRecallQelem	 Unsigned32, 
		smscFrhLogRecallQueues	 Unsigned32, 
		smscFrhTrcreqDiscarded	 Unsigned32, 
		smscFrhReportFirst	 Unsigned32, 
		smscFrhReportRetry	 Unsigned32, 
		smscFrhReportFailed	 Unsigned32, 
		smscFrhReportsSent	 Unsigned32
	}

smscFrhName  OBJECT-TYPE
	SYNTAX  DisplayString
	MAX-ACCESS  read-only
	STATUS   current
	DESCRIPTION
		"Identifies the name of the entity."
   ::= {frhInstanceEntry 1 }

smscFrhState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { frhInstanceEntry 2 }


smscFrhLastupdate OBJECT-TYPE
		SYNTAX	TimeTicks
		MAX-ACCESS read-only
		STATUS current
		DESCRIPTION
			"Value which reflects the last time the entities fields have been updated"
	::= { frhInstanceEntry	3 }

smscFrhNode  OBJECT-TYPE
	SYNTAX  DisplayString
	MAX-ACCESS  read-only
	STATUS   current
	DESCRIPTION
		"Identifies the node the entity is running on."
   ::= {frhInstanceEntry 4 }

smscFrhMsgReceived OBJECT-TYPE
		SYNTAX	Unsigned32
		MAX-ACCESS read-only
		STATUS current
		DESCRIPTION
			"Received messages"
	::= { frhInstanceEntry	5 }

smscFrhMsgRejected OBJECT-TYPE
		SYNTAX	Unsigned32
		MAX-ACCESS read-only
		STATUS current
		DESCRIPTION
			"Received messages and rejected"
	::= { frhInstanceEntry	6 }

smscFrhMsgTransmitted OBJECT-TYPE
		SYNTAX	Unsigned32
		MAX-ACCESS read-only
		STATUS current
		DESCRIPTION
			"Transmitted messages"
	::= { frhInstanceEntry	7 }

smscFrhMsgFailed OBJECT-TYPE
		SYNTAX	Unsigned32
		MAX-ACCESS read-only
		STATUS current
		DESCRIPTION
			"Messages that failed on sending"
	::= { frhInstanceEntry	8 }

smscFrhQelemUsed OBJECT-TYPE
		SYNTAX	Unsigned32
		MAX-ACCESS read-only
		STATUS current
		DESCRIPTION
			"Number of elements in internal queues"
	::= { frhInstanceEntry	9 }

smscFrhQelemInProcqueue OBJECT-TYPE
		SYNTAX	Unsigned32
		MAX-ACCESS read-only
		STATUS current
		DESCRIPTION
			"Number of elements used in process queue"
	::= { frhInstanceEntry	10 }

smscFrhQelemInExpqueue OBJECT-TYPE
		SYNTAX	Unsigned32
		MAX-ACCESS read-only
		STATUS current
		DESCRIPTION
			"Number of elements used in expedited queue"
	::= { frhInstanceEntry	11 }

smscFrhNrTimersRunning OBJECT-TYPE
		SYNTAX	Unsigned32
		MAX-ACCESS read-only
		STATUS current
		DESCRIPTION
			"Total number of timers running"
	::= { frhInstanceEntry	12 }

smscFrhNrSystemTimers OBJECT-TYPE
		SYNTAX	Unsigned32
		MAX-ACCESS read-only
		STATUS current
		DESCRIPTION
			"Number of system timers running"
	::= { frhInstanceEntry	13 }

smscFrhImiRecallQelem OBJECT-TYPE
		SYNTAX	Unsigned32
		MAX-ACCESS read-only
		STATUS current
		DESCRIPTION
			"Number of IMI recall-queue elements used"
	::= { frhInstanceEntry	14 }

smscFrhImiRecallQueues OBJECT-TYPE
		SYNTAX	Unsigned32
		MAX-ACCESS read-only
		STATUS current
		DESCRIPTION
			"Number of IMI-recall-queues used"
	::= { frhInstanceEntry	15 }

smscFrhIdiRecallQelem OBJECT-TYPE
		SYNTAX	Unsigned32
		MAX-ACCESS read-only
		STATUS current
		DESCRIPTION
			"Number of IDI recall-queue elements used"
	::= { frhInstanceEntry	16 }

smscFrhIdiRecallQueues OBJECT-TYPE
		SYNTAX	Unsigned32
		MAX-ACCESS read-only
		STATUS current
		DESCRIPTION
			"Number of IDI recall-queues used"
	::= { frhInstanceEntry	17 }

smscFrhIosRecallQelem OBJECT-TYPE
		SYNTAX	Unsigned32
		MAX-ACCESS read-only
		STATUS current
		DESCRIPTION
			"Number of IOS recall-queue elements used"
	::= { frhInstanceEntry	18 }

smscFrhIosRecallQueues OBJECT-TYPE
		SYNTAX	Unsigned32
		MAX-ACCESS read-only
		STATUS current
		DESCRIPTION
			"Number of IOS recall-queues used"
	::= { frhInstanceEntry	19 }

smscFrhLogRecallQelem OBJECT-TYPE
		SYNTAX	Unsigned32
		MAX-ACCESS read-only
		STATUS current
		DESCRIPTION
			"Number of LOG recall-queue elements used"
	::= { frhInstanceEntry	20 }

smscFrhLogRecallQueues OBJECT-TYPE
		SYNTAX	Unsigned32
		MAX-ACCESS read-only
		STATUS current
		DESCRIPTION
			"Number of LOG recall-queues used"
	::= { frhInstanceEntry	21 }

smscFrhTrcreqDiscarded OBJECT-TYPE
		SYNTAX	Unsigned32
		MAX-ACCESS read-only
		STATUS current
		DESCRIPTION
			"Number of trace requests discarded"
	::= { frhInstanceEntry	22 }

smscFrhReportFirst OBJECT-TYPE
		SYNTAX	Unsigned32
		MAX-ACCESS read-only
		STATUS current
		DESCRIPTION
			"Number of reports successfully delivered in first attempt"
	::= { frhInstanceEntry	23 }

smscFrhReportRetry OBJECT-TYPE
		SYNTAX	Unsigned32
		MAX-ACCESS read-only
		STATUS current
		DESCRIPTION
			"Number of reports successfully delivered after retries"
	::= { frhInstanceEntry	24 }

smscFrhReportFailed OBJECT-TYPE
		SYNTAX	Unsigned32
		MAX-ACCESS read-only
		STATUS current
		DESCRIPTION
			"Number of reports not delivered because retry scheme expired"
	::= { frhInstanceEntry	25 }

smscFrhReportsSent OBJECT-TYPE
		SYNTAX	Unsigned32
		MAX-ACCESS read-only
		STATUS current
		DESCRIPTION
			"Number of reports sent"
	::= { frhInstanceEntry	26 }



-- end of FRH description.
-- --------------------------------------


-- --------------------------------------
-- Class LOGSRV
-- 
smscLogsrv OBJECT-TYPE
	SYNTAX  SEQUENCE OF LogsrvInstanceEntry
	MAX-ACCESS  not-accessible
	STATUS  current
	DESCRIPTION
		"Mapping table for SMSC LOGSRV entities."
   ::= { smscClassOther   6  }

logsrvInstanceEntry  OBJECT-TYPE
	SYNTAX LogsrvInstanceEntry
	MAX-ACCESS  not-accessible
	STATUS  current
	DESCRIPTION
		"An entry (row) in the entityInstanceTable."
	INDEX { IMPLIED smscLogsrvName }
   ::= { smscLogsrv 1 }

LogsrvInstanceEntry ::= SEQUENCE {
		smscLogsrvName     DisplayString,
		smscLogsrvState   INTEGER,
		smscLogsrvLastupdate   TimeTicks,
		smscLogsrvNode	   DisplayString, 
		smscLogsrvMsgReceived	 Unsigned32, 
		smscLogsrvMsgRejected	 Unsigned32, 
		smscLogsrvMsgTransmitted	 Unsigned32, 
		smscLogsrvMsgFailed	 Unsigned32, 
		smscLogsrvQelemUsed	 Unsigned32, 
		smscLogsrvQelemInProcqueue	 Unsigned32, 
		smscLogsrvQelemInExpqueue	 Unsigned32, 
		smscLogsrvNrTimersRunning	 Unsigned32, 
		smscLogsrvNrSystemTimers	 Unsigned32, 
		smscLogsrvImiRecallQelem	 Unsigned32, 
		smscLogsrvImiRecallQueues	 Unsigned32, 
		smscLogsrvIdiRecallQelem	 Unsigned32, 
		smscLogsrvIdiRecallQueues	 Unsigned32, 
		smscLogsrvIosRecallQelem	 Unsigned32, 
		smscLogsrvIosRecallQueues	 Unsigned32, 
		smscLogsrvLogRecallQelem	 Unsigned32, 
		smscLogsrvLogRecallQueues	 Unsigned32, 
		smscLogsrvTrcreqDiscarded	 Unsigned32, 
		smscLogsrvIdiReceived	 Unsigned32, 
		smscLogsrvIdiLogged	 Unsigned32, 
		smscLogsrvFrpReceived	 Unsigned32, 
		smscLogsrvFrpLogged	 Unsigned32, 
		smscLogsrvFlgReceived	 Unsigned32, 
		smscLogsrvFlgLogged	 Unsigned32, 
		smscLogsrvTotReceived	 Unsigned32, 
		smscLogsrvTotLogged	 Unsigned32, 
		smscLogsrvIdiCdrWritten	 Unsigned32, 
		smscLogsrvFrpCdrWritten	 Unsigned32, 
		smscLogsrvTotCdrWritten	 Unsigned32, 
		smscLogsrvCdrBlocked	 Unsigned32, 
		smscLogsrvLogBlocked	 Unsigned32, 
		smscLogsrvIdiPrepaidcdrWritten	 Unsigned32, 
		smscLogsrvIdiJammedCdrWritten	 Unsigned32, 
		smscLogsrvIdiCdr1Written	 Unsigned32, 
		smscLogsrvIdiCdr2Written	 Unsigned32, 
		smscLogsrvIdiCdr3Written	 Unsigned32, 
		smscLogsrvIdiCdr4Written	 Unsigned32, 
		smscLogsrvIdiCdr5Written	 Unsigned32, 
		smscLogsrvIdiCdr6Written	 Unsigned32, 
		smscLogsrvIdiCdr7Written	 Unsigned32, 
		smscLogsrvIdiCdr8Written	 Unsigned32, 
		smscLogsrvIdiCdr9Written	 Unsigned32, 
		smscLogsrvIdiCdr10Written	 Unsigned32, 
		smscLogsrvPrepaidCdrBlocked	 Unsigned32, 
		smscLogsrvJammedCdrBlocked	 Unsigned32, 
		smscLogsrvCdr1Blocked	 Unsigned32, 
		smscLogsrvCdr2Blocked	 Unsigned32, 
		smscLogsrvCdr3Blocked	 Unsigned32, 
		smscLogsrvCdr4Blocked	 Unsigned32, 
		smscLogsrvCdr5Blocked	 Unsigned32, 
		smscLogsrvCdr6Blocked	 Unsigned32, 
		smscLogsrvCdr7Blocked	 Unsigned32, 
		smscLogsrvCdr8Blocked	 Unsigned32, 
		smscLogsrvCdr9Blocked	 Unsigned32, 
		smscLogsrvCdr10Blocked	 Unsigned32
	}

smscLogsrvName  OBJECT-TYPE
	SYNTAX  DisplayString
	MAX-ACCESS  read-only
	STATUS   current
	DESCRIPTION
		"Identifies the name of the entity."
   ::= {logsrvInstanceEntry 1 }

smscLogsrvState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { logsrvInstanceEntry 2 }


smscLogsrvLastupdate OBJECT-TYPE
		SYNTAX	TimeTicks
		MAX-ACCESS read-only
		STATUS current
		DESCRIPTION
			"Value which reflects the last time the entities fields have been updated"
	::= { logsrvInstanceEntry	3 }

smscLogsrvNode  OBJECT-TYPE
	SYNTAX  DisplayString
	MAX-ACCESS  read-only
	STATUS   current
	DESCRIPTION
		"Identifies the node the entity is running on."
   ::= {logsrvInstanceEntry 4 }

smscLogsrvMsgReceived OBJECT-TYPE
		SYNTAX	Unsigned32
		MAX-ACCESS read-only
		STATUS current
		DESCRIPTION
			"Received messages"
	::= { logsrvInstanceEntry	5 }

smscLogsrvMsgRejected OBJECT-TYPE
		SYNTAX	Unsigned32
		MAX-ACCESS read-only
		STATUS current
		DESCRIPTION
			"Received messages and rejected"
	::= { logsrvInstanceEntry	6 }

smscLogsrvMsgTransmitted OBJECT-TYPE
		SYNTAX	Unsigned32
		MAX-ACCESS read-only
		STATUS current
		DESCRIPTION
			"Transmitted messages"
	::= { logsrvInstanceEntry	7 }

smscLogsrvMsgFailed OBJECT-TYPE
		SYNTAX	Unsigned32
		MAX-ACCESS read-only
		STATUS current
		DESCRIPTION
			"Messages that failed on sending"
	::= { logsrvInstanceEntry	8 }

smscLogsrvQelemUsed OBJECT-TYPE
		SYNTAX	Unsigned32
		MAX-ACCESS read-only
		STATUS current
		DESCRIPTION
			"Number of elements in internal queues"
	::= { logsrvInstanceEntry	9 }

smscLogsrvQelemInProcqueue OBJECT-TYPE
		SYNTAX	Unsigned32
		MAX-ACCESS read-only
		STATUS current
		DESCRIPTION
			"Number of elements used in process queue"
	::= { logsrvInstanceEntry	10 }

smscLogsrvQelemInExpqueue OBJECT-TYPE
		SYNTAX	Unsigned32
		MAX-ACCESS read-only
		STATUS current
		DESCRIPTION
			"Number of elements used in expedited queue"
	::= { logsrvInstanceEntry	11 }

smscLogsrvNrTimersRunning OBJECT-TYPE
		SYNTAX	Unsigned32
		MAX-ACCESS read-only
		STATUS current
		DESCRIPTION
			"Total number of timers running"
	::= { logsrvInstanceEntry	12 }

smscLogsrvNrSystemTimers OBJECT-TYPE
		SYNTAX	Unsigned32
		MAX-ACCESS read-only
		STATUS current
		DESCRIPTION
			"Number of system timers running"
	::= { logsrvInstanceEntry	13 }

smscLogsrvImiRecallQelem OBJECT-TYPE
		SYNTAX	Unsigned32
		MAX-ACCESS read-only
		STATUS current
		DESCRIPTION
			"Number of IMI recall-queue elements used"
	::= { logsrvInstanceEntry	14 }

smscLogsrvImiRecallQueues OBJECT-TYPE
		SYNTAX	Unsigned32
		MAX-ACCESS read-only
		STATUS current
		DESCRIPTION
			"Number of IMI-recall-queues used"
	::= { logsrvInstanceEntry	15 }

smscLogsrvIdiRecallQelem OBJECT-TYPE
		SYNTAX	Unsigned32
		MAX-ACCESS read-only
		STATUS current
		DESCRIPTION
			"Number of IDI recall-queue elements used"
	::= { logsrvInstanceEntry	16 }

smscLogsrvIdiRecallQueues OBJECT-TYPE
		SYNTAX	Unsigned32
		MAX-ACCESS read-only
		STATUS current
		DESCRIPTION
			"Number of IDI recall-queues used"
	::= { logsrvInstanceEntry	17 }

smscLogsrvIosRecallQelem OBJECT-TYPE
		SYNTAX	Unsigned32
		MAX-ACCESS read-only
		STATUS current
		DESCRIPTION
			"Number of IOS recall-queue elements used"
	::= { logsrvInstanceEntry	18 }

smscLogsrvIosRecallQueues OBJECT-TYPE
		SYNTAX	Unsigned32
		MAX-ACCESS read-only
		STATUS current
		DESCRIPTION
			"Number of IOS recall-queues used"
	::= { logsrvInstanceEntry	19 }

smscLogsrvLogRecallQelem OBJECT-TYPE
		SYNTAX	Unsigned32
		MAX-ACCESS read-only
		STATUS current
		DESCRIPTION
			"Number of LOG recall-queue elements used"
	::= { logsrvInstanceEntry	20 }

smscLogsrvLogRecallQueues OBJECT-TYPE
		SYNTAX	Unsigned32
		MAX-ACCESS read-only
		STATUS current
		DESCRIPTION
			"Number of LOG recall-queues used"
	::= { logsrvInstanceEntry	21 }

smscLogsrvTrcreqDiscarded OBJECT-TYPE
		SYNTAX	Unsigned32
		MAX-ACCESS read-only
		STATUS current
		DESCRIPTION
			"Number of trace requests discarded"
	::= { logsrvInstanceEntry	22 }

smscLogsrvIdiReceived OBJECT-TYPE
		SYNTAX	Unsigned32
		MAX-ACCESS read-only
		STATUS current
		DESCRIPTION
			"Number of IDI log requests received"
	::= { logsrvInstanceEntry	23 }

smscLogsrvIdiLogged OBJECT-TYPE
		SYNTAX	Unsigned32
		MAX-ACCESS read-only
		STATUS current
		DESCRIPTION
			"Number of IDI log requests logged"
	::= { logsrvInstanceEntry	24 }

smscLogsrvFrpReceived OBJECT-TYPE
		SYNTAX	Unsigned32
		MAX-ACCESS read-only
		STATUS current
		DESCRIPTION
			"Number of FRP log requests received"
	::= { logsrvInstanceEntry	25 }

smscLogsrvFrpLogged OBJECT-TYPE
		SYNTAX	Unsigned32
		MAX-ACCESS read-only
		STATUS current
		DESCRIPTION
			"Number of FRP log requests logged"
	::= { logsrvInstanceEntry	26 }

smscLogsrvFlgReceived OBJECT-TYPE
		SYNTAX	Unsigned32
		MAX-ACCESS read-only
		STATUS current
		DESCRIPTION
			"Number of FLG log requests received"
	::= { logsrvInstanceEntry	27 }

smscLogsrvFlgLogged OBJECT-TYPE
		SYNTAX	Unsigned32
		MAX-ACCESS read-only
		STATUS current
		DESCRIPTION
			"Number of FLG log requests logged"
	::= { logsrvInstanceEntry	28 }

smscLogsrvTotReceived OBJECT-TYPE
		SYNTAX	Unsigned32
		MAX-ACCESS read-only
		STATUS current
		DESCRIPTION
			"Total number of log requests received"
	::= { logsrvInstanceEntry	29 }

smscLogsrvTotLogged OBJECT-TYPE
		SYNTAX	Unsigned32
		MAX-ACCESS read-only
		STATUS current
		DESCRIPTION
			"Total number of log requests logged"
	::= { logsrvInstanceEntry	30 }

smscLogsrvIdiCdrWritten OBJECT-TYPE
		SYNTAX	Unsigned32
		MAX-ACCESS read-only
		STATUS current
		DESCRIPTION
			"Number of ASN.1 CDR requests written"
	::= { logsrvInstanceEntry	31 }

smscLogsrvFrpCdrWritten OBJECT-TYPE
		SYNTAX	Unsigned32
		MAX-ACCESS read-only
		STATUS current
		DESCRIPTION
			"Number of FRP CDR requests written"
	::= { logsrvInstanceEntry	32 }

smscLogsrvTotCdrWritten OBJECT-TYPE
		SYNTAX	Unsigned32
		MAX-ACCESS read-only
		STATUS current
		DESCRIPTION
			"Total number of CDR (any type) requests written"
	::= { logsrvInstanceEntry	33 }

smscLogsrvCdrBlocked OBJECT-TYPE
		SYNTAX	Unsigned32
		MAX-ACCESS read-only
		STATUS current
		DESCRIPTION
			"Total number of requests blocked by CDR filter"
	::= { logsrvInstanceEntry	34 }

smscLogsrvLogBlocked OBJECT-TYPE
		SYNTAX	Unsigned32
		MAX-ACCESS read-only
		STATUS current
		DESCRIPTION
			"Total number of LOG requests blocked by LOGfilter"
	::= { logsrvInstanceEntry	35 }

smscLogsrvIdiPrepaidcdrWritten OBJECT-TYPE
		SYNTAX	Unsigned32
		MAX-ACCESS read-only
		STATUS current
		DESCRIPTION
			"Number of IDI ASN.1 prepaid CDR requests written"
	::= { logsrvInstanceEntry	36 }

smscLogsrvIdiJammedCdrWritten OBJECT-TYPE
		SYNTAX	Unsigned32
		MAX-ACCESS read-only
		STATUS current
		DESCRIPTION
			"Number of IDI ASN.1 jammed CDR requests written"
	::= { logsrvInstanceEntry	37 }

smscLogsrvIdiCdr1Written OBJECT-TYPE
		SYNTAX	Unsigned32
		MAX-ACCESS read-only
		STATUS current
		DESCRIPTION
			"Number of ASN.1 CDR requests written"
	::= { logsrvInstanceEntry	38 }

smscLogsrvIdiCdr2Written OBJECT-TYPE
		SYNTAX	Unsigned32
		MAX-ACCESS read-only
		STATUS current
		DESCRIPTION
			"Number of ASN.1 CDR requests written"
	::= { logsrvInstanceEntry	39 }

smscLogsrvIdiCdr3Written OBJECT-TYPE
		SYNTAX	Unsigned32
		MAX-ACCESS read-only
		STATUS current
		DESCRIPTION
			"Number of ASN.1 CDR requests written"
	::= { logsrvInstanceEntry	40 }

smscLogsrvIdiCdr4Written OBJECT-TYPE
		SYNTAX	Unsigned32
		MAX-ACCESS read-only
		STATUS current
		DESCRIPTION
			"Number of ASN.1 CDR requests written"
	::= { logsrvInstanceEntry	41 }

smscLogsrvIdiCdr5Written OBJECT-TYPE
		SYNTAX	Unsigned32
		MAX-ACCESS read-only
		STATUS current
		DESCRIPTION
			"Number of ASN.1 CDR requests written"
	::= { logsrvInstanceEntry	42 }

smscLogsrvIdiCdr6Written OBJECT-TYPE
		SYNTAX	Unsigned32
		MAX-ACCESS read-only
		STATUS current
		DESCRIPTION
			"Number of ASN.1 CDR requests written"
	::= { logsrvInstanceEntry	43 }

smscLogsrvIdiCdr7Written OBJECT-TYPE
		SYNTAX	Unsigned32
		MAX-ACCESS read-only
		STATUS current
		DESCRIPTION
			"Number of ASN.1 CDR requests written"
	::= { logsrvInstanceEntry	44 }

smscLogsrvIdiCdr8Written OBJECT-TYPE
		SYNTAX	Unsigned32
		MAX-ACCESS read-only
		STATUS current
		DESCRIPTION
			"Number of ASN.1 CDR requests written"
	::= { logsrvInstanceEntry	45 }

smscLogsrvIdiCdr9Written OBJECT-TYPE
		SYNTAX	Unsigned32
		MAX-ACCESS read-only
		STATUS current
		DESCRIPTION
			"Number of ASN.1 CDR requests written"
	::= { logsrvInstanceEntry	46 }

smscLogsrvIdiCdr10Written OBJECT-TYPE
		SYNTAX	Unsigned32
		MAX-ACCESS read-only
		STATUS current
		DESCRIPTION
			"Number of ASN.1 CDR requests written"
	::= { logsrvInstanceEntry	47 }

smscLogsrvPrepaidCdrBlocked OBJECT-TYPE
		SYNTAX	Unsigned32
		MAX-ACCESS read-only
		STATUS current
		DESCRIPTION
			"Total number of prepaid CDR requests blocked byprepaid CDR filter"
	::= { logsrvInstanceEntry	48 }

smscLogsrvJammedCdrBlocked OBJECT-TYPE
		SYNTAX	Unsigned32
		MAX-ACCESS read-only
		STATUS current
		DESCRIPTION
			"Total number of jammed CDR requests blocked byjammed CDR filter"
	::= { logsrvInstanceEntry	49 }

smscLogsrvCdr1Blocked OBJECT-TYPE
		SYNTAX	Unsigned32
		MAX-ACCESS read-only
		STATUS current
		DESCRIPTION
			"Total number of CDR requests blocked byCDR filter"
	::= { logsrvInstanceEntry	50 }

smscLogsrvCdr2Blocked OBJECT-TYPE
		SYNTAX	Unsigned32
		MAX-ACCESS read-only
		STATUS current
		DESCRIPTION
			"Total number of CDR requests blocked byCDR filter"
	::= { logsrvInstanceEntry	51 }

smscLogsrvCdr3Blocked OBJECT-TYPE
		SYNTAX	Unsigned32
		MAX-ACCESS read-only
		STATUS current
		DESCRIPTION
			"Total number of CDR requests blocked byCDR filter"
	::= { logsrvInstanceEntry	52 }

smscLogsrvCdr4Blocked OBJECT-TYPE
		SYNTAX	Unsigned32
		MAX-ACCESS read-only
		STATUS current
		DESCRIPTION
			"Total number of CDR requests blocked byCDR filter"
	::= { logsrvInstanceEntry	53 }

smscLogsrvCdr5Blocked OBJECT-TYPE
		SYNTAX	Unsigned32
		MAX-ACCESS read-only
		STATUS current
		DESCRIPTION
			"Total number of CDR requests blocked byCDR filter"
	::= { logsrvInstanceEntry	54 }

smscLogsrvCdr6Blocked OBJECT-TYPE
		SYNTAX	Unsigned32
		MAX-ACCESS read-only
		STATUS current
		DESCRIPTION
			"Total number of CDR requests blocked byCDR filter"
	::= { logsrvInstanceEntry	55 }

smscLogsrvCdr7Blocked OBJECT-TYPE
		SYNTAX	Unsigned32
		MAX-ACCESS read-only
		STATUS current
		DESCRIPTION
			"Total number of CDR requests blocked byCDR filter"
	::= { logsrvInstanceEntry	56 }

smscLogsrvCdr8Blocked OBJECT-TYPE
		SYNTAX	Unsigned32
		MAX-ACCESS read-only
		STATUS current
		DESCRIPTION
			"Total number of CDR requests blocked byCDR filter"
	::= { logsrvInstanceEntry	57 }

smscLogsrvCdr9Blocked OBJECT-TYPE
		SYNTAX	Unsigned32
		MAX-ACCESS read-only
		STATUS current
		DESCRIPTION
			"Total number of CDR requests blocked byCDR filter"
	::= { logsrvInstanceEntry	58 }

smscLogsrvCdr10Blocked OBJECT-TYPE
		SYNTAX	Unsigned32
		MAX-ACCESS read-only
		STATUS current
		DESCRIPTION
			"Total number of CDR requests blocked byCDR filter"
	::= { logsrvInstanceEntry	59 }



-- end of LOGSRV description.
-- --------------------------------------


-- --------------------------------------
-- Class TRCSRV
-- 
smscTrcsrv OBJECT-TYPE
	SYNTAX  SEQUENCE OF TrcsrvInstanceEntry
	MAX-ACCESS  not-accessible
	STATUS  current
	DESCRIPTION
		"Mapping table for SMSC TRCSRV entities."
   ::= { smscClassOther   7  }

trcsrvInstanceEntry  OBJECT-TYPE
	SYNTAX TrcsrvInstanceEntry
	MAX-ACCESS  not-accessible
	STATUS  current
	DESCRIPTION
		"An entry (row) in the entityInstanceTable."
	INDEX { IMPLIED smscTrcsrvName }
   ::= { smscTrcsrv 1 }

TrcsrvInstanceEntry ::= SEQUENCE {
		smscTrcsrvName     DisplayString,
		smscTrcsrvState   INTEGER,
		smscTrcsrvLastupdate   TimeTicks,
		smscTrcsrvNode	   DisplayString, 
		smscTrcsrvMsgReceived	 Unsigned32, 
		smscTrcsrvMsgRejected	 Unsigned32, 
		smscTrcsrvMsgTransmitted	 Unsigned32, 
		smscTrcsrvMsgFailed	 Unsigned32, 
		smscTrcsrvQelemUsed	 Unsigned32, 
		smscTrcsrvQelemInProcqueue	 Unsigned32, 
		smscTrcsrvQelemInExpqueue	 Unsigned32, 
		smscTrcsrvNrTimersRunning	 Unsigned32, 
		smscTrcsrvNrSystemTimers	 Unsigned32, 
		smscTrcsrvImiRecallQelem	 Unsigned32, 
		smscTrcsrvImiRecallQueues	 Unsigned32, 
		smscTrcsrvIdiRecallQelem	 Unsigned32, 
		smscTrcsrvIdiRecallQueues	 Unsigned32, 
		smscTrcsrvIosRecallQelem	 Unsigned32, 
		smscTrcsrvIosRecallQueues	 Unsigned32, 
		smscTrcsrvLogRecallQelem	 Unsigned32, 
		smscTrcsrvLogRecallQueues	 Unsigned32, 
		smscTrcsrvTrcreqDiscarded	 Unsigned32, 
		smscTrcsrvDummyStatistic	 Unsigned32, 
		smscTrcsrvTrcReceived	 Unsigned32, 
		smscTrcsrvTrcDiscarded	 Unsigned32, 
		smscTrcsrvTrcLogged	 Unsigned32
	}

smscTrcsrvName  OBJECT-TYPE
	SYNTAX  DisplayString
	MAX-ACCESS  read-only
	STATUS   current
	DESCRIPTION
		"Identifies the name of the entity."
   ::= {trcsrvInstanceEntry 1 }

smscTrcsrvState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { trcsrvInstanceEntry 2 }


smscTrcsrvLastupdate OBJECT-TYPE
		SYNTAX	TimeTicks
		MAX-ACCESS read-only
		STATUS current
		DESCRIPTION
			"Value which reflects the last time the entities fields have been updated"
	::= { trcsrvInstanceEntry	3 }

smscTrcsrvNode  OBJECT-TYPE
	SYNTAX  DisplayString
	MAX-ACCESS  read-only
	STATUS   current
	DESCRIPTION
		"Identifies the node the entity is running on."
   ::= {trcsrvInstanceEntry 4 }

smscTrcsrvMsgReceived OBJECT-TYPE
		SYNTAX	Unsigned32
		MAX-ACCESS read-only
		STATUS current
		DESCRIPTION
			"Received messages"
	::= { trcsrvInstanceEntry	5 }

smscTrcsrvMsgRejected OBJECT-TYPE
		SYNTAX	Unsigned32
		MAX-ACCESS read-only
		STATUS current
		DESCRIPTION
			"Received messages and rejected"
	::= { trcsrvInstanceEntry	6 }

smscTrcsrvMsgTransmitted OBJECT-TYPE
		SYNTAX	Unsigned32
		MAX-ACCESS read-only
		STATUS current
		DESCRIPTION
			"Transmitted messages"
	::= { trcsrvInstanceEntry	7 }

smscTrcsrvMsgFailed OBJECT-TYPE
		SYNTAX	Unsigned32
		MAX-ACCESS read-only
		STATUS current
		DESCRIPTION
			"Messages that failed on sending"
	::= { trcsrvInstanceEntry	8 }

smscTrcsrvQelemUsed OBJECT-TYPE
		SYNTAX	Unsigned32
		MAX-ACCESS read-only
		STATUS current
		DESCRIPTION
			"Number of elements in internal queues"
	::= { trcsrvInstanceEntry	9 }

smscTrcsrvQelemInProcqueue OBJECT-TYPE
		SYNTAX	Unsigned32
		MAX-ACCESS read-only
		STATUS current
		DESCRIPTION
			"Number of elements used in process queue"
	::= { trcsrvInstanceEntry	10 }

smscTrcsrvQelemInExpqueue OBJECT-TYPE
		SYNTAX	Unsigned32
		MAX-ACCESS read-only
		STATUS current
		DESCRIPTION
			"Number of elements used in expedited queue"
	::= { trcsrvInstanceEntry	11 }

smscTrcsrvNrTimersRunning OBJECT-TYPE
		SYNTAX	Unsigned32
		MAX-ACCESS read-only
		STATUS current
		DESCRIPTION
			"Total number of timers running"
	::= { trcsrvInstanceEntry	12 }

smscTrcsrvNrSystemTimers OBJECT-TYPE
		SYNTAX	Unsigned32
		MAX-ACCESS read-only
		STATUS current
		DESCRIPTION
			"Number of system timers running"
	::= { trcsrvInstanceEntry	13 }

smscTrcsrvImiRecallQelem OBJECT-TYPE
		SYNTAX	Unsigned32
		MAX-ACCESS read-only
		STATUS current
		DESCRIPTION
			"Number of IMI recall-queue elements used"
	::= { trcsrvInstanceEntry	14 }

smscTrcsrvImiRecallQueues OBJECT-TYPE
		SYNTAX	Unsigned32
		MAX-ACCESS read-only
		STATUS current
		DESCRIPTION
			"Number of IMI-recall-queues used"
	::= { trcsrvInstanceEntry	15 }

smscTrcsrvIdiRecallQelem OBJECT-TYPE
		SYNTAX	Unsigned32
		MAX-ACCESS read-only
		STATUS current
		DESCRIPTION
			"Number of IDI recall-queue elements used"
	::= { trcsrvInstanceEntry	16 }

smscTrcsrvIdiRecallQueues OBJECT-TYPE
		SYNTAX	Unsigned32
		MAX-ACCESS read-only
		STATUS current
		DESCRIPTION
			"Number of IDI recall-queues used"
	::= { trcsrvInstanceEntry	17 }

smscTrcsrvIosRecallQelem OBJECT-TYPE
		SYNTAX	Unsigned32
		MAX-ACCESS read-only
		STATUS current
		DESCRIPTION
			"Number of IOS recall-queue elements used"
	::= { trcsrvInstanceEntry	18 }

smscTrcsrvIosRecallQueues OBJECT-TYPE
		SYNTAX	Unsigned32
		MAX-ACCESS read-only
		STATUS current
		DESCRIPTION
			"Number of IOS recall-queues used"
	::= { trcsrvInstanceEntry	19 }

smscTrcsrvLogRecallQelem OBJECT-TYPE
		SYNTAX	Unsigned32
		MAX-ACCESS read-only
		STATUS current
		DESCRIPTION
			"Number of LOG recall-queue elements used"
	::= { trcsrvInstanceEntry	20 }

smscTrcsrvLogRecallQueues OBJECT-TYPE
		SYNTAX	Unsigned32
		MAX-ACCESS read-only
		STATUS current
		DESCRIPTION
			"Number of LOG recall-queues used"
	::= { trcsrvInstanceEntry	21 }

smscTrcsrvTrcreqDiscarded OBJECT-TYPE
		SYNTAX	Unsigned32
		MAX-ACCESS read-only
		STATUS current
		DESCRIPTION
			"Number of trace requests discarded"
	::= { trcsrvInstanceEntry	22 }

smscTrcsrvDummyStatistic OBJECT-TYPE
		SYNTAX	Unsigned32
		MAX-ACCESS read-only
		STATUS current
		DESCRIPTION
			"No statistical counters"
	::= { trcsrvInstanceEntry	23 }

smscTrcsrvTrcReceived OBJECT-TYPE
		SYNTAX	Unsigned32
		MAX-ACCESS read-only
		STATUS current
		DESCRIPTION
			"Number of trace messages received"
	::= { trcsrvInstanceEntry	24 }

smscTrcsrvTrcDiscarded OBJECT-TYPE
		SYNTAX	Unsigned32
		MAX-ACCESS read-only
		STATUS current
		DESCRIPTION
			"Number of trace messages discarded"
	::= { trcsrvInstanceEntry	25 }

smscTrcsrvTrcLogged OBJECT-TYPE
		SYNTAX	Unsigned32
		MAX-ACCESS read-only
		STATUS current
		DESCRIPTION
			"Number of trace messages written to file"
	::= { trcsrvInstanceEntry	26 }



-- end of TRCSRV description.
-- --------------------------------------


-- --------------------------------------
-- Class PBR
-- 
smscPbr OBJECT-TYPE
	SYNTAX  SEQUENCE OF PbrInstanceEntry
	MAX-ACCESS  not-accessible
	STATUS  current
	DESCRIPTION
		"Mapping table for SMSC PBR entities."
   ::= { smscClassOther   8  }

pbrInstanceEntry  OBJECT-TYPE
	SYNTAX PbrInstanceEntry
	MAX-ACCESS  not-accessible
	STATUS  current
	DESCRIPTION
		"An entry (row) in the entityInstanceTable."
	INDEX { IMPLIED smscPbrName }
   ::= { smscPbr 1 }

PbrInstanceEntry ::= SEQUENCE {
		smscPbrName     DisplayString,
		smscPbrState   INTEGER,
		smscPbrLastupdate   TimeTicks,
		smscPbrNode	   DisplayString, 
		smscPbrMsgReceived	 Unsigned32, 
		smscPbrMsgRejected	 Unsigned32, 
		smscPbrMsgTransmitted	 Unsigned32, 
		smscPbrMsgFailed	 Unsigned32, 
		smscPbrQelemUsed	 Unsigned32, 
		smscPbrQelemInProcqueue	 Unsigned32, 
		smscPbrQelemInExpqueue	 Unsigned32, 
		smscPbrNrTimersRunning	 Unsigned32, 
		smscPbrNrSystemTimers	 Unsigned32, 
		smscPbrImiRecallQelem	 Unsigned32, 
		smscPbrImiRecallQueues	 Unsigned32, 
		smscPbrIdiRecallQelem	 Unsigned32, 
		smscPbrIdiRecallQueues	 Unsigned32, 
		smscPbrIosRecallQelem	 Unsigned32, 
		smscPbrIosRecallQueues	 Unsigned32, 
		smscPbrLogRecallQelem	 Unsigned32, 
		smscPbrLogRecallQueues	 Unsigned32, 
		smscPbrTrcreqDiscarded	 Unsigned32, 
		smscPbrPrimserChargedDebit	 Unsigned32, 
		smscPbrPrimserFreeDebit	 Unsigned32, 
		smscPbrPrimserChargedCredit	 Unsigned32, 
		smscPbrPrimserFreeCredit	 Unsigned32, 
		smscPbrAddserChargedDebit	 Unsigned32, 
		smscPbrAddserFreeDebit	 Unsigned32, 
		smscPbrAddserChargedCredit	 Unsigned32, 
		smscPbrAddserFreeCredit	 Unsigned32, 
		smscPbrSubTriggers	 Unsigned32, 
		smscPbrPrimackUnblocked	 Unsigned32, 
		smscPbrPrimackBlocked	 Unsigned32, 
		smscPbrPrimackPostpaid	 Unsigned32, 
		smscPbrAddackUnblocked	 Unsigned32, 
		smscPbrAddackBlocked	 Unsigned32, 
		smscPbrAddackPostpaid	 Unsigned32, 
		smscPbrPpCacheConsults	 Unsigned32
	}

smscPbrName  OBJECT-TYPE
	SYNTAX  DisplayString
	MAX-ACCESS  read-only
	STATUS   current
	DESCRIPTION
		"Identifies the name of the entity."
   ::= {pbrInstanceEntry 1 }

smscPbrState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { pbrInstanceEntry 2 }


smscPbrLastupdate OBJECT-TYPE
		SYNTAX	TimeTicks
		MAX-ACCESS read-only
		STATUS current
		DESCRIPTION
			"Value which reflects the last time the entities fields have been updated"
	::= { pbrInstanceEntry	3 }

smscPbrNode  OBJECT-TYPE
	SYNTAX  DisplayString
	MAX-ACCESS  read-only
	STATUS   current
	DESCRIPTION
		"Identifies the node the entity is running on."
   ::= {pbrInstanceEntry 4 }

smscPbrMsgReceived OBJECT-TYPE
		SYNTAX	Unsigned32
		MAX-ACCESS read-only
		STATUS current
		DESCRIPTION
			"Received messages"
	::= { pbrInstanceEntry	5 }

smscPbrMsgRejected OBJECT-TYPE
		SYNTAX	Unsigned32
		MAX-ACCESS read-only
		STATUS current
		DESCRIPTION
			"Received messages and rejected"
	::= { pbrInstanceEntry	6 }

smscPbrMsgTransmitted OBJECT-TYPE
		SYNTAX	Unsigned32
		MAX-ACCESS read-only
		STATUS current
		DESCRIPTION
			"Transmitted messages"
	::= { pbrInstanceEntry	7 }

smscPbrMsgFailed OBJECT-TYPE
		SYNTAX	Unsigned32
		MAX-ACCESS read-only
		STATUS current
		DESCRIPTION
			"Messages that failed on sending"
	::= { pbrInstanceEntry	8 }

smscPbrQelemUsed OBJECT-TYPE
		SYNTAX	Unsigned32
		MAX-ACCESS read-only
		STATUS current
		DESCRIPTION
			"Number of elements in internal queues"
	::= { pbrInstanceEntry	9 }

smscPbrQelemInProcqueue OBJECT-TYPE
		SYNTAX	Unsigned32
		MAX-ACCESS read-only
		STATUS current
		DESCRIPTION
			"Number of elements used in process queue"
	::= { pbrInstanceEntry	10 }

smscPbrQelemInExpqueue OBJECT-TYPE
		SYNTAX	Unsigned32
		MAX-ACCESS read-only
		STATUS current
		DESCRIPTION
			"Number of elements used in expedited queue"
	::= { pbrInstanceEntry	11 }

smscPbrNrTimersRunning OBJECT-TYPE
		SYNTAX	Unsigned32
		MAX-ACCESS read-only
		STATUS current
		DESCRIPTION
			"Total number of timers running"
	::= { pbrInstanceEntry	12 }

smscPbrNrSystemTimers OBJECT-TYPE
		SYNTAX	Unsigned32
		MAX-ACCESS read-only
		STATUS current
		DESCRIPTION
			"Number of system timers running"
	::= { pbrInstanceEntry	13 }

smscPbrImiRecallQelem OBJECT-TYPE
		SYNTAX	Unsigned32
		MAX-ACCESS read-only
		STATUS current
		DESCRIPTION
			"Number of IMI recall-queue elements used"
	::= { pbrInstanceEntry	14 }

smscPbrImiRecallQueues OBJECT-TYPE
		SYNTAX	Unsigned32
		MAX-ACCESS read-only
		STATUS current
		DESCRIPTION
			"Number of IMI-recall-queues used"
	::= { pbrInstanceEntry	15 }

smscPbrIdiRecallQelem OBJECT-TYPE
		SYNTAX	Unsigned32
		MAX-ACCESS read-only
		STATUS current
		DESCRIPTION
			"Number of IDI recall-queue elements used"
	::= { pbrInstanceEntry	16 }

smscPbrIdiRecallQueues OBJECT-TYPE
		SYNTAX	Unsigned32
		MAX-ACCESS read-only
		STATUS current
		DESCRIPTION
			"Number of IDI recall-queues used"
	::= { pbrInstanceEntry	17 }

smscPbrIosRecallQelem OBJECT-TYPE
		SYNTAX	Unsigned32
		MAX-ACCESS read-only
		STATUS current
		DESCRIPTION
			"Number of IOS recall-queue elements used"
	::= { pbrInstanceEntry	18 }

smscPbrIosRecallQueues OBJECT-TYPE
		SYNTAX	Unsigned32
		MAX-ACCESS read-only
		STATUS current
		DESCRIPTION
			"Number of IOS recall-queues used"
	::= { pbrInstanceEntry	19 }

smscPbrLogRecallQelem OBJECT-TYPE
		SYNTAX	Unsigned32
		MAX-ACCESS read-only
		STATUS current
		DESCRIPTION
			"Number of LOG recall-queue elements used"
	::= { pbrInstanceEntry	20 }

smscPbrLogRecallQueues OBJECT-TYPE
		SYNTAX	Unsigned32
		MAX-ACCESS read-only
		STATUS current
		DESCRIPTION
			"Number of LOG recall-queues used"
	::= { pbrInstanceEntry	21 }

smscPbrTrcreqDiscarded OBJECT-TYPE
		SYNTAX	Unsigned32
		MAX-ACCESS read-only
		STATUS current
		DESCRIPTION
			"Number of trace requests discarded"
	::= { pbrInstanceEntry	22 }

smscPbrPrimserChargedDebit OBJECT-TYPE
		SYNTAX	Unsigned32
		MAX-ACCESS read-only
		STATUS current
		DESCRIPTION
			"Number of PRIM_SERVICE (debit, charged) msgs"
	::= { pbrInstanceEntry	23 }

smscPbrPrimserFreeDebit OBJECT-TYPE
		SYNTAX	Unsigned32
		MAX-ACCESS read-only
		STATUS current
		DESCRIPTION
			"Number of PRIM_SERVICE (debit, free) msgs"
	::= { pbrInstanceEntry	24 }

smscPbrPrimserChargedCredit OBJECT-TYPE
		SYNTAX	Unsigned32
		MAX-ACCESS read-only
		STATUS current
		DESCRIPTION
			"Number of PRIM_SERVICE (credit, charged) msgs"
	::= { pbrInstanceEntry	25 }

smscPbrPrimserFreeCredit OBJECT-TYPE
		SYNTAX	Unsigned32
		MAX-ACCESS read-only
		STATUS current
		DESCRIPTION
			"Number of PRIM_SERVICE (credit, free) msgs"
	::= { pbrInstanceEntry	26 }

smscPbrAddserChargedDebit OBJECT-TYPE
		SYNTAX	Unsigned32
		MAX-ACCESS read-only
		STATUS current
		DESCRIPTION
			"Number of ADD_SERVICE (debit, charged) msgs"
	::= { pbrInstanceEntry	27 }

smscPbrAddserFreeDebit OBJECT-TYPE
		SYNTAX	Unsigned32
		MAX-ACCESS read-only
		STATUS current
		DESCRIPTION
			"Number of ADD_SERVICE (debit, free) msgs"
	::= { pbrInstanceEntry	28 }

smscPbrAddserChargedCredit OBJECT-TYPE
		SYNTAX	Unsigned32
		MAX-ACCESS read-only
		STATUS current
		DESCRIPTION
			"Number of ADD_SERVICE (credit, charged) msgs"
	::= { pbrInstanceEntry	29 }

smscPbrAddserFreeCredit OBJECT-TYPE
		SYNTAX	Unsigned32
		MAX-ACCESS read-only
		STATUS current
		DESCRIPTION
			"Number of ADD_SERVICE (credit, free) msgs"
	::= { pbrInstanceEntry	30 }

smscPbrSubTriggers OBJECT-TYPE
		SYNTAX	Unsigned32
		MAX-ACCESS read-only
		STATUS current
		DESCRIPTION
			"Number of SUB_TRIGGER msgs"
	::= { pbrInstanceEntry	31 }

smscPbrPrimackUnblocked OBJECT-TYPE
		SYNTAX	Unsigned32
		MAX-ACCESS read-only
		STATUS current
		DESCRIPTION
			"Number PRIMACK (UNBLOCKED) msgs"
	::= { pbrInstanceEntry	32 }

smscPbrPrimackBlocked OBJECT-TYPE
		SYNTAX	Unsigned32
		MAX-ACCESS read-only
		STATUS current
		DESCRIPTION
			"Number PRIMACK (BLOCKED) msgs"
	::= { pbrInstanceEntry	33 }

smscPbrPrimackPostpaid OBJECT-TYPE
		SYNTAX	Unsigned32
		MAX-ACCESS read-only
		STATUS current
		DESCRIPTION
			"Number PRIMACK (POSTPAID) msgs"
	::= { pbrInstanceEntry	34 }

smscPbrAddackUnblocked OBJECT-TYPE
		SYNTAX	Unsigned32
		MAX-ACCESS read-only
		STATUS current
		DESCRIPTION
			"Number ADDACK (UNBLOCKED) msgs"
	::= { pbrInstanceEntry	35 }

smscPbrAddackBlocked OBJECT-TYPE
		SYNTAX	Unsigned32
		MAX-ACCESS read-only
		STATUS current
		DESCRIPTION
			"Number ADDACK (BLOCKED) msgs"
	::= { pbrInstanceEntry	36 }

smscPbrAddackPostpaid OBJECT-TYPE
		SYNTAX	Unsigned32
		MAX-ACCESS read-only
		STATUS current
		DESCRIPTION
			"Number ADDACK (POSTPAID) msgs"
	::= { pbrInstanceEntry	37 }

smscPbrPpCacheConsults OBJECT-TYPE
		SYNTAX	Unsigned32
		MAX-ACCESS read-only
		STATUS current
		DESCRIPTION
			"Number cache consults"
	::= { pbrInstanceEntry	38 }



-- end of PBR description.
-- --------------------------------------


-- --------------------------------------
-- Class PBB
-- 
smscPbb OBJECT-TYPE
	SYNTAX  SEQUENCE OF PbbInstanceEntry
	MAX-ACCESS  not-accessible
	STATUS  current
	DESCRIPTION
		"Mapping table for SMSC PBB entities."
   ::= { smscClassOther   9  }

pbbInstanceEntry  OBJECT-TYPE
	SYNTAX PbbInstanceEntry
	MAX-ACCESS  not-accessible
	STATUS  current
	DESCRIPTION
		"An entry (row) in the entityInstanceTable."
	INDEX { IMPLIED smscPbbName }
   ::= { smscPbb 1 }

PbbInstanceEntry ::= SEQUENCE {
		smscPbbName     DisplayString,
		smscPbbState   INTEGER,
		smscPbbLastupdate   TimeTicks,
		smscPbbNode	   DisplayString, 
		smscPbbMsgReceived	 Unsigned32, 
		smscPbbMsgRejected	 Unsigned32, 
		smscPbbMsgTransmitted	 Unsigned32, 
		smscPbbMsgFailed	 Unsigned32, 
		smscPbbQelemUsed	 Unsigned32, 
		smscPbbQelemInProcqueue	 Unsigned32, 
		smscPbbQelemInExpqueue	 Unsigned32, 
		smscPbbNrTimersRunning	 Unsigned32, 
		smscPbbNrSystemTimers	 Unsigned32, 
		smscPbbImiRecallQelem	 Unsigned32, 
		smscPbbImiRecallQueues	 Unsigned32, 
		smscPbbIdiRecallQelem	 Unsigned32, 
		smscPbbIdiRecallQueues	 Unsigned32, 
		smscPbbIosRecallQelem	 Unsigned32, 
		smscPbbIosRecallQueues	 Unsigned32, 
		smscPbbLogRecallQelem	 Unsigned32, 
		smscPbbLogRecallQueues	 Unsigned32, 
		smscPbbTrcreqDiscarded	 Unsigned32, 
		smscPbbAddReceived	 Unsigned32, 
		smscPbbAddOk	 Unsigned32, 
		smscPbbAddNok	 Unsigned32, 
		smscPbbRemoveReceived	 Unsigned32, 
		smscPbbRemoveOk	 Unsigned32, 
		smscPbbRemoveNok	 Unsigned32, 
		smscPbbBlockReceived	 Unsigned32, 
		smscPbbBlockOk	 Unsigned32, 
		smscPbbBlockNok	 Unsigned32, 
		smscPbbUnblockReceived	 Unsigned32, 
		smscPbbUnblockOk	 Unsigned32, 
		smscPbbUnblockNok	 Unsigned32
	}

smscPbbName  OBJECT-TYPE
	SYNTAX  DisplayString
	MAX-ACCESS  read-only
	STATUS   current
	DESCRIPTION
		"Identifies the name of the entity."
   ::= {pbbInstanceEntry 1 }

smscPbbState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { pbbInstanceEntry 2 }


smscPbbLastupdate OBJECT-TYPE
		SYNTAX	TimeTicks
		MAX-ACCESS read-only
		STATUS current
		DESCRIPTION
			"Value which reflects the last time the entities fields have been updated"
	::= { pbbInstanceEntry	3 }

smscPbbNode  OBJECT-TYPE
	SYNTAX  DisplayString
	MAX-ACCESS  read-only
	STATUS   current
	DESCRIPTION
		"Identifies the node the entity is running on."
   ::= {pbbInstanceEntry 4 }

smscPbbMsgReceived OBJECT-TYPE
		SYNTAX	Unsigned32
		MAX-ACCESS read-only
		STATUS current
		DESCRIPTION
			"Received messages"
	::= { pbbInstanceEntry	5 }

smscPbbMsgRejected OBJECT-TYPE
		SYNTAX	Unsigned32
		MAX-ACCESS read-only
		STATUS current
		DESCRIPTION
			"Received messages and rejected"
	::= { pbbInstanceEntry	6 }

smscPbbMsgTransmitted OBJECT-TYPE
		SYNTAX	Unsigned32
		MAX-ACCESS read-only
		STATUS current
		DESCRIPTION
			"Transmitted messages"
	::= { pbbInstanceEntry	7 }

smscPbbMsgFailed OBJECT-TYPE
		SYNTAX	Unsigned32
		MAX-ACCESS read-only
		STATUS current
		DESCRIPTION
			"Messages that failed on sending"
	::= { pbbInstanceEntry	8 }

smscPbbQelemUsed OBJECT-TYPE
		SYNTAX	Unsigned32
		MAX-ACCESS read-only
		STATUS current
		DESCRIPTION
			"Number of elements in internal queues"
	::= { pbbInstanceEntry	9 }

smscPbbQelemInProcqueue OBJECT-TYPE
		SYNTAX	Unsigned32
		MAX-ACCESS read-only
		STATUS current
		DESCRIPTION
			"Number of elements used in process queue"
	::= { pbbInstanceEntry	10 }

smscPbbQelemInExpqueue OBJECT-TYPE
		SYNTAX	Unsigned32
		MAX-ACCESS read-only
		STATUS current
		DESCRIPTION
			"Number of elements used in expedited queue"
	::= { pbbInstanceEntry	11 }

smscPbbNrTimersRunning OBJECT-TYPE
		SYNTAX	Unsigned32
		MAX-ACCESS read-only
		STATUS current
		DESCRIPTION
			"Total number of timers running"
	::= { pbbInstanceEntry	12 }

smscPbbNrSystemTimers OBJECT-TYPE
		SYNTAX	Unsigned32
		MAX-ACCESS read-only
		STATUS current
		DESCRIPTION
			"Number of system timers running"
	::= { pbbInstanceEntry	13 }

smscPbbImiRecallQelem OBJECT-TYPE
		SYNTAX	Unsigned32
		MAX-ACCESS read-only
		STATUS current
		DESCRIPTION
			"Number of IMI recall-queue elements used"
	::= { pbbInstanceEntry	14 }

smscPbbImiRecallQueues OBJECT-TYPE
		SYNTAX	Unsigned32
		MAX-ACCESS read-only
		STATUS current
		DESCRIPTION
			"Number of IMI-recall-queues used"
	::= { pbbInstanceEntry	15 }

smscPbbIdiRecallQelem OBJECT-TYPE
		SYNTAX	Unsigned32
		MAX-ACCESS read-only
		STATUS current
		DESCRIPTION
			"Number of IDI recall-queue elements used"
	::= { pbbInstanceEntry	16 }

smscPbbIdiRecallQueues OBJECT-TYPE
		SYNTAX	Unsigned32
		MAX-ACCESS read-only
		STATUS current
		DESCRIPTION
			"Number of IDI recall-queues used"
	::= { pbbInstanceEntry	17 }

smscPbbIosRecallQelem OBJECT-TYPE
		SYNTAX	Unsigned32
		MAX-ACCESS read-only
		STATUS current
		DESCRIPTION
			"Number of IOS recall-queue elements used"
	::= { pbbInstanceEntry	18 }

smscPbbIosRecallQueues OBJECT-TYPE
		SYNTAX	Unsigned32
		MAX-ACCESS read-only
		STATUS current
		DESCRIPTION
			"Number of IOS recall-queues used"
	::= { pbbInstanceEntry	19 }

smscPbbLogRecallQelem OBJECT-TYPE
		SYNTAX	Unsigned32
		MAX-ACCESS read-only
		STATUS current
		DESCRIPTION
			"Number of LOG recall-queue elements used"
	::= { pbbInstanceEntry	20 }

smscPbbLogRecallQueues OBJECT-TYPE
		SYNTAX	Unsigned32
		MAX-ACCESS read-only
		STATUS current
		DESCRIPTION
			"Number of LOG recall-queues used"
	::= { pbbInstanceEntry	21 }

smscPbbTrcreqDiscarded OBJECT-TYPE
		SYNTAX	Unsigned32
		MAX-ACCESS read-only
		STATUS current
		DESCRIPTION
			"Number of trace requests discarded"
	::= { pbbInstanceEntry	22 }

smscPbbAddReceived OBJECT-TYPE
		SYNTAX	Unsigned32
		MAX-ACCESS read-only
		STATUS current
		DESCRIPTION
			"Number of received ADD transactions"
	::= { pbbInstanceEntry	23 }

smscPbbAddOk OBJECT-TYPE
		SYNTAX	Unsigned32
		MAX-ACCESS read-only
		STATUS current
		DESCRIPTION
			"Number of processed ADD transactions"
	::= { pbbInstanceEntry	24 }

smscPbbAddNok OBJECT-TYPE
		SYNTAX	Unsigned32
		MAX-ACCESS read-only
		STATUS current
		DESCRIPTION
			"Number of failed ADD transactions"
	::= { pbbInstanceEntry	25 }

smscPbbRemoveReceived OBJECT-TYPE
		SYNTAX	Unsigned32
		MAX-ACCESS read-only
		STATUS current
		DESCRIPTION
			"Number of received REMOVE transactions"
	::= { pbbInstanceEntry	26 }

smscPbbRemoveOk OBJECT-TYPE
		SYNTAX	Unsigned32
		MAX-ACCESS read-only
		STATUS current
		DESCRIPTION
			"Number of processed REMOVE transactions"
	::= { pbbInstanceEntry	27 }

smscPbbRemoveNok OBJECT-TYPE
		SYNTAX	Unsigned32
		MAX-ACCESS read-only
		STATUS current
		DESCRIPTION
			"Number of failed REMOVE transactions"
	::= { pbbInstanceEntry	28 }

smscPbbBlockReceived OBJECT-TYPE
		SYNTAX	Unsigned32
		MAX-ACCESS read-only
		STATUS current
		DESCRIPTION
			"Number of received BLOCK transactions"
	::= { pbbInstanceEntry	29 }

smscPbbBlockOk OBJECT-TYPE
		SYNTAX	Unsigned32
		MAX-ACCESS read-only
		STATUS current
		DESCRIPTION
			"Number of processed BLOCK transactions"
	::= { pbbInstanceEntry	30 }

smscPbbBlockNok OBJECT-TYPE
		SYNTAX	Unsigned32
		MAX-ACCESS read-only
		STATUS current
		DESCRIPTION
			"Number of failed BLOCK transactions"
	::= { pbbInstanceEntry	31 }

smscPbbUnblockReceived OBJECT-TYPE
		SYNTAX	Unsigned32
		MAX-ACCESS read-only
		STATUS current
		DESCRIPTION
			"Number of received UNBLOCK transactions"
	::= { pbbInstanceEntry	32 }

smscPbbUnblockOk OBJECT-TYPE
		SYNTAX	Unsigned32
		MAX-ACCESS read-only
		STATUS current
		DESCRIPTION
			"Number of processed UNBLOCK transactions"
	::= { pbbInstanceEntry	33 }

smscPbbUnblockNok OBJECT-TYPE
		SYNTAX	Unsigned32
		MAX-ACCESS read-only
		STATUS current
		DESCRIPTION
			"Number of failed UNBLOCK transactions"
	::= { pbbInstanceEntry	34 }



-- end of PBB description.
-- --------------------------------------


-- --------------------------------------
-- Class CMLOG
-- 
smscCmlog OBJECT-TYPE
	SYNTAX  SEQUENCE OF CmlogInstanceEntry
	MAX-ACCESS  not-accessible
	STATUS  current
	DESCRIPTION
		"Mapping table for SMSC CMLOG entities."
   ::= { smscClassOther   10  }

cmlogInstanceEntry  OBJECT-TYPE
	SYNTAX CmlogInstanceEntry
	MAX-ACCESS  not-accessible
	STATUS  current
	DESCRIPTION
		"An entry (row) in the entityInstanceTable."
	INDEX { IMPLIED smscCmlogName }
   ::= { smscCmlog 1 }

CmlogInstanceEntry ::= SEQUENCE {
		smscCmlogName     DisplayString,
		smscCmlogState   INTEGER,
		smscCmlogLastupdate   TimeTicks,
		smscCmlogNode	   DisplayString, 
		smscCmlogMsgReceived	 Unsigned32, 
		smscCmlogMsgRejected	 Unsigned32, 
		smscCmlogMsgTransmitted	 Unsigned32, 
		smscCmlogMsgFailed	 Unsigned32, 
		smscCmlogQelemUsed	 Unsigned32, 
		smscCmlogQelemInProcqueue	 Unsigned32, 
		smscCmlogQelemInExpqueue	 Unsigned32, 
		smscCmlogNrTimersRunning	 Unsigned32, 
		smscCmlogNrSystemTimers	 Unsigned32, 
		smscCmlogImiRecallQelem	 Unsigned32, 
		smscCmlogImiRecallQueues	 Unsigned32, 
		smscCmlogIdiRecallQelem	 Unsigned32, 
		smscCmlogIdiRecallQueues	 Unsigned32, 
		smscCmlogIosRecallQelem	 Unsigned32, 
		smscCmlogIosRecallQueues	 Unsigned32, 
		smscCmlogLogRecallQelem	 Unsigned32, 
		smscCmlogLogRecallQueues	 Unsigned32, 
		smscCmlogTrcreqDiscarded	 Unsigned32, 
		smscCmlogSubmSegmOk	 Unsigned32, 
		smscCmlogSubmSegmDisc	 Unsigned32, 
		smscCmlogDelivSegmOk	 Unsigned32, 
		smscCmlogDelivSegmDisc	 Unsigned32, 
		smscCmlogSubmCmCompl	 Unsigned32, 
		smscCmlogSubmCmIncompl	 Unsigned32, 
		smscCmlogDelivCmCompl	 Unsigned32, 
		smscCmlogDelivCmIncompl	 Unsigned32, 
		smscCmlogExtObjOk	 Unsigned32, 
		smscCmlogSegmUdhNok	 Unsigned32, 
		smscCmlogCmWait	 Unsigned32, 
		smscCmlogEoWait	 Unsigned32, 
		smscCmlogTotLogged	 Unsigned32, 
		smscCmlogIdiCdrWritten	 Unsigned32, 
		smscCmlogIdiPrepaidcdrWritten	 Unsigned32, 
		smscCmlogIdiJammedCdrWritten	 Unsigned32, 
		smscCmlogIdiCdr1Written	 Unsigned32, 
		smscCmlogIdiCdr2Written	 Unsigned32, 
		smscCmlogIdiCdr3Written	 Unsigned32, 
		smscCmlogIdiCdr4Written	 Unsigned32, 
		smscCmlogIdiCdr5Written	 Unsigned32, 
		smscCmlogIdiCdr6Written	 Unsigned32, 
		smscCmlogIdiCdr7Written	 Unsigned32, 
		smscCmlogIdiCdr8Written	 Unsigned32, 
		smscCmlogIdiCdr9Written	 Unsigned32, 
		smscCmlogIdiCdr10Written	 Unsigned32, 
		smscCmlogTotCdrWritten	 Unsigned32, 
		smscCmlogCdrBlocked	 Unsigned32, 
		smscCmlogPrepaidCdrBlocked	 Unsigned32, 
		smscCmlogJammedCdrBlocked	 Unsigned32, 
		smscCmlogCdr1Blocked	 Unsigned32, 
		smscCmlogCdr2Blocked	 Unsigned32, 
		smscCmlogCdr3Blocked	 Unsigned32, 
		smscCmlogCdr4Blocked	 Unsigned32, 
		smscCmlogCdr5Blocked	 Unsigned32, 
		smscCmlogCdr6Blocked	 Unsigned32, 
		smscCmlogCdr7Blocked	 Unsigned32, 
		smscCmlogCdr8Blocked	 Unsigned32, 
		smscCmlogCdr9Blocked	 Unsigned32, 
		smscCmlogCdr10Blocked	 Unsigned32, 
		smscCmlogLogBlocked	 Unsigned32
	}

smscCmlogName  OBJECT-TYPE
	SYNTAX  DisplayString
	MAX-ACCESS  read-only
	STATUS   current
	DESCRIPTION
		"Identifies the name of the entity."
   ::= {cmlogInstanceEntry 1 }

smscCmlogState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { cmlogInstanceEntry 2 }


smscCmlogLastupdate OBJECT-TYPE
		SYNTAX	TimeTicks
		MAX-ACCESS read-only
		STATUS current
		DESCRIPTION
			"Value which reflects the last time the entities fields have been updated"
	::= { cmlogInstanceEntry	3 }

smscCmlogNode  OBJECT-TYPE
	SYNTAX  DisplayString
	MAX-ACCESS  read-only
	STATUS   current
	DESCRIPTION
		"Identifies the node the entity is running on."
   ::= {cmlogInstanceEntry 4 }

smscCmlogMsgReceived OBJECT-TYPE
		SYNTAX	Unsigned32
		MAX-ACCESS read-only
		STATUS current
		DESCRIPTION
			"Received messages"
	::= { cmlogInstanceEntry	5 }

smscCmlogMsgRejected OBJECT-TYPE
		SYNTAX	Unsigned32
		MAX-ACCESS read-only
		STATUS current
		DESCRIPTION
			"Received messages and rejected"
	::= { cmlogInstanceEntry	6 }

smscCmlogMsgTransmitted OBJECT-TYPE
		SYNTAX	Unsigned32
		MAX-ACCESS read-only
		STATUS current
		DESCRIPTION
			"Transmitted messages"
	::= { cmlogInstanceEntry	7 }

smscCmlogMsgFailed OBJECT-TYPE
		SYNTAX	Unsigned32
		MAX-ACCESS read-only
		STATUS current
		DESCRIPTION
			"Messages that failed on sending"
	::= { cmlogInstanceEntry	8 }

smscCmlogQelemUsed OBJECT-TYPE
		SYNTAX	Unsigned32
		MAX-ACCESS read-only
		STATUS current
		DESCRIPTION
			"Number of elements in internal queues"
	::= { cmlogInstanceEntry	9 }

smscCmlogQelemInProcqueue OBJECT-TYPE
		SYNTAX	Unsigned32
		MAX-ACCESS read-only
		STATUS current
		DESCRIPTION
			"Number of elements used in process queue"
	::= { cmlogInstanceEntry	10 }

smscCmlogQelemInExpqueue OBJECT-TYPE
		SYNTAX	Unsigned32
		MAX-ACCESS read-only
		STATUS current
		DESCRIPTION
			"Number of elements used in expedited queue"
	::= { cmlogInstanceEntry	11 }

smscCmlogNrTimersRunning OBJECT-TYPE
		SYNTAX	Unsigned32
		MAX-ACCESS read-only
		STATUS current
		DESCRIPTION
			"Total number of timers running"
	::= { cmlogInstanceEntry	12 }

smscCmlogNrSystemTimers OBJECT-TYPE
		SYNTAX	Unsigned32
		MAX-ACCESS read-only
		STATUS current
		DESCRIPTION
			"Number of system timers running"
	::= { cmlogInstanceEntry	13 }

smscCmlogImiRecallQelem OBJECT-TYPE
		SYNTAX	Unsigned32
		MAX-ACCESS read-only
		STATUS current
		DESCRIPTION
			"Number of IMI recall-queue elements used"
	::= { cmlogInstanceEntry	14 }

smscCmlogImiRecallQueues OBJECT-TYPE
		SYNTAX	Unsigned32
		MAX-ACCESS read-only
		STATUS current
		DESCRIPTION
			"Number of IMI-recall-queues used"
	::= { cmlogInstanceEntry	15 }

smscCmlogIdiRecallQelem OBJECT-TYPE
		SYNTAX	Unsigned32
		MAX-ACCESS read-only
		STATUS current
		DESCRIPTION
			"Number of IDI recall-queue elements used"
	::= { cmlogInstanceEntry	16 }

smscCmlogIdiRecallQueues OBJECT-TYPE
		SYNTAX	Unsigned32
		MAX-ACCESS read-only
		STATUS current
		DESCRIPTION
			"Number of IDI recall-queues used"
	::= { cmlogInstanceEntry	17 }

smscCmlogIosRecallQelem OBJECT-TYPE
		SYNTAX	Unsigned32
		MAX-ACCESS read-only
		STATUS current
		DESCRIPTION
			"Number of IOS recall-queue elements used"
	::= { cmlogInstanceEntry	18 }

smscCmlogIosRecallQueues OBJECT-TYPE
		SYNTAX	Unsigned32
		MAX-ACCESS read-only
		STATUS current
		DESCRIPTION
			"Number of IOS recall-queues used"
	::= { cmlogInstanceEntry	19 }

smscCmlogLogRecallQelem OBJECT-TYPE
		SYNTAX	Unsigned32
		MAX-ACCESS read-only
		STATUS current
		DESCRIPTION
			"Number of LOG recall-queue elements used"
	::= { cmlogInstanceEntry	20 }

smscCmlogLogRecallQueues OBJECT-TYPE
		SYNTAX	Unsigned32
		MAX-ACCESS read-only
		STATUS current
		DESCRIPTION
			"Number of LOG recall-queues used"
	::= { cmlogInstanceEntry	21 }

smscCmlogTrcreqDiscarded OBJECT-TYPE
		SYNTAX	Unsigned32
		MAX-ACCESS read-only
		STATUS current
		DESCRIPTION
			"Number of trace requests discarded"
	::= { cmlogInstanceEntry	22 }

smscCmlogSubmSegmOk OBJECT-TYPE
		SYNTAX	Unsigned32
		MAX-ACCESS read-only
		STATUS current
		DESCRIPTION
			"Number of successfully handled sumitted segments"
	::= { cmlogInstanceEntry	23 }

smscCmlogSubmSegmDisc OBJECT-TYPE
		SYNTAX	Unsigned32
		MAX-ACCESS read-only
		STATUS current
		DESCRIPTION
			"Number of discarded sumitted segments"
	::= { cmlogInstanceEntry	24 }

smscCmlogDelivSegmOk OBJECT-TYPE
		SYNTAX	Unsigned32
		MAX-ACCESS read-only
		STATUS current
		DESCRIPTION
			"Number of successfully handled delivered segments"
	::= { cmlogInstanceEntry	25 }

smscCmlogDelivSegmDisc OBJECT-TYPE
		SYNTAX	Unsigned32
		MAX-ACCESS read-only
		STATUS current
		DESCRIPTION
			"Number of discarded delivered segments"
	::= { cmlogInstanceEntry	26 }

smscCmlogSubmCmCompl OBJECT-TYPE
		SYNTAX	Unsigned32
		MAX-ACCESS read-only
		STATUS current
		DESCRIPTION
			"Number of completed submission CMs"
	::= { cmlogInstanceEntry	27 }

smscCmlogSubmCmIncompl OBJECT-TYPE
		SYNTAX	Unsigned32
		MAX-ACCESS read-only
		STATUS current
		DESCRIPTION
			"Number of timed out submission CMs"
	::= { cmlogInstanceEntry	28 }

smscCmlogDelivCmCompl OBJECT-TYPE
		SYNTAX	Unsigned32
		MAX-ACCESS read-only
		STATUS current
		DESCRIPTION
			"Number of completed delivery CMs"
	::= { cmlogInstanceEntry	29 }

smscCmlogDelivCmIncompl OBJECT-TYPE
		SYNTAX	Unsigned32
		MAX-ACCESS read-only
		STATUS current
		DESCRIPTION
			"Number of timed out delivery CMs"
	::= { cmlogInstanceEntry	30 }

smscCmlogExtObjOk OBJECT-TYPE
		SYNTAX	Unsigned32
		MAX-ACCESS read-only
		STATUS current
		DESCRIPTION
			"Number of Extended Objects handled ok"
	::= { cmlogInstanceEntry	31 }

smscCmlogSegmUdhNok OBJECT-TYPE
		SYNTAX	Unsigned32
		MAX-ACCESS read-only
		STATUS current
		DESCRIPTION
			"Number of segments with incorrect UDH data"
	::= { cmlogInstanceEntry	32 }

smscCmlogCmWait OBJECT-TYPE
		SYNTAX	Unsigned32
		MAX-ACCESS read-only
		STATUS current
		DESCRIPTION
			"Number of CMs waiting"
	::= { cmlogInstanceEntry	33 }

smscCmlogEoWait OBJECT-TYPE
		SYNTAX	Unsigned32
		MAX-ACCESS read-only
		STATUS current
		DESCRIPTION
			"Number of Extended Objects waiting"
	::= { cmlogInstanceEntry	34 }

smscCmlogTotLogged OBJECT-TYPE
		SYNTAX	Unsigned32
		MAX-ACCESS read-only
		STATUS current
		DESCRIPTION
			"Total number of summary log requests logged"
	::= { cmlogInstanceEntry	35 }

smscCmlogIdiCdrWritten OBJECT-TYPE
		SYNTAX	Unsigned32
		MAX-ACCESS read-only
		STATUS current
		DESCRIPTION
			"Number of summary IDI ASN.1-postpaid/prepaid/jammed CDR requests written"
	::= { cmlogInstanceEntry	36 }

smscCmlogIdiPrepaidcdrWritten OBJECT-TYPE
		SYNTAX	Unsigned32
		MAX-ACCESS read-only
		STATUS current
		DESCRIPTION
			"Number of summary IDI ASN.1 prepaid CDR requestswritten"
	::= { cmlogInstanceEntry	37 }

smscCmlogIdiJammedCdrWritten OBJECT-TYPE
		SYNTAX	Unsigned32
		MAX-ACCESS read-only
		STATUS current
		DESCRIPTION
			"Number of summary IDI ASN.1 jammed CDR requestswritten"
	::= { cmlogInstanceEntry	38 }

smscCmlogIdiCdr1Written OBJECT-TYPE
		SYNTAX	Unsigned32
		MAX-ACCESS read-only
		STATUS current
		DESCRIPTION
			"Number of summary IDI ASN.1 CDR requests writtenin CDR 1 stream"
	::= { cmlogInstanceEntry	39 }

smscCmlogIdiCdr2Written OBJECT-TYPE
		SYNTAX	Unsigned32
		MAX-ACCESS read-only
		STATUS current
		DESCRIPTION
			"Number of summary IDI ASN.1 CDR requests writtenin CDR 2 stream"
	::= { cmlogInstanceEntry	40 }

smscCmlogIdiCdr3Written OBJECT-TYPE
		SYNTAX	Unsigned32
		MAX-ACCESS read-only
		STATUS current
		DESCRIPTION
			"Number of summary IDI ASN.1 CDR requests writtenin CDR 3 stream"
	::= { cmlogInstanceEntry	41 }

smscCmlogIdiCdr4Written OBJECT-TYPE
		SYNTAX	Unsigned32
		MAX-ACCESS read-only
		STATUS current
		DESCRIPTION
			"Number of summary IDI ASN.1 CDR requests writtenin CDR 4 stream"
	::= { cmlogInstanceEntry	42 }

smscCmlogIdiCdr5Written OBJECT-TYPE
		SYNTAX	Unsigned32
		MAX-ACCESS read-only
		STATUS current
		DESCRIPTION
			"Number of summary IDI ASN.1 CDR requests writtenin CDR 5 stream"
	::= { cmlogInstanceEntry	43 }

smscCmlogIdiCdr6Written OBJECT-TYPE
		SYNTAX	Unsigned32
		MAX-ACCESS read-only
		STATUS current
		DESCRIPTION
			"Number of summary IDI ASN.1 CDR requests writtenin CDR 6 stream"
	::= { cmlogInstanceEntry	44 }

smscCmlogIdiCdr7Written OBJECT-TYPE
		SYNTAX	Unsigned32
		MAX-ACCESS read-only
		STATUS current
		DESCRIPTION
			"Number of summary IDI ASN.1 CDR requests writtenin CDR 7 stream"
	::= { cmlogInstanceEntry	45 }

smscCmlogIdiCdr8Written OBJECT-TYPE
		SYNTAX	Unsigned32
		MAX-ACCESS read-only
		STATUS current
		DESCRIPTION
			"Number of summary IDI ASN.1 CDR requests writtenin CDR 8 stream"
	::= { cmlogInstanceEntry	46 }

smscCmlogIdiCdr9Written OBJECT-TYPE
		SYNTAX	Unsigned32
		MAX-ACCESS read-only
		STATUS current
		DESCRIPTION
			"Number of summary IDI ASN.1 CDR requests writtenin CDR 9 stream"
	::= { cmlogInstanceEntry	47 }

smscCmlogIdiCdr10Written OBJECT-TYPE
		SYNTAX	Unsigned32
		MAX-ACCESS read-only
		STATUS current
		DESCRIPTION
			"Number of summary IDI ASN.1 CDR requests writtenin CDR 10 stream"
	::= { cmlogInstanceEntry	48 }

smscCmlogTotCdrWritten OBJECT-TYPE
		SYNTAX	Unsigned32
		MAX-ACCESS read-only
		STATUS current
		DESCRIPTION
			"Total number of summary CDR (any type) requestswritten"
	::= { cmlogInstanceEntry	49 }

smscCmlogCdrBlocked OBJECT-TYPE
		SYNTAX	Unsigned32
		MAX-ACCESS read-only
		STATUS current
		DESCRIPTION
			"Total number of SUMMARY IDI ASN.1 postpaid/prepaid/jammed requests blocked by CDR filter"
	::= { cmlogInstanceEntry	50 }

smscCmlogPrepaidCdrBlocked OBJECT-TYPE
		SYNTAX	Unsigned32
		MAX-ACCESS read-only
		STATUS current
		DESCRIPTION
			"Total number of summary prepaid CDR requestsblocked by Prepaid CDR filter"
	::= { cmlogInstanceEntry	51 }

smscCmlogJammedCdrBlocked OBJECT-TYPE
		SYNTAX	Unsigned32
		MAX-ACCESS read-only
		STATUS current
		DESCRIPTION
			"Total number of summary jammed CDR requestsblocked by jammed CDR filter"
	::= { cmlogInstanceEntry	52 }

smscCmlogCdr1Blocked OBJECT-TYPE
		SYNTAX	Unsigned32
		MAX-ACCESS read-only
		STATUS current
		DESCRIPTION
			"Total number of SUMMARY IDI ASN.1 requestsblocked by CDR filter for CDR 1 stream"
	::= { cmlogInstanceEntry	53 }

smscCmlogCdr2Blocked OBJECT-TYPE
		SYNTAX	Unsigned32
		MAX-ACCESS read-only
		STATUS current
		DESCRIPTION
			"Total number of SUMMARY IDI ASN.1 requestsblocked by CDR filter for CDR 2 stream"
	::= { cmlogInstanceEntry	54 }

smscCmlogCdr3Blocked OBJECT-TYPE
		SYNTAX	Unsigned32
		MAX-ACCESS read-only
		STATUS current
		DESCRIPTION
			"Total number of SUMMARY IDI ASN.1 requests blocked by CDR filter for CDR 3 stream"
	::= { cmlogInstanceEntry	55 }

smscCmlogCdr4Blocked OBJECT-TYPE
		SYNTAX	Unsigned32
		MAX-ACCESS read-only
		STATUS current
		DESCRIPTION
			"Total number of SUMMARY IDI ASN.1 requestsblocked by CDR filter for CDR 4 stream"
	::= { cmlogInstanceEntry	56 }

smscCmlogCdr5Blocked OBJECT-TYPE
		SYNTAX	Unsigned32
		MAX-ACCESS read-only
		STATUS current
		DESCRIPTION
			"Total number of SUMMARY IDI ASN.1 requestsblocked by CDR filter for CDR 5 stream"
	::= { cmlogInstanceEntry	57 }

smscCmlogCdr6Blocked OBJECT-TYPE
		SYNTAX	Unsigned32
		MAX-ACCESS read-only
		STATUS current
		DESCRIPTION
			"Total number of SUMMARY IDI ASN.1 requestsblocked by CDR filter for CDR 6 stream"
	::= { cmlogInstanceEntry	58 }

smscCmlogCdr7Blocked OBJECT-TYPE
		SYNTAX	Unsigned32
		MAX-ACCESS read-only
		STATUS current
		DESCRIPTION
			"Total number of SUMMARY IDI ASN.1 requestsblocked by CDR filter for CDR 7 stream"
	::= { cmlogInstanceEntry	59 }

smscCmlogCdr8Blocked OBJECT-TYPE
		SYNTAX	Unsigned32
		MAX-ACCESS read-only
		STATUS current
		DESCRIPTION
			"Total number of SUMMARY IDI ASN.1 requestsblocked by CDR filter for CDR 8 stream"
	::= { cmlogInstanceEntry	60 }

smscCmlogCdr9Blocked OBJECT-TYPE
		SYNTAX	Unsigned32
		MAX-ACCESS read-only
		STATUS current
		DESCRIPTION
			"Total number of SUMMARY IDI ASN.1 requestsblocked by CDR filter for CDR 9 stream"
	::= { cmlogInstanceEntry	61 }

smscCmlogCdr10Blocked OBJECT-TYPE
		SYNTAX	Unsigned32
		MAX-ACCESS read-only
		STATUS current
		DESCRIPTION
			"Total number of SUMMARY IDI ASN.1 requestsblocked by CDR filter for CDR 10 stream"
	::= { cmlogInstanceEntry	62 }

smscCmlogLogBlocked OBJECT-TYPE
		SYNTAX	Unsigned32
		MAX-ACCESS read-only
		STATUS current
		DESCRIPTION
			"Total number of summary LOG requests blockedby LOG filter"
	::= { cmlogInstanceEntry	63 }



-- end of CMLOG description.
-- --------------------------------------


-- --------------------------------------
-- Class IP7
-- 
smscIp7 OBJECT-TYPE
	SYNTAX  SEQUENCE OF Ip7InstanceEntry
	MAX-ACCESS  not-accessible
	STATUS  current
	DESCRIPTION
		"Mapping table for SMSC IP7 entities."
   ::= { smscClassOther   11  }

ip7InstanceEntry  OBJECT-TYPE
	SYNTAX Ip7InstanceEntry
	MAX-ACCESS  not-accessible
	STATUS  current
	DESCRIPTION
		"An entry (row) in the entityInstanceTable."
	INDEX { IMPLIED smscIp7Name }
   ::= { smscIp7 1 }

Ip7InstanceEntry ::= SEQUENCE {
		smscIp7Name     DisplayString,
		smscIp7State   INTEGER,
		smscIp7Lastupdate   TimeTicks,
		smscIp7Node	   DisplayString, 
		smscIp7MsgReceived	 Unsigned32, 
		smscIp7MsgRejected	 Unsigned32, 
		smscIp7MsgTransmitted	 Unsigned32, 
		smscIp7MsgFailed	 Unsigned32, 
		smscIp7QelemUsed	 Unsigned32, 
		smscIp7QelemInProcqueue	 Unsigned32, 
		smscIp7QelemInExpqueue	 Unsigned32, 
		smscIp7NrTimersRunning	 Unsigned32, 
		smscIp7NrSystemTimers	 Unsigned32, 
		smscIp7ImiRecallQelem	 Unsigned32, 
		smscIp7ImiRecallQueues	 Unsigned32, 
		smscIp7IdiRecallQelem	 Unsigned32, 
		smscIp7IdiRecallQueues	 Unsigned32, 
		smscIp7IosRecallQelem	 Unsigned32, 
		smscIp7IosRecallQueues	 Unsigned32, 
		smscIp7LogRecallQelem	 Unsigned32, 
		smscIp7LogRecallQueues	 Unsigned32, 
		smscIp7TrcreqDiscarded	 Unsigned32, 
		smscIp7SctpCtrlChksSnt	 Unsigned32, 
		smscIp7SctpCtrlChksRcvd	 Unsigned32, 
		smscIp7SctpDtChksSnt	 Unsigned32, 
		smscIp7SctpDtChksRetrans	 Unsigned32, 
		smscIp7SctpDtChksSntOrd	 Unsigned32, 
		smscIp7SctpDtChksSntUnord	 Unsigned32, 
		smscIp7SctpDtBytesSnt	 Unsigned32, 
		smscIp7SctpDtChksRcvd	 Unsigned32, 
		smscIp7SctpDtChksDiscarded	 Unsigned32, 
		smscIp7SctpDtChksRcvdOrd	 Unsigned32, 
		smscIp7SctpDtChksRcvdUnrd	 Unsigned32, 
		smscIp7SctpDtBytesRcvd	 Unsigned32, 
		smscIp7SctpDtChksRcvdOos	 Unsigned32, 
		smscIp7SctpSctpDgramsSnt	 Unsigned32, 
		smscIp7SctpSctpDgramsRcvd	 Unsigned32, 
		smscIp7SctpUlpDgramsSnt	 Unsigned32, 
		smscIp7SctpUlpDgramsReady	 Unsigned32, 
		smscIp7SctpUlpDgramsRcvd	 Unsigned32, 
		smscIp7SctpApplReqFree	 Unsigned32, 
		smscIp7SctpApplReqInUse	 Unsigned32, 
		smscIp7SctpApplReqMaxUsed	 Unsigned32, 
		smscIp7SctpApplReqNoMem	 Unsigned32, 
		smscIp7SctpChkDescFree	 Unsigned32, 
		smscIp7SctpChkDescInUse	 Unsigned32, 
		smscIp7SctpChkDescMaxUsed	 Unsigned32, 
		smscIp7SctpChkDescNoMem	 Unsigned32, 
		smscIp7SctpDgrmHdrFree	 Unsigned32, 
		smscIp7SctpDgrmHdrInUse	 Unsigned32, 
		smscIp7SctpDgrmHdrMaxUsed	 Unsigned32, 
		smscIp7SctpDgrmHdrNoMem	 Unsigned32, 
		smscIp7SuaSndBufFree	 Unsigned32, 
		smscIp7SuaSndBufInUse	 Unsigned32, 
		smscIp7SuaSndBufMaxUsed	 Unsigned32, 
		smscIp7SuaSndBufNoMem	 Unsigned32, 
		smscIp7SuaSigNodesFree	 Unsigned32, 
		smscIp7SuaSigNodesInUse	 Unsigned32, 
		smscIp7SuaSigNodesMaxUsed	 Unsigned32, 
		smscIp7SuaSigNodesNoMem	 Unsigned32, 
		smscIp7SctpAssocCurrEstab	 Unsigned32, 
		smscIp7SctpAssocActvEstab	 Unsigned32, 
		smscIp7SctpAssocPassEstab	 Unsigned32, 
		smscIp7SctpAssocAborted	 Unsigned32, 
		smscIp7SctpAssocShutdowns	 Unsigned32, 
		smscIp7SctpT1Expired	 Unsigned32, 
		smscIp7SctpT2Expired	 Unsigned32, 
		smscIp7TcapUnknSprimRcvd	 Unsigned32, 
		smscIp7SuaRasBufFree	 Unsigned32, 
		smscIp7SuaRasBufInUse	 Unsigned32, 
		smscIp7SuaRasBufMaxUsed	 Unsigned32, 
		smscIp7SuaRasBufNoMem	 Unsigned32, 
		smscIp7SuaInvalidMsg	 Unsigned32, 
		smscIp7SuaNoUsers	 Unsigned32, 
		smscIp7SuaNoSpecUser	 Unsigned32, 
		smscIp7SuaTransFailure	 Unsigned32, 
		smscIp7SuaNoReassembly	 Unsigned32, 
		smscIp7SuaFailedReassembly	 Unsigned32, 
		smscIp7SuaNoticeFailure	 Unsigned32, 
		smscIp7SccpSstSent	 Unsigned32, 
		smscIp7SccpSstRcvd	 Unsigned32, 
		smscIp7SccpSspSent	 Unsigned32, 
		smscIp7SccpSspRcvd	 Unsigned32, 
		smscIp7SccpSsaSent	 Unsigned32, 
		smscIp7SccpSsaRcvd	 Unsigned32, 
		smscIp7SccpSscRcvd	 Unsigned32, 
		smscIp7SccpUdtsSent	 Unsigned32, 
		smscIp7SccpUdtsRcvd	 Unsigned32, 
		smscIp7SccpXudtsSent	 Unsigned32, 
		smscIp7SccpXudtsRcvd	 Unsigned32, 
		smscIp7SccpLudtsSent	 Unsigned32, 
		smscIp7SccpLudtsRcvd	 Unsigned32, 
		smscIp7SccpUdtSent	 Unsigned32, 
		smscIp7SccpUdtRcvd	 Unsigned32, 
		smscIp7SccpXudtSent	 Unsigned32, 
		smscIp7SccpXudtRcvd	 Unsigned32, 
		smscIp7SccpLudtSent	 Unsigned32, 
		smscIp7SccpLudtRcvd	 Unsigned32, 
		smscIp7SccpNoReassembly	 Unsigned32, 
		smscIp7SsnmDpcEntFree	 Unsigned32, 
		smscIp7SsnmDpcEntInUse	 Unsigned32, 
		smscIp7SsnmDpcEntMaxUsed	 Unsigned32, 
		smscIp7SsnmDpcEntNoMem	 Unsigned32, 
		smscIp7SsnmStatEntFree	 Unsigned32, 
		smscIp7SsnmStatEntInUse	 Unsigned32, 
		smscIp7SsnmStatEntMxUsd	 Unsigned32, 
		smscIp7SsnmStatEntNoMem	 Unsigned32, 
		smscIp7SsnmSsnEntFree	 Unsigned32, 
		smscIp7SsnmSsnEntInUse	 Unsigned32, 
		smscIp7SsnmSsnEntMaxUsed	 Unsigned32, 
		smscIp7SsnmSsnEntNoMem	 Unsigned32, 
		smscIp7SsrvLocalSsFail	 Unsigned32, 
		smscIp7SsrvLocalMtpFail	 Unsigned32, 
		smscIp7SsrvLocalNtwkCong	 Unsigned32, 
		smscIp7SsrvLocalSccpFail	 Unsigned32, 
		smscIp7SsrvLocalSegmUnsup	 Unsigned32, 
		smscIp7SsrvLocalSegmFail	 Unsigned32, 
		smscIp7SsrvNwRcvNtranNoa	 Unsigned32, 
		smscIp7SsrvNwRcvNtranAddr	 Unsigned32, 
		smscIp7SsrvNwRcvSsCong	 Unsigned32, 
		smscIp7SsrvNwRcvSsFail	 Unsigned32, 
		smscIp7SsrvNwRcvUnequipped	 Unsigned32, 
		smscIp7SsrvNwRcvMtpFail	 Unsigned32, 
		smscIp7SsrvNwRcvNtwkCong	 Unsigned32, 
		smscIp7SsrvNwRcvUnqual	 Unsigned32, 
		smscIp7SsrvNwRcvMsgTrans	 Unsigned32, 
		smscIp7SsrvNwRcvLocalProc	 Unsigned32, 
		smscIp7SsrvNwRcvReasUnsup	 Unsigned32, 
		smscIp7SsrvNwRcvSccpFail	 Unsigned32, 
		smscIp7SsrvNwRcvHopcViol	 Unsigned32, 
		smscIp7SsrvNwRcvSegmUnsup	 Unsigned32, 
		smscIp7SsrvNwRcvSegmFail	 Unsigned32, 
		smscIp7SctpIpSent	 Unsigned32, 
		smscIp7SctpIpSentFailIof	 Unsigned32, 
		smscIp7SctpIpSentFailOor	 Unsigned32, 
		smscIp7SctpIpRcvd	 Unsigned32, 
		smscIp7SctpIpRcvdFailOor	 Unsigned32, 
		smscIp7SuaOverloadProtect	 Unsigned32, 
		smscIp7SsrvLocalSsCong	 Unsigned32
	}

smscIp7Name  OBJECT-TYPE
	SYNTAX  DisplayString
	MAX-ACCESS  read-only
	STATUS   current
	DESCRIPTION
		"Identifies the name of the entity."
   ::= {ip7InstanceEntry 1 }

smscIp7State  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { ip7InstanceEntry 2 }


smscIp7Lastupdate OBJECT-TYPE
		SYNTAX	TimeTicks
		MAX-ACCESS read-only
		STATUS current
		DESCRIPTION
			"Value which reflects the last time the entities fields have been updated"
	::= { ip7InstanceEntry	3 }

smscIp7Node  OBJECT-TYPE
	SYNTAX  DisplayString
	MAX-ACCESS  read-only
	STATUS   current
	DESCRIPTION
		"Identifies the node the entity is running on."
   ::= {ip7InstanceEntry 4 }

smscIp7MsgReceived OBJECT-TYPE
		SYNTAX	Unsigned32
		MAX-ACCESS read-only
		STATUS current
		DESCRIPTION
			"Received messages"
	::= { ip7InstanceEntry	5 }

smscIp7MsgRejected OBJECT-TYPE
		SYNTAX	Unsigned32
		MAX-ACCESS read-only
		STATUS current
		DESCRIPTION
			"Received messages and rejected"
	::= { ip7InstanceEntry	6 }

smscIp7MsgTransmitted OBJECT-TYPE
		SYNTAX	Unsigned32
		MAX-ACCESS read-only
		STATUS current
		DESCRIPTION
			"Transmitted messages"
	::= { ip7InstanceEntry	7 }

smscIp7MsgFailed OBJECT-TYPE
		SYNTAX	Unsigned32
		MAX-ACCESS read-only
		STATUS current
		DESCRIPTION
			"Messages that failed on sending"
	::= { ip7InstanceEntry	8 }

smscIp7QelemUsed OBJECT-TYPE
		SYNTAX	Unsigned32
		MAX-ACCESS read-only
		STATUS current
		DESCRIPTION
			"Number of elements in internal queues"
	::= { ip7InstanceEntry	9 }

smscIp7QelemInProcqueue OBJECT-TYPE
		SYNTAX	Unsigned32
		MAX-ACCESS read-only
		STATUS current
		DESCRIPTION
			"Number of elements used in process queue"
	::= { ip7InstanceEntry	10 }

smscIp7QelemInExpqueue OBJECT-TYPE
		SYNTAX	Unsigned32
		MAX-ACCESS read-only
		STATUS current
		DESCRIPTION
			"Number of elements used in expedited queue"
	::= { ip7InstanceEntry	11 }

smscIp7NrTimersRunning OBJECT-TYPE
		SYNTAX	Unsigned32
		MAX-ACCESS read-only
		STATUS current
		DESCRIPTION
			"Total number of timers running"
	::= { ip7InstanceEntry	12 }

smscIp7NrSystemTimers OBJECT-TYPE
		SYNTAX	Unsigned32
		MAX-ACCESS read-only
		STATUS current
		DESCRIPTION
			"Number of system timers running"
	::= { ip7InstanceEntry	13 }

smscIp7ImiRecallQelem OBJECT-TYPE
		SYNTAX	Unsigned32
		MAX-ACCESS read-only
		STATUS current
		DESCRIPTION
			"Number of IMI recall-queue elements used"
	::= { ip7InstanceEntry	14 }

smscIp7ImiRecallQueues OBJECT-TYPE
		SYNTAX	Unsigned32
		MAX-ACCESS read-only
		STATUS current
		DESCRIPTION
			"Number of IMI-recall-queues used"
	::= { ip7InstanceEntry	15 }

smscIp7IdiRecallQelem OBJECT-TYPE
		SYNTAX	Unsigned32
		MAX-ACCESS read-only
		STATUS current
		DESCRIPTION
			"Number of IDI recall-queue elements used"
	::= { ip7InstanceEntry	16 }

smscIp7IdiRecallQueues OBJECT-TYPE
		SYNTAX	Unsigned32
		MAX-ACCESS read-only
		STATUS current
		DESCRIPTION
			"Number of IDI recall-queues used"
	::= { ip7InstanceEntry	17 }

smscIp7IosRecallQelem OBJECT-TYPE
		SYNTAX	Unsigned32
		MAX-ACCESS read-only
		STATUS current
		DESCRIPTION
			"Number of IOS recall-queue elements used"
	::= { ip7InstanceEntry	18 }

smscIp7IosRecallQueues OBJECT-TYPE
		SYNTAX	Unsigned32
		MAX-ACCESS read-only
		STATUS current
		DESCRIPTION
			"Number of IOS recall-queues used"
	::= { ip7InstanceEntry	19 }

smscIp7LogRecallQelem OBJECT-TYPE
		SYNTAX	Unsigned32
		MAX-ACCESS read-only
		STATUS current
		DESCRIPTION
			"Number of LOG recall-queue elements used"
	::= { ip7InstanceEntry	20 }

smscIp7LogRecallQueues OBJECT-TYPE
		SYNTAX	Unsigned32
		MAX-ACCESS read-only
		STATUS current
		DESCRIPTION
			"Number of LOG recall-queues used"
	::= { ip7InstanceEntry	21 }

smscIp7TrcreqDiscarded OBJECT-TYPE
		SYNTAX	Unsigned32
		MAX-ACCESS read-only
		STATUS current
		DESCRIPTION
			"Number of trace requests discarded"
	::= { ip7InstanceEntry	22 }

smscIp7SctpCtrlChksSnt OBJECT-TYPE
		SYNTAX	Unsigned32
		MAX-ACCESS read-only
		STATUS current
		DESCRIPTION
			"Number of Control Chunks Sent"
	::= { ip7InstanceEntry	23 }

smscIp7SctpCtrlChksRcvd OBJECT-TYPE
		SYNTAX	Unsigned32
		MAX-ACCESS read-only
		STATUS current
		DESCRIPTION
			"Number of Control Chunks Received"
	::= { ip7InstanceEntry	24 }

smscIp7SctpDtChksSnt OBJECT-TYPE
		SYNTAX	Unsigned32
		MAX-ACCESS read-only
		STATUS current
		DESCRIPTION
			"Number of Data Chunks Total Sent"
	::= { ip7InstanceEntry	25 }

smscIp7SctpDtChksRetrans OBJECT-TYPE
		SYNTAX	Unsigned32
		MAX-ACCESS read-only
		STATUS current
		DESCRIPTION
			"Number of Data Chunks Retransmitted"
	::= { ip7InstanceEntry	26 }

smscIp7SctpDtChksSntOrd OBJECT-TYPE
		SYNTAX	Unsigned32
		MAX-ACCESS read-only
		STATUS current
		DESCRIPTION
			"Number of Data Chunks Sent Ordered"
	::= { ip7InstanceEntry	27 }

smscIp7SctpDtChksSntUnord OBJECT-TYPE
		SYNTAX	Unsigned32
		MAX-ACCESS read-only
		STATUS current
		DESCRIPTION
			"Number of Data Chunks Sent Unordered"
	::= { ip7InstanceEntry	28 }

smscIp7SctpDtBytesSnt OBJECT-TYPE
		SYNTAX	Unsigned32
		MAX-ACCESS read-only
		STATUS current
		DESCRIPTION
			"Number of Total Data Bytes Sent"
	::= { ip7InstanceEntry	29 }

smscIp7SctpDtChksRcvd OBJECT-TYPE
		SYNTAX	Unsigned32
		MAX-ACCESS read-only
		STATUS current
		DESCRIPTION
			"Number of Data Chunks Total Received"
	::= { ip7InstanceEntry	30 }

smscIp7SctpDtChksDiscarded OBJECT-TYPE
		SYNTAX	Unsigned32
		MAX-ACCESS read-only
		STATUS current
		DESCRIPTION
			"Number of Data Chunks Discarded"
	::= { ip7InstanceEntry	31 }

smscIp7SctpDtChksRcvdOrd OBJECT-TYPE
		SYNTAX	Unsigned32
		MAX-ACCESS read-only
		STATUS current
		DESCRIPTION
			"Number of Data Chunks Received Ordered"
	::= { ip7InstanceEntry	32 }

smscIp7SctpDtChksRcvdUnrd OBJECT-TYPE
		SYNTAX	Unsigned32
		MAX-ACCESS read-only
		STATUS current
		DESCRIPTION
			"Number of Data Chunks Received Unordered"
	::= { ip7InstanceEntry	33 }

smscIp7SctpDtBytesRcvd OBJECT-TYPE
		SYNTAX	Unsigned32
		MAX-ACCESS read-only
		STATUS current
		DESCRIPTION
			"Number of Total Data Bytes Received"
	::= { ip7InstanceEntry	34 }

smscIp7SctpDtChksRcvdOos OBJECT-TYPE
		SYNTAX	Unsigned32
		MAX-ACCESS read-only
		STATUS current
		DESCRIPTION
			"Number of Data Chunks Received Out of Seq TSN"
	::= { ip7InstanceEntry	35 }

smscIp7SctpSctpDgramsSnt OBJECT-TYPE
		SYNTAX	Unsigned32
		MAX-ACCESS read-only
		STATUS current
		DESCRIPTION
			"Number of SCTP Dgrams Sent"
	::= { ip7InstanceEntry	36 }

smscIp7SctpSctpDgramsRcvd OBJECT-TYPE
		SYNTAX	Unsigned32
		MAX-ACCESS read-only
		STATUS current
		DESCRIPTION
			"Number of SCTP Dgrams Received"
	::= { ip7InstanceEntry	37 }

smscIp7SctpUlpDgramsSnt OBJECT-TYPE
		SYNTAX	Unsigned32
		MAX-ACCESS read-only
		STATUS current
		DESCRIPTION
			"Number of ULP Dgrams Sent"
	::= { ip7InstanceEntry	38 }

smscIp7SctpUlpDgramsReady OBJECT-TYPE
		SYNTAX	Unsigned32
		MAX-ACCESS read-only
		STATUS current
		DESCRIPTION
			"Number of ULP Dgrams Ready"
	::= { ip7InstanceEntry	39 }

smscIp7SctpUlpDgramsRcvd OBJECT-TYPE
		SYNTAX	Unsigned32
		MAX-ACCESS read-only
		STATUS current
		DESCRIPTION
			"Number of ULP Dgrams Received"
	::= { ip7InstanceEntry	40 }

smscIp7SctpApplReqFree OBJECT-TYPE
		SYNTAX	Unsigned32
		MAX-ACCESS read-only
		STATUS current
		DESCRIPTION
			"Number of Free Application Requests"
	::= { ip7InstanceEntry	41 }

smscIp7SctpApplReqInUse OBJECT-TYPE
		SYNTAX	Unsigned32
		MAX-ACCESS read-only
		STATUS current
		DESCRIPTION
			"Number of Used Application Requests"
	::= { ip7InstanceEntry	42 }

smscIp7SctpApplReqMaxUsed OBJECT-TYPE
		SYNTAX	Unsigned32
		MAX-ACCESS read-only
		STATUS current
		DESCRIPTION
			"Highest peak of Application Requests used"
	::= { ip7InstanceEntry	43 }

smscIp7SctpApplReqNoMem OBJECT-TYPE
		SYNTAX	Unsigned32
		MAX-ACCESS read-only
		STATUS current
		DESCRIPTION
			"Number of times No Application Request available"
	::= { ip7InstanceEntry	44 }

smscIp7SctpChkDescFree OBJECT-TYPE
		SYNTAX	Unsigned32
		MAX-ACCESS read-only
		STATUS current
		DESCRIPTION
			"Number of Free Chunk Descriptions"
	::= { ip7InstanceEntry	45 }

smscIp7SctpChkDescInUse OBJECT-TYPE
		SYNTAX	Unsigned32
		MAX-ACCESS read-only
		STATUS current
		DESCRIPTION
			"Number of Used Chunk Descriptions"
	::= { ip7InstanceEntry	46 }

smscIp7SctpChkDescMaxUsed OBJECT-TYPE
		SYNTAX	Unsigned32
		MAX-ACCESS read-only
		STATUS current
		DESCRIPTION
			"Highest peak of Chunk Descriptions used"
	::= { ip7InstanceEntry	47 }

smscIp7SctpChkDescNoMem OBJECT-TYPE
		SYNTAX	Unsigned32
		MAX-ACCESS read-only
		STATUS current
		DESCRIPTION
			"Number of times No Chunk Descriptions available"
	::= { ip7InstanceEntry	48 }

smscIp7SctpDgrmHdrFree OBJECT-TYPE
		SYNTAX	Unsigned32
		MAX-ACCESS read-only
		STATUS current
		DESCRIPTION
			"Number of Free Datagram Headers"
	::= { ip7InstanceEntry	49 }

smscIp7SctpDgrmHdrInUse OBJECT-TYPE
		SYNTAX	Unsigned32
		MAX-ACCESS read-only
		STATUS current
		DESCRIPTION
			"Number of Used Datagram Headers"
	::= { ip7InstanceEntry	50 }

smscIp7SctpDgrmHdrMaxUsed OBJECT-TYPE
		SYNTAX	Unsigned32
		MAX-ACCESS read-only
		STATUS current
		DESCRIPTION
			"Highest peak of Datagram Headers used"
	::= { ip7InstanceEntry	51 }

smscIp7SctpDgrmHdrNoMem OBJECT-TYPE
		SYNTAX	Unsigned32
		MAX-ACCESS read-only
		STATUS current
		DESCRIPTION
			"Number of times No Datagram Headers available"
	::= { ip7InstanceEntry	52 }

smscIp7SuaSndBufFree OBJECT-TYPE
		SYNTAX	Unsigned32
		MAX-ACCESS read-only
		STATUS current
		DESCRIPTION
			"Number of Free Send Buffers"
	::= { ip7InstanceEntry	53 }

smscIp7SuaSndBufInUse OBJECT-TYPE
		SYNTAX	Unsigned32
		MAX-ACCESS read-only
		STATUS current
		DESCRIPTION
			"Number of Used Send Buffers"
	::= { ip7InstanceEntry	54 }

smscIp7SuaSndBufMaxUsed OBJECT-TYPE
		SYNTAX	Unsigned32
		MAX-ACCESS read-only
		STATUS current
		DESCRIPTION
			"Highest peak of Send Buffers used"
	::= { ip7InstanceEntry	55 }

smscIp7SuaSndBufNoMem OBJECT-TYPE
		SYNTAX	Unsigned32
		MAX-ACCESS read-only
		STATUS current
		DESCRIPTION
			"Number of times No Send Buffers available"
	::= { ip7InstanceEntry	56 }

smscIp7SuaSigNodesFree OBJECT-TYPE
		SYNTAX	Unsigned32
		MAX-ACCESS read-only
		STATUS current
		DESCRIPTION
			"Number of Free Signal Buffers"
	::= { ip7InstanceEntry	57 }

smscIp7SuaSigNodesInUse OBJECT-TYPE
		SYNTAX	Unsigned32
		MAX-ACCESS read-only
		STATUS current
		DESCRIPTION
			"Number of Used Signal Buffers"
	::= { ip7InstanceEntry	58 }

smscIp7SuaSigNodesMaxUsed OBJECT-TYPE
		SYNTAX	Unsigned32
		MAX-ACCESS read-only
		STATUS current
		DESCRIPTION
			"Highest peak of Signal Buffers used"
	::= { ip7InstanceEntry	59 }

smscIp7SuaSigNodesNoMem OBJECT-TYPE
		SYNTAX	Unsigned32
		MAX-ACCESS read-only
		STATUS current
		DESCRIPTION
			"Number of times No Signal Buffers available"
	::= { ip7InstanceEntry	60 }

smscIp7SctpAssocCurrEstab OBJECT-TYPE
		SYNTAX	Unsigned32
		MAX-ACCESS read-only
		STATUS current
		DESCRIPTION
			"Number of Associations Currently Established"
	::= { ip7InstanceEntry	61 }

smscIp7SctpAssocActvEstab OBJECT-TYPE
		SYNTAX	Unsigned32
		MAX-ACCESS read-only
		STATUS current
		DESCRIPTION
			"Number of Associations Active Established"
	::= { ip7InstanceEntry	62 }

smscIp7SctpAssocPassEstab OBJECT-TYPE
		SYNTAX	Unsigned32
		MAX-ACCESS read-only
		STATUS current
		DESCRIPTION
			"Number of Associations Passive Established"
	::= { ip7InstanceEntry	63 }

smscIp7SctpAssocAborted OBJECT-TYPE
		SYNTAX	Unsigned32
		MAX-ACCESS read-only
		STATUS current
		DESCRIPTION
			"Number of Associations Aborted"
	::= { ip7InstanceEntry	64 }

smscIp7SctpAssocShutdowns OBJECT-TYPE
		SYNTAX	Unsigned32
		MAX-ACCESS read-only
		STATUS current
		DESCRIPTION
			"Number of Associations Shutdowns"
	::= { ip7InstanceEntry	65 }

smscIp7SctpT1Expired OBJECT-TYPE
		SYNTAX	Unsigned32
		MAX-ACCESS read-only
		STATUS current
		DESCRIPTION
			"Number of Timer 1 Expired"
	::= { ip7InstanceEntry	66 }

smscIp7SctpT2Expired OBJECT-TYPE
		SYNTAX	Unsigned32
		MAX-ACCESS read-only
		STATUS current
		DESCRIPTION
			"Number of Timer 2 Expired"
	::= { ip7InstanceEntry	67 }

smscIp7TcapUnknSprimRcvd OBJECT-TYPE
		SYNTAX	Unsigned32
		MAX-ACCESS read-only
		STATUS current
		DESCRIPTION
			"Number of unknown SCCP primitives received"
	::= { ip7InstanceEntry	68 }

smscIp7SuaRasBufFree OBJECT-TYPE
		SYNTAX	Unsigned32
		MAX-ACCESS read-only
		STATUS current
		DESCRIPTION
			"Number of Free Reassembly Buffers"
	::= { ip7InstanceEntry	69 }

smscIp7SuaRasBufInUse OBJECT-TYPE
		SYNTAX	Unsigned32
		MAX-ACCESS read-only
		STATUS current
		DESCRIPTION
			"Number of Used Reassembly Buffers"
	::= { ip7InstanceEntry	70 }

smscIp7SuaRasBufMaxUsed OBJECT-TYPE
		SYNTAX	Unsigned32
		MAX-ACCESS read-only
		STATUS current
		DESCRIPTION
			"Highest peak of Reassembly Buffers used"
	::= { ip7InstanceEntry	71 }

smscIp7SuaRasBufNoMem OBJECT-TYPE
		SYNTAX	Unsigned32
		MAX-ACCESS read-only
		STATUS current
		DESCRIPTION
			"Number of times No Reassembly Buffers available"
	::= { ip7InstanceEntry	72 }

smscIp7SuaInvalidMsg OBJECT-TYPE
		SYNTAX	Unsigned32
		MAX-ACCESS read-only
		STATUS current
		DESCRIPTION
			"Number of dropped msgs due to invalid content"
	::= { ip7InstanceEntry	73 }

smscIp7SuaNoUsers OBJECT-TYPE
		SYNTAX	Unsigned32
		MAX-ACCESS read-only
		STATUS current
		DESCRIPTION
			"Number of dropped msgs due to unavailable users"
	::= { ip7InstanceEntry	74 }

smscIp7SuaNoSpecUser OBJECT-TYPE
		SYNTAX	Unsigned32
		MAX-ACCESS read-only
		STATUS current
		DESCRIPTION
			"Number of dropped msgs due to absent user"
	::= { ip7InstanceEntry	75 }

smscIp7SuaTransFailure OBJECT-TYPE
		SYNTAX	Unsigned32
		MAX-ACCESS read-only
		STATUS current
		DESCRIPTION
			"Number of dropped msgs due to user transport error"
	::= { ip7InstanceEntry	76 }

smscIp7SuaNoReassembly OBJECT-TYPE
		SYNTAX	Unsigned32
		MAX-ACCESS read-only
		STATUS current
		DESCRIPTION
			"Nr. of dropped SUA msgs due to disabled reassembly"
	::= { ip7InstanceEntry	77 }

smscIp7SuaFailedReassembly OBJECT-TYPE
		SYNTAX	Unsigned32
		MAX-ACCESS read-only
		STATUS current
		DESCRIPTION
			"Number of dropped msgs due to failed reassembly"
	::= { ip7InstanceEntry	78 }

smscIp7SuaNoticeFailure OBJECT-TYPE
		SYNTAX	Unsigned32
		MAX-ACCESS read-only
		STATUS current
		DESCRIPTION
			"Number of dropped notices due to send error"
	::= { ip7InstanceEntry	79 }

smscIp7SccpSstSent OBJECT-TYPE
		SYNTAX	Unsigned32
		MAX-ACCESS read-only
		STATUS current
		DESCRIPTION
			"Number of transmitted SCCP SST messages"
	::= { ip7InstanceEntry	80 }

smscIp7SccpSstRcvd OBJECT-TYPE
		SYNTAX	Unsigned32
		MAX-ACCESS read-only
		STATUS current
		DESCRIPTION
			"Number of received SCCP SST messages"
	::= { ip7InstanceEntry	81 }

smscIp7SccpSspSent OBJECT-TYPE
		SYNTAX	Unsigned32
		MAX-ACCESS read-only
		STATUS current
		DESCRIPTION
			"Number of transmitted SCCP SSP messages"
	::= { ip7InstanceEntry	82 }

smscIp7SccpSspRcvd OBJECT-TYPE
		SYNTAX	Unsigned32
		MAX-ACCESS read-only
		STATUS current
		DESCRIPTION
			"Number of received SCCP SSP messages"
	::= { ip7InstanceEntry	83 }

smscIp7SccpSsaSent OBJECT-TYPE
		SYNTAX	Unsigned32
		MAX-ACCESS read-only
		STATUS current
		DESCRIPTION
			"Number of transmitted SCCP SSA messages"
	::= { ip7InstanceEntry	84 }

smscIp7SccpSsaRcvd OBJECT-TYPE
		SYNTAX	Unsigned32
		MAX-ACCESS read-only
		STATUS current
		DESCRIPTION
			"Number of received SCCP SSA messages"
	::= { ip7InstanceEntry	85 }

smscIp7SccpSscRcvd OBJECT-TYPE
		SYNTAX	Unsigned32
		MAX-ACCESS read-only
		STATUS current
		DESCRIPTION
			"Number of received SCCP SSC messages"
	::= { ip7InstanceEntry	86 }

smscIp7SccpUdtsSent OBJECT-TYPE
		SYNTAX	Unsigned32
		MAX-ACCESS read-only
		STATUS current
		DESCRIPTION
			"Number of transmitted SCCP UDTS messages"
	::= { ip7InstanceEntry	87 }

smscIp7SccpUdtsRcvd OBJECT-TYPE
		SYNTAX	Unsigned32
		MAX-ACCESS read-only
		STATUS current
		DESCRIPTION
			"Number of received SCCP UDTS messages"
	::= { ip7InstanceEntry	88 }

smscIp7SccpXudtsSent OBJECT-TYPE
		SYNTAX	Unsigned32
		MAX-ACCESS read-only
		STATUS current
		DESCRIPTION
			"Number of transmitted SCCP XUDTS messages"
	::= { ip7InstanceEntry	89 }

smscIp7SccpXudtsRcvd OBJECT-TYPE
		SYNTAX	Unsigned32
		MAX-ACCESS read-only
		STATUS current
		DESCRIPTION
			"Number of received SCCP XUDTS messages"
	::= { ip7InstanceEntry	90 }

smscIp7SccpLudtsSent OBJECT-TYPE
		SYNTAX	Unsigned32
		MAX-ACCESS read-only
		STATUS current
		DESCRIPTION
			"Number of transmitted SCCP LUDTS messages"
	::= { ip7InstanceEntry	91 }

smscIp7SccpLudtsRcvd OBJECT-TYPE
		SYNTAX	Unsigned32
		MAX-ACCESS read-only
		STATUS current
		DESCRIPTION
			"Number of received SCCP LUDTS messages"
	::= { ip7InstanceEntry	92 }

smscIp7SccpUdtSent OBJECT-TYPE
		SYNTAX	Unsigned32
		MAX-ACCESS read-only
		STATUS current
		DESCRIPTION
			"Number of transmitted SCCP UDT messages"
	::= { ip7InstanceEntry	93 }

smscIp7SccpUdtRcvd OBJECT-TYPE
		SYNTAX	Unsigned32
		MAX-ACCESS read-only
		STATUS current
		DESCRIPTION
			"Number of received SCCP UDT messages"
	::= { ip7InstanceEntry	94 }

smscIp7SccpXudtSent OBJECT-TYPE
		SYNTAX	Unsigned32
		MAX-ACCESS read-only
		STATUS current
		DESCRIPTION
			"Number of transmitted SCCP XUDT messages"
	::= { ip7InstanceEntry	95 }

smscIp7SccpXudtRcvd OBJECT-TYPE
		SYNTAX	Unsigned32
		MAX-ACCESS read-only
		STATUS current
		DESCRIPTION
			"Number of received SCCP XUDT messages"
	::= { ip7InstanceEntry	96 }

smscIp7SccpLudtSent OBJECT-TYPE
		SYNTAX	Unsigned32
		MAX-ACCESS read-only
		STATUS current
		DESCRIPTION
			"Number of transmitted SCCP LUDT messages"
	::= { ip7InstanceEntry	97 }

smscIp7SccpLudtRcvd OBJECT-TYPE
		SYNTAX	Unsigned32
		MAX-ACCESS read-only
		STATUS current
		DESCRIPTION
			"Number of received SCCP LUDT messages"
	::= { ip7InstanceEntry	98 }

smscIp7SccpNoReassembly OBJECT-TYPE
		SYNTAX	Unsigned32
		MAX-ACCESS read-only
		STATUS current
		DESCRIPTION
			"Number of ignored received SCCP segments"
	::= { ip7InstanceEntry	99 }

smscIp7SsnmDpcEntFree OBJECT-TYPE
		SYNTAX	Unsigned32
		MAX-ACCESS read-only
		STATUS current
		DESCRIPTION
			"Number of free SSNM table DPC dynamic entries"
	::= { ip7InstanceEntry	100 }

smscIp7SsnmDpcEntInUse OBJECT-TYPE
		SYNTAX	Unsigned32
		MAX-ACCESS read-only
		STATUS current
		DESCRIPTION
			"Number of SSNM table DPC dynamic entries in use"
	::= { ip7InstanceEntry	101 }

smscIp7SsnmDpcEntMaxUsed OBJECT-TYPE
		SYNTAX	Unsigned32
		MAX-ACCESS read-only
		STATUS current
		DESCRIPTION
			"Highest peak of SSNM table DPC dyn. entries used"
	::= { ip7InstanceEntry	102 }

smscIp7SsnmDpcEntNoMem OBJECT-TYPE
		SYNTAX	Unsigned32
		MAX-ACCESS read-only
		STATUS current
		DESCRIPTION
			"Nr. of times no SSNM table DPC dyn. entries avail."
	::= { ip7InstanceEntry	103 }

smscIp7SsnmStatEntFree OBJECT-TYPE
		SYNTAX	Unsigned32
		MAX-ACCESS read-only
		STATUS current
		DESCRIPTION
			"Number of free SSNM table DPC state entries"
	::= { ip7InstanceEntry	104 }

smscIp7SsnmStatEntInUse OBJECT-TYPE
		SYNTAX	Unsigned32
		MAX-ACCESS read-only
		STATUS current
		DESCRIPTION
			"Number of SSNM table DPC state entries in use"
	::= { ip7InstanceEntry	105 }

smscIp7SsnmStatEntMxUsd OBJECT-TYPE
		SYNTAX	Unsigned32
		MAX-ACCESS read-only
		STATUS current
		DESCRIPTION
			"Highest peak of SSNM table DPC state entries used"
	::= { ip7InstanceEntry	106 }

smscIp7SsnmStatEntNoMem OBJECT-TYPE
		SYNTAX	Unsigned32
		MAX-ACCESS read-only
		STATUS current
		DESCRIPTION
			"Nr. of times no SSNM table state entries available"
	::= { ip7InstanceEntry	107 }

smscIp7SsnmSsnEntFree OBJECT-TYPE
		SYNTAX	Unsigned32
		MAX-ACCESS read-only
		STATUS current
		DESCRIPTION
			"Number of free SSNM table SSN entries"
	::= { ip7InstanceEntry	108 }

smscIp7SsnmSsnEntInUse OBJECT-TYPE
		SYNTAX	Unsigned32
		MAX-ACCESS read-only
		STATUS current
		DESCRIPTION
			"Number of SSNM table SSN entries in use"
	::= { ip7InstanceEntry	109 }

smscIp7SsnmSsnEntMaxUsed OBJECT-TYPE
		SYNTAX	Unsigned32
		MAX-ACCESS read-only
		STATUS current
		DESCRIPTION
			"Highest peak of SSNM table SSN entries used"
	::= { ip7InstanceEntry	110 }

smscIp7SsnmSsnEntNoMem OBJECT-TYPE
		SYNTAX	Unsigned32
		MAX-ACCESS read-only
		STATUS current
		DESCRIPTION
			"Nr. of times no SSNM table SSN entries available"
	::= { ip7InstanceEntry	111 }

smscIp7SsrvLocalSsFail OBJECT-TYPE
		SYNTAX	Unsigned32
		MAX-ACCESS read-only
		STATUS current
		DESCRIPTION
			"Nr. of dropped outbound msgs - subsystem failure"
	::= { ip7InstanceEntry	112 }

smscIp7SsrvLocalMtpFail OBJECT-TYPE
		SYNTAX	Unsigned32
		MAX-ACCESS read-only
		STATUS current
		DESCRIPTION
			"Nr. of dropped outbound msgs - MTP failure"
	::= { ip7InstanceEntry	113 }

smscIp7SsrvLocalNtwkCong OBJECT-TYPE
		SYNTAX	Unsigned32
		MAX-ACCESS read-only
		STATUS current
		DESCRIPTION
			"Nr. of dropped outbound msgs - network congestion"
	::= { ip7InstanceEntry	114 }

smscIp7SsrvLocalSccpFail OBJECT-TYPE
		SYNTAX	Unsigned32
		MAX-ACCESS read-only
		STATUS current
		DESCRIPTION
			"Nr. of dropped outbound msgs - SCCP failure"
	::= { ip7InstanceEntry	115 }

smscIp7SsrvLocalSegmUnsup OBJECT-TYPE
		SYNTAX	Unsigned32
		MAX-ACCESS read-only
		STATUS current
		DESCRIPTION
			"Nr. of dropped outbound msgs - unsup. segmentation"
	::= { ip7InstanceEntry	116 }

smscIp7SsrvLocalSegmFail OBJECT-TYPE
		SYNTAX	Unsigned32
		MAX-ACCESS read-only
		STATUS current
		DESCRIPTION
			"Nr. of dropped outbound msgs - failed segmentation"
	::= { ip7InstanceEntry	117 }

smscIp7SsrvNwRcvNtranNoa OBJECT-TYPE
		SYNTAX	Unsigned32
		MAX-ACCESS read-only
		STATUS current
		DESCRIPTION
			"Number of received SUA/SCCP return msgs NTRAN_NOA"
	::= { ip7InstanceEntry	118 }

smscIp7SsrvNwRcvNtranAddr OBJECT-TYPE
		SYNTAX	Unsigned32
		MAX-ACCESS read-only
		STATUS current
		DESCRIPTION
			"Number of received SUA/SCCP return msgs NTRAN_ADDR"
	::= { ip7InstanceEntry	119 }

smscIp7SsrvNwRcvSsCong OBJECT-TYPE
		SYNTAX	Unsigned32
		MAX-ACCESS read-only
		STATUS current
		DESCRIPTION
			"Number of received SUA/SCCP return msgs SS_CONG"
	::= { ip7InstanceEntry	120 }

smscIp7SsrvNwRcvSsFail OBJECT-TYPE
		SYNTAX	Unsigned32
		MAX-ACCESS read-only
		STATUS current
		DESCRIPTION
			"Number of received SUA/SCCP return msgs SS_FAIL"
	::= { ip7InstanceEntry	121 }

smscIp7SsrvNwRcvUnequipped OBJECT-TYPE
		SYNTAX	Unsigned32
		MAX-ACCESS read-only
		STATUS current
		DESCRIPTION
			"Number of received SUA/SCCP return msgs UNEQUIPPED"
	::= { ip7InstanceEntry	122 }

smscIp7SsrvNwRcvMtpFail OBJECT-TYPE
		SYNTAX	Unsigned32
		MAX-ACCESS read-only
		STATUS current
		DESCRIPTION
			"Number of received SUA/SCCP return msgs MTP_FAIL"
	::= { ip7InstanceEntry	123 }

smscIp7SsrvNwRcvNtwkCong OBJECT-TYPE
		SYNTAX	Unsigned32
		MAX-ACCESS read-only
		STATUS current
		DESCRIPTION
			"Number of received SUA/SCCP return msgs NTWK_CONG"
	::= { ip7InstanceEntry	124 }

smscIp7SsrvNwRcvUnqual OBJECT-TYPE
		SYNTAX	Unsigned32
		MAX-ACCESS read-only
		STATUS current
		DESCRIPTION
			"Number of received SUA/SCCP return msgs UNQUAL"
	::= { ip7InstanceEntry	125 }

smscIp7SsrvNwRcvMsgTrans OBJECT-TYPE
		SYNTAX	Unsigned32
		MAX-ACCESS read-only
		STATUS current
		DESCRIPTION
			"Number of received SUA/SCCP return msgs MSG_TRANS"
	::= { ip7InstanceEntry	126 }

smscIp7SsrvNwRcvLocalProc OBJECT-TYPE
		SYNTAX	Unsigned32
		MAX-ACCESS read-only
		STATUS current
		DESCRIPTION
			"Number of received SUA/SCCP return msgs LOCAL_PROC"
	::= { ip7InstanceEntry	127 }

smscIp7SsrvNwRcvReasUnsup OBJECT-TYPE
		SYNTAX	Unsigned32
		MAX-ACCESS read-only
		STATUS current
		DESCRIPTION
			"Number of received SUA/SCCP return msgs REAS_UNSUP"
	::= { ip7InstanceEntry	128 }

smscIp7SsrvNwRcvSccpFail OBJECT-TYPE
		SYNTAX	Unsigned32
		MAX-ACCESS read-only
		STATUS current
		DESCRIPTION
			"Number of received SUA/SCCP return msgs SCCP_FAIL"
	::= { ip7InstanceEntry	129 }

smscIp7SsrvNwRcvHopcViol OBJECT-TYPE
		SYNTAX	Unsigned32
		MAX-ACCESS read-only
		STATUS current
		DESCRIPTION
			"Number of received SUA/SCCP return msgs HOPC_VIOL"
	::= { ip7InstanceEntry	130 }

smscIp7SsrvNwRcvSegmUnsup OBJECT-TYPE
		SYNTAX	Unsigned32
		MAX-ACCESS read-only
		STATUS current
		DESCRIPTION
			"Number of received SUA/SCCP return msgs SEGM_UNSUP"
	::= { ip7InstanceEntry	131 }

smscIp7SsrvNwRcvSegmFail OBJECT-TYPE
		SYNTAX	Unsigned32
		MAX-ACCESS read-only
		STATUS current
		DESCRIPTION
			"Number of received SUA/SCCP return msgs SEGM_FAIL"
	::= { ip7InstanceEntry	132 }

smscIp7SctpIpSent OBJECT-TYPE
		SYNTAX	Unsigned32
		MAX-ACCESS read-only
		STATUS current
		DESCRIPTION
			"Number of IP Pckts Sent"
	::= { ip7InstanceEntry	133 }

smscIp7SctpIpSentFailIof OBJECT-TYPE
		SYNTAX	Unsigned32
		MAX-ACCESS read-only
		STATUS current
		DESCRIPTION
			"Number of failed IP Pckts Sent (I/O Failure)"
	::= { ip7InstanceEntry	134 }

smscIp7SctpIpSentFailOor OBJECT-TYPE
		SYNTAX	Unsigned32
		MAX-ACCESS read-only
		STATUS current
		DESCRIPTION
			"Number of failed IP Pckts Sent (Out Of Resources)"
	::= { ip7InstanceEntry	135 }

smscIp7SctpIpRcvd OBJECT-TYPE
		SYNTAX	Unsigned32
		MAX-ACCESS read-only
		STATUS current
		DESCRIPTION
			"Number of IP Pckts Rcvd"
	::= { ip7InstanceEntry	136 }

smscIp7SctpIpRcvdFailOor OBJECT-TYPE
		SYNTAX	Unsigned32
		MAX-ACCESS read-only
		STATUS current
		DESCRIPTION
			"Number of failed IP Pckts Rcvd (Out Of Resources)"
	::= { ip7InstanceEntry	137 }

smscIp7SuaOverloadProtect OBJECT-TYPE
		SYNTAX	Unsigned32
		MAX-ACCESS read-only
		STATUS current
		DESCRIPTION
			"Number of dropped msgs due to overload protection"
	::= { ip7InstanceEntry	138 }

smscIp7SsrvLocalSsCong OBJECT-TYPE
		SYNTAX	Unsigned32
		MAX-ACCESS read-only
		STATUS current
		DESCRIPTION
			"Nr. of dropped outbound msgs -subsystem congestion"
	::= { ip7InstanceEntry	139 }



-- end of IP7 description.
-- --------------------------------------


-- --------------------------------------
-- Class LIW
-- 
smscLiw OBJECT-TYPE
	SYNTAX  SEQUENCE OF LiwInstanceEntry
	MAX-ACCESS  not-accessible
	STATUS  current
	DESCRIPTION
		"Mapping table for SMSC LIW entities."
   ::= { smscClassOther   12  }

liwInstanceEntry  OBJECT-TYPE
	SYNTAX LiwInstanceEntry
	MAX-ACCESS  not-accessible
	STATUS  current
	DESCRIPTION
		"An entry (row) in the entityInstanceTable."
	INDEX { IMPLIED smscLiwName }
   ::= { smscLiw 1 }

LiwInstanceEntry ::= SEQUENCE {
		smscLiwName     DisplayString,
		smscLiwState   INTEGER,
		smscLiwLastupdate   TimeTicks,
		smscLiwNode	   DisplayString, 
		smscLiwMsgReceived	 Unsigned32, 
		smscLiwMsgRejected	 Unsigned32, 
		smscLiwMsgTransmitted	 Unsigned32, 
		smscLiwMsgFailed	 Unsigned32, 
		smscLiwQelemUsed	 Unsigned32, 
		smscLiwQelemInProcqueue	 Unsigned32, 
		smscLiwQelemInExpqueue	 Unsigned32, 
		smscLiwNrTimersRunning	 Unsigned32, 
		smscLiwNrSystemTimers	 Unsigned32, 
		smscLiwImiRecallQelem	 Unsigned32, 
		smscLiwImiRecallQueues	 Unsigned32, 
		smscLiwIdiRecallQelem	 Unsigned32, 
		smscLiwIdiRecallQueues	 Unsigned32, 
		smscLiwIosRecallQelem	 Unsigned32, 
		smscLiwIosRecallQueues	 Unsigned32, 
		smscLiwLogRecallQelem	 Unsigned32, 
		smscLiwLogRecallQueues	 Unsigned32, 
		smscLiwTrcreqDiscarded	 Unsigned32, 
		smscLiwTransactionRate	 Unsigned32, 
		smscLiwRemoveNok	 Unsigned32, 
		smscLiwUpdateNok	 Unsigned32, 
		smscLiwAddNok	 Unsigned32, 
		smscLiwUpdateOk	 Unsigned32, 
		smscLiwRemoveOk	 Unsigned32, 
		smscLiwAddOk	 Unsigned32, 
		smscLiwInvalidMessage	 Unsigned32, 
		smscLiwAddIgnored	 Unsigned32, 
		smscLiwUpdateIgnored	 Unsigned32, 
		smscLiwRemoveIgnored	 Unsigned32
	}

smscLiwName  OBJECT-TYPE
	SYNTAX  DisplayString
	MAX-ACCESS  read-only
	STATUS   current
	DESCRIPTION
		"Identifies the name of the entity."
   ::= {liwInstanceEntry 1 }

smscLiwState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { liwInstanceEntry 2 }


smscLiwLastupdate OBJECT-TYPE
		SYNTAX	TimeTicks
		MAX-ACCESS read-only
		STATUS current
		DESCRIPTION
			"Value which reflects the last time the entities fields have been updated"
	::= { liwInstanceEntry	3 }

smscLiwNode  OBJECT-TYPE
	SYNTAX  DisplayString
	MAX-ACCESS  read-only
	STATUS   current
	DESCRIPTION
		"Identifies the node the entity is running on."
   ::= {liwInstanceEntry 4 }

smscLiwMsgReceived OBJECT-TYPE
		SYNTAX	Unsigned32
		MAX-ACCESS read-only
		STATUS current
		DESCRIPTION
			"Received messages"
	::= { liwInstanceEntry	5 }

smscLiwMsgRejected OBJECT-TYPE
		SYNTAX	Unsigned32
		MAX-ACCESS read-only
		STATUS current
		DESCRIPTION
			"Received messages and rejected"
	::= { liwInstanceEntry	6 }

smscLiwMsgTransmitted OBJECT-TYPE
		SYNTAX	Unsigned32
		MAX-ACCESS read-only
		STATUS current
		DESCRIPTION
			"Transmitted messages"
	::= { liwInstanceEntry	7 }

smscLiwMsgFailed OBJECT-TYPE
		SYNTAX	Unsigned32
		MAX-ACCESS read-only
		STATUS current
		DESCRIPTION
			"Messages that failed on sending"
	::= { liwInstanceEntry	8 }

smscLiwQelemUsed OBJECT-TYPE
		SYNTAX	Unsigned32
		MAX-ACCESS read-only
		STATUS current
		DESCRIPTION
			"Number of elements in internal queues"
	::= { liwInstanceEntry	9 }

smscLiwQelemInProcqueue OBJECT-TYPE
		SYNTAX	Unsigned32
		MAX-ACCESS read-only
		STATUS current
		DESCRIPTION
			"Number of elements used in process queue"
	::= { liwInstanceEntry	10 }

smscLiwQelemInExpqueue OBJECT-TYPE
		SYNTAX	Unsigned32
		MAX-ACCESS read-only
		STATUS current
		DESCRIPTION
			"Number of elements used in expedited queue"
	::= { liwInstanceEntry	11 }

smscLiwNrTimersRunning OBJECT-TYPE
		SYNTAX	Unsigned32
		MAX-ACCESS read-only
		STATUS current
		DESCRIPTION
			"Total number of timers running"
	::= { liwInstanceEntry	12 }

smscLiwNrSystemTimers OBJECT-TYPE
		SYNTAX	Unsigned32
		MAX-ACCESS read-only
		STATUS current
		DESCRIPTION
			"Number of system timers running"
	::= { liwInstanceEntry	13 }

smscLiwImiRecallQelem OBJECT-TYPE
		SYNTAX	Unsigned32
		MAX-ACCESS read-only
		STATUS current
		DESCRIPTION
			"Number of IMI recall-queue elements used"
	::= { liwInstanceEntry	14 }

smscLiwImiRecallQueues OBJECT-TYPE
		SYNTAX	Unsigned32
		MAX-ACCESS read-only
		STATUS current
		DESCRIPTION
			"Number of IMI-recall-queues used"
	::= { liwInstanceEntry	15 }

smscLiwIdiRecallQelem OBJECT-TYPE
		SYNTAX	Unsigned32
		MAX-ACCESS read-only
		STATUS current
		DESCRIPTION
			"Number of IDI recall-queue elements used"
	::= { liwInstanceEntry	16 }

smscLiwIdiRecallQueues OBJECT-TYPE
		SYNTAX	Unsigned32
		MAX-ACCESS read-only
		STATUS current
		DESCRIPTION
			"Number of IDI recall-queues used"
	::= { liwInstanceEntry	17 }

smscLiwIosRecallQelem OBJECT-TYPE
		SYNTAX	Unsigned32
		MAX-ACCESS read-only
		STATUS current
		DESCRIPTION
			"Number of IOS recall-queue elements used"
	::= { liwInstanceEntry	18 }

smscLiwIosRecallQueues OBJECT-TYPE
		SYNTAX	Unsigned32
		MAX-ACCESS read-only
		STATUS current
		DESCRIPTION
			"Number of IOS recall-queues used"
	::= { liwInstanceEntry	19 }

smscLiwLogRecallQelem OBJECT-TYPE
		SYNTAX	Unsigned32
		MAX-ACCESS read-only
		STATUS current
		DESCRIPTION
			"Number of LOG recall-queue elements used"
	::= { liwInstanceEntry	20 }

smscLiwLogRecallQueues OBJECT-TYPE
		SYNTAX	Unsigned32
		MAX-ACCESS read-only
		STATUS current
		DESCRIPTION
			"Number of LOG recall-queues used"
	::= { liwInstanceEntry	21 }

smscLiwTrcreqDiscarded OBJECT-TYPE
		SYNTAX	Unsigned32
		MAX-ACCESS read-only
		STATUS current
		DESCRIPTION
			"Number of trace requests discarded"
	::= { liwInstanceEntry	22 }

smscLiwTransactionRate OBJECT-TYPE
		SYNTAX	Unsigned32
		MAX-ACCESS read-only
		STATUS current
		DESCRIPTION
			"Rate of incoming transactions  (trans/sec)"
	::= { liwInstanceEntry	23 }

smscLiwRemoveNok OBJECT-TYPE
		SYNTAX	Unsigned32
		MAX-ACCESS read-only
		STATUS current
		DESCRIPTION
			"Number of unsuccessful Removes"
	::= { liwInstanceEntry	24 }

smscLiwUpdateNok OBJECT-TYPE
		SYNTAX	Unsigned32
		MAX-ACCESS read-only
		STATUS current
		DESCRIPTION
			"Number of unsuccessful Updates"
	::= { liwInstanceEntry	25 }

smscLiwAddNok OBJECT-TYPE
		SYNTAX	Unsigned32
		MAX-ACCESS read-only
		STATUS current
		DESCRIPTION
			"Number of unsuccessful Adds"
	::= { liwInstanceEntry	26 }

smscLiwUpdateOk OBJECT-TYPE
		SYNTAX	Unsigned32
		MAX-ACCESS read-only
		STATUS current
		DESCRIPTION
			"Number of successful Updates"
	::= { liwInstanceEntry	27 }

smscLiwRemoveOk OBJECT-TYPE
		SYNTAX	Unsigned32
		MAX-ACCESS read-only
		STATUS current
		DESCRIPTION
			"Number of successful Removes"
	::= { liwInstanceEntry	28 }

smscLiwAddOk OBJECT-TYPE
		SYNTAX	Unsigned32
		MAX-ACCESS read-only
		STATUS current
		DESCRIPTION
			"Number of successful Adds"
	::= { liwInstanceEntry	29 }

smscLiwInvalidMessage OBJECT-TYPE
		SYNTAX	Unsigned32
		MAX-ACCESS read-only
		STATUS current
		DESCRIPTION
			"Number of invalid messages from CDS"
	::= { liwInstanceEntry	30 }

smscLiwAddIgnored OBJECT-TYPE
		SYNTAX	Unsigned32
		MAX-ACCESS read-only
		STATUS current
		DESCRIPTION
			"Number of ignored Adds"
	::= { liwInstanceEntry	31 }

smscLiwUpdateIgnored OBJECT-TYPE
		SYNTAX	Unsigned32
		MAX-ACCESS read-only
		STATUS current
		DESCRIPTION
			"Number of ignored Updates"
	::= { liwInstanceEntry	32 }

smscLiwRemoveIgnored OBJECT-TYPE
		SYNTAX	Unsigned32
		MAX-ACCESS read-only
		STATUS current
		DESCRIPTION
			"Number of ignored Removes"
	::= { liwInstanceEntry	33 }



-- end of LIW description.
-- --------------------------------------


-- --------------------------------------
-- Class STORE
-- 
smscStore OBJECT-TYPE
	SYNTAX  SEQUENCE OF StoreInstanceEntry
	MAX-ACCESS  not-accessible
	STATUS  current
	DESCRIPTION
		"Mapping table for SMSC STORE entities."
   ::= { smscClassOther   13  }

storeInstanceEntry  OBJECT-TYPE
	SYNTAX StoreInstanceEntry
	MAX-ACCESS  not-accessible
	STATUS  current
	DESCRIPTION
		"An entry (row) in the entityInstanceTable."
	INDEX { IMPLIED smscStoreName }
   ::= { smscStore 1 }

StoreInstanceEntry ::= SEQUENCE {
		smscStoreName     DisplayString,
		smscStoreState   INTEGER,
		smscStoreLastupdate   TimeTicks,
		smscStoreNode	   DisplayString, 
		smscStoreMsgReceived	 Unsigned32, 
		smscStoreMsgRejected	 Unsigned32, 
		smscStoreMsgTransmitted	 Unsigned32, 
		smscStoreMsgFailed	 Unsigned32, 
		smscStoreQelemUsed	 Unsigned32, 
		smscStoreQelemInProcqueue	 Unsigned32, 
		smscStoreQelemInExpqueue	 Unsigned32, 
		smscStoreNrTimersRunning	 Unsigned32, 
		smscStoreNrSystemTimers	 Unsigned32, 
		smscStoreImiRecallQelem	 Unsigned32, 
		smscStoreImiRecallQueues	 Unsigned32, 
		smscStoreIdiRecallQelem	 Unsigned32, 
		smscStoreIdiRecallQueues	 Unsigned32, 
		smscStoreIosRecallQelem	 Unsigned32, 
		smscStoreIosRecallQueues	 Unsigned32, 
		smscStoreLogRecallQelem	 Unsigned32, 
		smscStoreLogRecallQueues	 Unsigned32, 
		smscStoreTrcreqDiscarded	 Unsigned32, 
		smscStoreDummyStatistic	 Unsigned32
	}

smscStoreName  OBJECT-TYPE
	SYNTAX  DisplayString
	MAX-ACCESS  read-only
	STATUS   current
	DESCRIPTION
		"Identifies the name of the entity."
   ::= {storeInstanceEntry 1 }

smscStoreState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { storeInstanceEntry 2 }


smscStoreLastupdate OBJECT-TYPE
		SYNTAX	TimeTicks
		MAX-ACCESS read-only
		STATUS current
		DESCRIPTION
			"Value which reflects the last time the entities fields have been updated"
	::= { storeInstanceEntry	3 }

smscStoreNode  OBJECT-TYPE
	SYNTAX  DisplayString
	MAX-ACCESS  read-only
	STATUS   current
	DESCRIPTION
		"Identifies the node the entity is running on."
   ::= {storeInstanceEntry 4 }

smscStoreMsgReceived OBJECT-TYPE
		SYNTAX	Unsigned32
		MAX-ACCESS read-only
		STATUS current
		DESCRIPTION
			"Received messages"
	::= { storeInstanceEntry	5 }

smscStoreMsgRejected OBJECT-TYPE
		SYNTAX	Unsigned32
		MAX-ACCESS read-only
		STATUS current
		DESCRIPTION
			"Received messages and rejected"
	::= { storeInstanceEntry	6 }

smscStoreMsgTransmitted OBJECT-TYPE
		SYNTAX	Unsigned32
		MAX-ACCESS read-only
		STATUS current
		DESCRIPTION
			"Transmitted messages"
	::= { storeInstanceEntry	7 }

smscStoreMsgFailed OBJECT-TYPE
		SYNTAX	Unsigned32
		MAX-ACCESS read-only
		STATUS current
		DESCRIPTION
			"Messages that failed on sending"
	::= { storeInstanceEntry	8 }

smscStoreQelemUsed OBJECT-TYPE
		SYNTAX	Unsigned32
		MAX-ACCESS read-only
		STATUS current
		DESCRIPTION
			"Number of elements in internal queues"
	::= { storeInstanceEntry	9 }

smscStoreQelemInProcqueue OBJECT-TYPE
		SYNTAX	Unsigned32
		MAX-ACCESS read-only
		STATUS current
		DESCRIPTION
			"Number of elements used in process queue"
	::= { storeInstanceEntry	10 }

smscStoreQelemInExpqueue OBJECT-TYPE
		SYNTAX	Unsigned32
		MAX-ACCESS read-only
		STATUS current
		DESCRIPTION
			"Number of elements used in expedited queue"
	::= { storeInstanceEntry	11 }

smscStoreNrTimersRunning OBJECT-TYPE
		SYNTAX	Unsigned32
		MAX-ACCESS read-only
		STATUS current
		DESCRIPTION
			"Total number of timers running"
	::= { storeInstanceEntry	12 }

smscStoreNrSystemTimers OBJECT-TYPE
		SYNTAX	Unsigned32
		MAX-ACCESS read-only
		STATUS current
		DESCRIPTION
			"Number of system timers running"
	::= { storeInstanceEntry	13 }

smscStoreImiRecallQelem OBJECT-TYPE
		SYNTAX	Unsigned32
		MAX-ACCESS read-only
		STATUS current
		DESCRIPTION
			"Number of IMI recall-queue elements used"
	::= { storeInstanceEntry	14 }

smscStoreImiRecallQueues OBJECT-TYPE
		SYNTAX	Unsigned32
		MAX-ACCESS read-only
		STATUS current
		DESCRIPTION
			"Number of IMI-recall-queues used"
	::= { storeInstanceEntry	15 }

smscStoreIdiRecallQelem OBJECT-TYPE
		SYNTAX	Unsigned32
		MAX-ACCESS read-only
		STATUS current
		DESCRIPTION
			"Number of IDI recall-queue elements used"
	::= { storeInstanceEntry	16 }

smscStoreIdiRecallQueues OBJECT-TYPE
		SYNTAX	Unsigned32
		MAX-ACCESS read-only
		STATUS current
		DESCRIPTION
			"Number of IDI recall-queues used"
	::= { storeInstanceEntry	17 }

smscStoreIosRecallQelem OBJECT-TYPE
		SYNTAX	Unsigned32
		MAX-ACCESS read-only
		STATUS current
		DESCRIPTION
			"Number of IOS recall-queue elements used"
	::= { storeInstanceEntry	18 }

smscStoreIosRecallQueues OBJECT-TYPE
		SYNTAX	Unsigned32
		MAX-ACCESS read-only
		STATUS current
		DESCRIPTION
			"Number of IOS recall-queues used"
	::= { storeInstanceEntry	19 }

smscStoreLogRecallQelem OBJECT-TYPE
		SYNTAX	Unsigned32
		MAX-ACCESS read-only
		STATUS current
		DESCRIPTION
			"Number of LOG recall-queue elements used"
	::= { storeInstanceEntry	20 }

smscStoreLogRecallQueues OBJECT-TYPE
		SYNTAX	Unsigned32
		MAX-ACCESS read-only
		STATUS current
		DESCRIPTION
			"Number of LOG recall-queues used"
	::= { storeInstanceEntry	21 }

smscStoreTrcreqDiscarded OBJECT-TYPE
		SYNTAX	Unsigned32
		MAX-ACCESS read-only
		STATUS current
		DESCRIPTION
			"Number of trace requests discarded"
	::= { storeInstanceEntry	22 }

smscStoreDummyStatistic OBJECT-TYPE
		SYNTAX	Unsigned32
		MAX-ACCESS read-only
		STATUS current
		DESCRIPTION
			"No statistical counters"
	::= { storeInstanceEntry	23 }



-- end of STORE description.
-- --------------------------------------


-- --------------------------------------
-- Class LA_UCP
-- 
smscLaucp OBJECT-TYPE
	SYNTAX  SEQUENCE OF LaucpInstanceEntry
	MAX-ACCESS  not-accessible
	STATUS  current
	DESCRIPTION
		"Mapping table for SMSC LA_UCP entities."
   ::= { smscClassOther   14  }

laucpInstanceEntry  OBJECT-TYPE
	SYNTAX LaucpInstanceEntry
	MAX-ACCESS  not-accessible
	STATUS  current
	DESCRIPTION
		"An entry (row) in the entityInstanceTable."
	INDEX { IMPLIED smscLaucpName }
   ::= { smscLaucp 1 }

LaucpInstanceEntry ::= SEQUENCE {
		smscLaucpName     DisplayString,
		smscLaucpState   INTEGER,
		smscLaucpLastupdate   TimeTicks,
		smscLaucpNode	   DisplayString
	}

smscLaucpName  OBJECT-TYPE
	SYNTAX  DisplayString
	MAX-ACCESS  read-only
	STATUS   current
	DESCRIPTION
		"Identifies the name of the entity."
   ::= {laucpInstanceEntry 1 }

smscLaucpState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { laucpInstanceEntry 2 }


smscLaucpLastupdate OBJECT-TYPE
		SYNTAX	TimeTicks
		MAX-ACCESS read-only
		STATUS current
		DESCRIPTION
			"Value which reflects the last time the entities fields have been updated"
	::= { laucpInstanceEntry	3 }

smscLaucpNode  OBJECT-TYPE
	SYNTAX  DisplayString
	MAX-ACCESS  read-only
	STATUS   current
	DESCRIPTION
		"Identifies the node the entity is running on."
   ::= {laucpInstanceEntry 4 }



-- end of LA_UCP description.
-- --------------------------------------


-- --------------------------------------
-- Class LA_SMPP
-- 
smscLasmpp OBJECT-TYPE
	SYNTAX  SEQUENCE OF LasmppInstanceEntry
	MAX-ACCESS  not-accessible
	STATUS  current
	DESCRIPTION
		"Mapping table for SMSC LA_SMPP entities."
   ::= { smscClassOther   15  }

lasmppInstanceEntry  OBJECT-TYPE
	SYNTAX LasmppInstanceEntry
	MAX-ACCESS  not-accessible
	STATUS  current
	DESCRIPTION
		"An entry (row) in the entityInstanceTable."
	INDEX { IMPLIED smscLasmppName }
   ::= { smscLasmpp 1 }

LasmppInstanceEntry ::= SEQUENCE {
		smscLasmppName     DisplayString,
		smscLasmppState   INTEGER,
		smscLasmppLastupdate   TimeTicks,
		smscLasmppNode	   DisplayString
	}

smscLasmppName  OBJECT-TYPE
	SYNTAX  DisplayString
	MAX-ACCESS  read-only
	STATUS   current
	DESCRIPTION
		"Identifies the name of the entity."
   ::= {lasmppInstanceEntry 1 }

smscLasmppState  OBJECT-TYPE
	SYNTAX  INTEGER {
		initialized(1),
		active(2),
		suspend(3),
		blocked(4),
		shuttingdown(5),
		stopped(6),
		reltest(7),
		restarting(8),
		unknown(9)
	}
	MAX-ACCESS  read-only
	STATUS  current
	DESCRIPTION
		"Identifies the state of the entity."
   ::= { lasmppInstanceEntry 2 }


smscLasmppLastupdate OBJECT-TYPE
		SYNTAX	TimeTicks
		MAX-ACCESS read-only
		STATUS current
		DESCRIPTION
			"Value which reflects the last time the entities fields have been updated"
	::= { lasmppInstanceEntry	3 }

smscLasmppNode  OBJECT-TYPE
	SYNTAX  DisplayString
	MAX-ACCESS  read-only
	STATUS   current
	DESCRIPTION
		"Identifies the node the entity is running on."
   ::= {lasmppInstanceEntry 4 }



-- end of LA_SMPP description.
-- --------------------------------------


-- --------------------------------------
-- Class MD
-- 
smscMd   OBJECT IDENTIFIER ::= { smscClassManagement   1   }

smscMdName  OBJECT-TYPE
	SYNTAX  DisplayString
	MAX-ACCESS  read-only
	STATUS   current
	DESCRIPTION
		"Identifies the name of the entity."
   ::= { smscMd 1 }

smscMdState  OBJECT-TYPE
	SYNTAX  INTEGER {
		initialized(1),
		active(2),
		suspend(3),
		blocked(4),
		shuttingdown(5),
		stopped(6),
		reltest(7),
		restarting(8),
		unknown(9)
	}
	MAX-ACCESS  read-only
	STATUS   current
	DESCRIPTION
		"Identifies the state of the Md in the system."
   ::= { smscMd 2 }


smscMdLastupdate OBJECT-TYPE
		SYNTAX	TimeTicks
		MAX-ACCESS read-only
		STATUS current
		DESCRIPTION
			"Value which reflects the last time the entities fields have been updated"
	::= { smscMd	3 }

smscMdNode  OBJECT-TYPE
	SYNTAX  DisplayString
	MAX-ACCESS  read-only
	STATUS   current
	DESCRIPTION
		"Identifies the node the entity is running on."
   ::= {smscMd 4 }



-- end of MD description.
-- --------------------------------------


-- --------------------------------------
-- Class AD
-- 
smscAd   OBJECT IDENTIFIER ::= { smscClassManagement   2   }

smscAdName  OBJECT-TYPE
	SYNTAX  DisplayString
	MAX-ACCESS  read-only
	STATUS   current
	DESCRIPTION
		"Identifies the name of the entity."
   ::= { smscAd 1 }

smscAdState  OBJECT-TYPE
	SYNTAX  INTEGER {
		initialized(1),
		active(2),
		suspend(3),
		blocked(4),
		shuttingdown(5),
		stopped(6),
		reltest(7),
		restarting(8),
		unknown(9)
	}
	MAX-ACCESS  read-only
	STATUS   current
	DESCRIPTION
		"Identifies the state of the Ad in the system."
   ::= { smscAd 2 }


smscAdLastupdate OBJECT-TYPE
		SYNTAX	TimeTicks
		MAX-ACCESS read-only
		STATUS current
		DESCRIPTION
			"Value which reflects the last time the entities fields have been updated"
	::= { smscAd	3 }

smscAdNode  OBJECT-TYPE
	SYNTAX  DisplayString
	MAX-ACCESS  read-only
	STATUS   current
	DESCRIPTION
		"Identifies the node the entity is running on."
   ::= {smscAd 4 }

smscAdAdReceived OBJECT-TYPE
		SYNTAX	Unsigned32
		MAX-ACCESS read-only
		STATUS current
		DESCRIPTION
			"Number of commands received for AD"
	::= { smscAd	5 }

smscAdAdResponded OBJECT-TYPE
		SYNTAX	Unsigned32
		MAX-ACCESS read-only
		STATUS current
		DESCRIPTION
			"Number of responses on AD commands sent"
	::= { smscAd	6 }

smscAdEntReceived OBJECT-TYPE
		SYNTAX	Unsigned32
		MAX-ACCESS read-only
		STATUS current
		DESCRIPTION
			"Number of commands received and routed to entity"
	::= { smscAd	7 }

smscAdEntResponded OBJECT-TYPE
		SYNTAX	Unsigned32
		MAX-ACCESS read-only
		STATUS current
		DESCRIPTION
			"Number of resp. received and routed from entity"
	::= { smscAd	8 }

smscAdEntActive OBJECT-TYPE
		SYNTAX	Unsigned32
		MAX-ACCESS read-only
		STATUS current
		DESCRIPTION
			"Number of entities on this node"
	::= { smscAd	9 }



-- end of AD description.
-- --------------------------------------


    smscCfgFilterNode OBJECT-TYPE
        SYNTAX  INTEGER {
            enabled(1),
            disabled(2)
        }
        MAX-ACCESS  read-write
        STATUS      current
        DESCRIPTION
        "Switch for filter on node name."
        DEFVAL { enabled }
        ::= { smscTrapFilterCfg 1 }


    smscCfgFilterSeverity OBJECT-TYPE
        SYNTAX  INTEGER {
            enabled(1),
            disabled(2)
        }
        MAX-ACCESS  read-write
        STATUS      current
        DESCRIPTION
        "Switch for filter on severity"
        DEFVAL { enabled }
        ::= { smscTrapFilterCfg 2 }

    smscCfgFilterPattern OBJECT-TYPE
        SYNTAX  INTEGER {
            enabled(1),
            disabled(2)
        }
        MAX-ACCESS  read-write
        STATUS      current
        DESCRIPTION
        "Switch for filter on text pattern"
        DEFVAL { enabled }
        ::= { smscTrapFilterCfg 3 }

--
-- TRAP section for the SMSC subagent
-- traps generated from the SMSC model
-- Do not modify !
--

--
-- Cold start trap when agent is starting
--
    smscColdStartTrap TRAP-TYPE
        ENTERPRISE  smscAgent
        VARIABLES  {trapTimeStamp, trapNodeName}
        DESCRIPTION
            "This is the cold start trap for the SMSC agent. The following
            definitions are TeMIP specific clauses
            EVENTTYPE-DEFAULT: 2
            PCAUSE-DEFAULT: 58
            SEVERITY-DEFAULT: Clear
            MANAGEDOBJECT-DEFAULT: smscAgent"
        ::= 0


--
-- Warm start trap when agent is restarting
--
    smscWarmStartTrap TRAP-TYPE
        ENTERPRISE  smscAgent
        VARIABLES  {trapTimeStamp, trapNodeName}
        DESCRIPTION
            "This is the warm start trap for the SMSC agent. The following
            definitions are TeMIP specific clauses
            EVENTTYPE-DEFAULT: 2
            PCAUSE-DEFAULT: 59
            SEVERITY-DEFAULT: Clear
            MANAGEDOBJECT-DEFAULT: smscAgent"
        ::= 1

--
-- Termination trap when agent is stopped
--
    smscTerminationTrap TRAP-TYPE
        ENTERPRISE  smscAgent
        VARIABLES  {trapTimeStamp, trapNodeName}
        DESCRIPTION
            "Trap to indicate termination of the SMSC agent
            SEVERITY-DEFAULT: Warning
            MANAGEDOBJECT-DEFAULT: smscAgent"
        ::= 2


--
--Internal Trap give status information of the agent
--
    smscInternalTrap TRAP-TYPE
        ENTERPRISE  smscAgent
        VARIABLES  {trapNotificationId, trapSeverity, trapData, trapTimeStamp}
        DESCRIPTION
            "Internal status information of the agent
            NOTIFICATIONID-VARIABLE: trapNotificationId
            SEVERITY-VARIABLE: trapSeverity
            ADDITIONAL-TEXT-VARIABLES: {trapData}
            MANAGEDOBJECT-DEFAULT: smscAgent"
        ::= 10

   --
   --Internal Trap give status information of the agent
   --
    smscInternalIndeterminateTrap TRAP-TYPE
        ENTERPRISE  smscAgent
        VARIABLES  {trapNotificationId, trapSeverity, trapData, trapTimeStamp}
        DESCRIPTION
            "Internal status information of the agent
            NOTIFICATIONID-VARIABLE: trapNotificationId
            SEVERITY-VARIABLE: trapSeverity
            ADDITIONAL-TEXT-VARIABLES: {trapData}
            MANAGEDOBJECT-DEFAULT: smscAgent"
        ::= 50


   --
   --Internal Trap give status information of the agent
   --
    smscInternalCriticalTrap TRAP-TYPE
        ENTERPRISE  smscAgent
        VARIABLES  {trapNotificationId, trapSeverity, trapData, trapTimeStamp}
        DESCRIPTION
            "Internal status information of the agent
            NOTIFICATIONID-VARIABLE: trapNotificationId
            SEVERITY-VARIABLE: trapSeverity
            ADDITIONAL-TEXT-VARIABLES: {trapData}
            MANAGEDOBJECT-DEFAULT: smscAgent"
        ::= 51
               
   --
   --Internal Trap give status information of the agent
   --
    smscInternalMajorTrap TRAP-TYPE
        ENTERPRISE  smscAgent
        VARIABLES  {trapNotificationId, trapSeverity, trapData, trapTimeStamp}
        DESCRIPTION
            "Internal status information of the agent
            NOTIFICATIONID-VARIABLE: trapNotificationId
            SEVERITY-VARIABLE: trapSeverity
            ADDITIONAL-TEXT-VARIABLES: {trapData}
            MANAGEDOBJECT-DEFAULT: smscAgent"
        ::= 52


   --
   --Internal Trap give status information of the agent
   --
    smscInternalMinorTrap TRAP-TYPE
        ENTERPRISE  smscAgent
        VARIABLES  {trapNotificationId, trapSeverity, trapData, trapTimeStamp}
        DESCRIPTION
            "Internal status information of the agent
            NOTIFICATIONID-VARIABLE: trapNotificationId
            SEVERITY-VARIABLE: trapSeverity
            ADDITIONAL-TEXT-VARIABLES: {trapData}
            MANAGEDOBJECT-DEFAULT: smscAgent"
        ::= 53
                      
   --
   --Internal Trap give status information of the agent
   --
    smscInternalWarningTrap TRAP-TYPE
        ENTERPRISE  smscAgent
        VARIABLES  {trapNotificationId, trapSeverity, trapData, trapTimeStamp}
        DESCRIPTION
            "Internal status information of the agent
            NOTIFICATIONID-VARIABLE: trapNotificationId
            SEVERITY-VARIABLE: trapSeverity
            ADDITIONAL-TEXT-VARIABLES: {trapData}
            MANAGEDOBJECT-DEFAULT: smscAgent"
        ::= 54


   --
   --Internal Trap give status information of the agent
   --
    smscInternalClearTrap TRAP-TYPE
        ENTERPRISE  smscAgent
        VARIABLES  {trapNotificationId, trapSeverity, trapData, trapTimeStamp}
        DESCRIPTION
            "Internal status information of the agent
            NOTIFICATIONID-VARIABLE: trapNotificationId
            SEVERITY-VARIABLE: trapSeverity
            ADDITIONAL-TEXT-VARIABLES: {trapData}
            MANAGEDOBJECT-DEFAULT: smscAgent"
        ::= 55
        

    --
    -- Obsolete Section for Backward compatibility (before SMSC 4.5)
    --
    

   --
   -- TRAP for table: smscX25
   --
    smscX25TrapOld TRAP-TYPE
        ENTERPRISE  smscAgent
        VARIABLES  {trapNotificationId, trapSeverity, trapData
                , smscX25Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX25
            MANAGEDOBJECT-DEFAULT: smscAgent"
        ::= 400


   --
   -- TRAP for table: smscX25
   --
    smscX25IndeterminateTrapOld TRAP-TYPE
        ENTERPRISE  smscAgent
        VARIABLES  {trapNotificationId, trapSeverity, trapData
                , smscX25Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX25
            MANAGEDOBJECT-DEFAULT: smscAgent"
        ::= 4000


   --
   -- TRAP for table: smscX25
   --
    smscX25CriticalTrapOld TRAP-TYPE
        ENTERPRISE  smscAgent
        VARIABLES  {trapNotificationId, trapSeverity, trapData
                , smscX25Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX25
            MANAGEDOBJECT-DEFAULT: smscAgent"
        ::= 4001


   --
   -- TRAP for table: smscX25
   --
    smscX25MajorTrapOld TRAP-TYPE
        ENTERPRISE  smscAgent
        VARIABLES  {trapNotificationId, trapSeverity, trapData
                , smscX25Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX25
            MANAGEDOBJECT-DEFAULT: smscAgent"
        ::= 4002


   --
   -- TRAP for table: smscX25
   --
    smscX25MinorTrapOld TRAP-TYPE
        ENTERPRISE  smscAgent
        VARIABLES  {trapNotificationId, trapSeverity, trapData
                , smscX25Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX25
            MANAGEDOBJECT-DEFAULT: smscAgent"
        ::= 4003


   --
   -- TRAP for table: smscX25
   --
    smscX25WarningTrapOld TRAP-TYPE
        ENTERPRISE  smscAgent
        VARIABLES  {trapNotificationId, trapSeverity, trapData
                , smscX25Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX25
            MANAGEDOBJECT-DEFAULT: smscAgent"
        ::= 4004


   --
   -- TRAP for table: smscX25
   --
    smscX25ClearTrapOld TRAP-TYPE
        ENTERPRISE  smscAgent
        VARIABLES  {trapNotificationId, trapSeverity, trapData
                , smscX25Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX25
            MANAGEDOBJECT-DEFAULT: smscAgent"
        ::= 4005


   --
   -- TRAP for table: smscTcp
   --
    smscTcpTrapOld TRAP-TYPE
        ENTERPRISE  smscAgent
        VARIABLES  {trapNotificationId, trapSeverity, trapData
                , smscTcpName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTcp
            MANAGEDOBJECT-DEFAULT: smscAgent"
        ::= 401


   --
   -- TRAP for table: smscTcp
   --
    smscTcpIndeterminateTrapOld TRAP-TYPE
        ENTERPRISE  smscAgent
        VARIABLES  {trapNotificationId, trapSeverity, trapData
                , smscTcpName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTcp
            MANAGEDOBJECT-DEFAULT: smscAgent"
        ::= 4010


   --
   -- TRAP for table: smscTcp
   --
    smscTcpCriticalTrapOld TRAP-TYPE
        ENTERPRISE  smscAgent
        VARIABLES  {trapNotificationId, trapSeverity, trapData
                , smscTcpName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTcp
            MANAGEDOBJECT-DEFAULT: smscAgent"
        ::= 4011


   --
   -- TRAP for table: smscTcp
   --
    smscTcpMajorTrapOld TRAP-TYPE
        ENTERPRISE  smscAgent
        VARIABLES  {trapNotificationId, trapSeverity, trapData
                , smscTcpName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTcp
            MANAGEDOBJECT-DEFAULT: smscAgent"
        ::= 4012


   --
   -- TRAP for table: smscTcp
   --
    smscTcpMinorTrapOld TRAP-TYPE
        ENTERPRISE  smscAgent
        VARIABLES  {trapNotificationId, trapSeverity, trapData
                , smscTcpName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTcp
            MANAGEDOBJECT-DEFAULT: smscAgent"
        ::= 4013


   --
   -- TRAP for table: smscTcp
   --
    smscTcpWarningTrapOld TRAP-TYPE
        ENTERPRISE  smscAgent
        VARIABLES  {trapNotificationId, trapSeverity, trapData
                , smscTcpName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTcp
            MANAGEDOBJECT-DEFAULT: smscAgent"
        ::= 4014


   --
   -- TRAP for table: smscTcp
   --
    smscTcpClearTrapOld TRAP-TYPE
        ENTERPRISE  smscAgent
        VARIABLES  {trapNotificationId, trapSeverity, trapData
                , smscTcpName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTcp
            MANAGEDOBJECT-DEFAULT: smscAgent"
        ::= 4015


   --
   -- TRAP for table: smscX29
   --
    smscX29TrapOld TRAP-TYPE
        ENTERPRISE  smscAgent
        VARIABLES  {trapNotificationId, trapSeverity, trapData
                , smscX29Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX29
            MANAGEDOBJECT-DEFAULT: smscAgent"
        ::= 402


   --
   -- TRAP for table: smscX29
   --
    smscX29IndeterminateTrapOld TRAP-TYPE
        ENTERPRISE  smscAgent
        VARIABLES  {trapNotificationId, trapSeverity, trapData
                , smscX29Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX29
            MANAGEDOBJECT-DEFAULT: smscAgent"
        ::= 4020


   --
   -- TRAP for table: smscX29
   --
    smscX29CriticalTrapOld TRAP-TYPE
        ENTERPRISE  smscAgent
        VARIABLES  {trapNotificationId, trapSeverity, trapData
                , smscX29Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX29
            MANAGEDOBJECT-DEFAULT: smscAgent"
        ::= 4021


   --
   -- TRAP for table: smscX29
   --
    smscX29MajorTrapOld TRAP-TYPE
        ENTERPRISE  smscAgent
        VARIABLES  {trapNotificationId, trapSeverity, trapData
                , smscX29Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX29
            MANAGEDOBJECT-DEFAULT: smscAgent"
        ::= 4022


   --
   -- TRAP for table: smscX29
   --
    smscX29MinorTrapOld TRAP-TYPE
        ENTERPRISE  smscAgent
        VARIABLES  {trapNotificationId, trapSeverity, trapData
                , smscX29Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX29
            MANAGEDOBJECT-DEFAULT: smscAgent"
        ::= 4023


   --
   -- TRAP for table: smscX29
   --
    smscX29WarningTrapOld TRAP-TYPE
        ENTERPRISE  smscAgent
        VARIABLES  {trapNotificationId, trapSeverity, trapData
                , smscX29Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX29
            MANAGEDOBJECT-DEFAULT: smscAgent"
        ::= 4024


   --
   -- TRAP for table: smscX29
   --
    smscX29ClearTrapOld TRAP-TYPE
        ENTERPRISE  smscAgent
        VARIABLES  {trapNotificationId, trapSeverity, trapData
                , smscX29Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscX29
            MANAGEDOBJECT-DEFAULT: smscAgent"
        ::= 4025


   --
   -- TRAP for table: smscEmap
   --
    smscEmapTrapOld TRAP-TYPE
        ENTERPRISE  smscAgent
        VARIABLES  {trapNotificationId, trapSeverity, trapData
                , smscEmapName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEmap
            MANAGEDOBJECT-DEFAULT: smscAgent"
        ::= 403


   --
   -- TRAP for table: smscEmap
   --
    smscEmapIndeterminateTrapOld TRAP-TYPE
        ENTERPRISE  smscAgent
        VARIABLES  {trapNotificationId, trapSeverity, trapData
                , smscEmapName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEmap
            MANAGEDOBJECT-DEFAULT: smscAgent"
        ::= 4030


   --
   -- TRAP for table: smscEmap
   --
    smscEmapCriticalTrapOld TRAP-TYPE
        ENTERPRISE  smscAgent
        VARIABLES  {trapNotificationId, trapSeverity, trapData
                , smscEmapName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEmap
            MANAGEDOBJECT-DEFAULT: smscAgent"
        ::= 4031


   --
   -- TRAP for table: smscEmap
   --
    smscEmapMajorTrapOld TRAP-TYPE
        ENTERPRISE  smscAgent
        VARIABLES  {trapNotificationId, trapSeverity, trapData
                , smscEmapName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEmap
            MANAGEDOBJECT-DEFAULT: smscAgent"
        ::= 4032


   --
   -- TRAP for table: smscEmap
   --
    smscEmapMinorTrapOld TRAP-TYPE
        ENTERPRISE  smscAgent
        VARIABLES  {trapNotificationId, trapSeverity, trapData
                , smscEmapName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEmap
            MANAGEDOBJECT-DEFAULT: smscAgent"
        ::= 4033


   --
   -- TRAP for table: smscEmap
   --
    smscEmapWarningTrapOld TRAP-TYPE
        ENTERPRISE  smscAgent
        VARIABLES  {trapNotificationId, trapSeverity, trapData
                , smscEmapName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEmap
            MANAGEDOBJECT-DEFAULT: smscAgent"
        ::= 4034


   --
   -- TRAP for table: smscEmap
   --
    smscEmapClearTrapOld TRAP-TYPE
        ENTERPRISE  smscAgent
        VARIABLES  {trapNotificationId, trapSeverity, trapData
                , smscEmapName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEmap
            MANAGEDOBJECT-DEFAULT: smscAgent"
        ::= 4035


   --
   -- TRAP for table: smscPstna
   --
    smscPstnaTrapOld TRAP-TYPE
        ENTERPRISE  smscAgent
        VARIABLES  {trapNotificationId, trapSeverity, trapData
                , smscPstnaName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPstna
            MANAGEDOBJECT-DEFAULT: smscAgent"
        ::= 404


   --
   -- TRAP for table: smscPstna
   --
    smscPstnaIndeterminateTrapOld TRAP-TYPE
        ENTERPRISE  smscAgent
        VARIABLES  {trapNotificationId, trapSeverity, trapData
                , smscPstnaName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPstna
            MANAGEDOBJECT-DEFAULT: smscAgent"
        ::= 4040


   --
   -- TRAP for table: smscPstna
   --
    smscPstnaCriticalTrapOld TRAP-TYPE
        ENTERPRISE  smscAgent
        VARIABLES  {trapNotificationId, trapSeverity, trapData
                , smscPstnaName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPstna
            MANAGEDOBJECT-DEFAULT: smscAgent"
        ::= 4041


   --
   -- TRAP for table: smscPstna
   --
    smscPstnaMajorTrapOld TRAP-TYPE
        ENTERPRISE  smscAgent
        VARIABLES  {trapNotificationId, trapSeverity, trapData
                , smscPstnaName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPstna
            MANAGEDOBJECT-DEFAULT: smscAgent"
        ::= 4042


   --
   -- TRAP for table: smscPstna
   --
    smscPstnaMinorTrapOld TRAP-TYPE
        ENTERPRISE  smscAgent
        VARIABLES  {trapNotificationId, trapSeverity, trapData
                , smscPstnaName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPstna
            MANAGEDOBJECT-DEFAULT: smscAgent"
        ::= 4043


   --
   -- TRAP for table: smscPstna
   --
    smscPstnaWarningTrapOld TRAP-TYPE
        ENTERPRISE  smscAgent
        VARIABLES  {trapNotificationId, trapSeverity, trapData
                , smscPstnaName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPstna
            MANAGEDOBJECT-DEFAULT: smscAgent"
        ::= 4044


   --
   -- TRAP for table: smscPstna
   --
    smscPstnaClearTrapOld TRAP-TYPE
        ENTERPRISE  smscAgent
        VARIABLES  {trapNotificationId, trapSeverity, trapData
                , smscPstnaName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPstna
            MANAGEDOBJECT-DEFAULT: smscAgent"
        ::= 4045


   --
   -- TRAP for table: smscGiw
   --
    smscGiwTrapOld TRAP-TYPE
        ENTERPRISE  smscAgent
        VARIABLES  {trapNotificationId, trapSeverity, trapData
                , smscGiwName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscGiw
            MANAGEDOBJECT-DEFAULT: smscAgent"
        ::= 405


   --
   -- TRAP for table: smscGiw
   --
    smscGiwIndeterminateTrapOld TRAP-TYPE
        ENTERPRISE  smscAgent
        VARIABLES  {trapNotificationId, trapSeverity, trapData
                , smscGiwName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscGiw
            MANAGEDOBJECT-DEFAULT: smscAgent"
        ::= 4050


   --
   -- TRAP for table: smscGiw
   --
    smscGiwCriticalTrapOld TRAP-TYPE
        ENTERPRISE  smscAgent
        VARIABLES  {trapNotificationId, trapSeverity, trapData
                , smscGiwName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscGiw
            MANAGEDOBJECT-DEFAULT: smscAgent"
        ::= 4051


   --
   -- TRAP for table: smscGiw
   --
    smscGiwMajorTrapOld TRAP-TYPE
        ENTERPRISE  smscAgent
        VARIABLES  {trapNotificationId, trapSeverity, trapData
                , smscGiwName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscGiw
            MANAGEDOBJECT-DEFAULT: smscAgent"
        ::= 4052


   --
   -- TRAP for table: smscGiw
   --
    smscGiwMinorTrapOld TRAP-TYPE
        ENTERPRISE  smscAgent
        VARIABLES  {trapNotificationId, trapSeverity, trapData
                , smscGiwName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscGiw
            MANAGEDOBJECT-DEFAULT: smscAgent"
        ::= 4053


   --
   -- TRAP for table: smscGiw
   --
    smscGiwWarningTrapOld TRAP-TYPE
        ENTERPRISE  smscAgent
        VARIABLES  {trapNotificationId, trapSeverity, trapData
                , smscGiwName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscGiw
            MANAGEDOBJECT-DEFAULT: smscAgent"
        ::= 4054


   --
   -- TRAP for table: smscGiw
   --
    smscGiwClearTrapOld TRAP-TYPE
        ENTERPRISE  smscAgent
        VARIABLES  {trapNotificationId, trapSeverity, trapData
                , smscGiwName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscGiw
            MANAGEDOBJECT-DEFAULT: smscAgent"
        ::= 4055


   --
   -- TRAP for table: smscFax3srv
   --
    smscFax3srvTrapOld TRAP-TYPE
        ENTERPRISE  smscAgent
        VARIABLES  {trapNotificationId, trapSeverity, trapData
                , smscFax3srvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFax3srv
            MANAGEDOBJECT-DEFAULT: smscAgent"
        ::= 406


   --
   -- TRAP for table: smscFax3srv
   --
    smscFax3srvIndeterminateTrapOld TRAP-TYPE
        ENTERPRISE  smscAgent
        VARIABLES  {trapNotificationId, trapSeverity, trapData
                , smscFax3srvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFax3srv
            MANAGEDOBJECT-DEFAULT: smscAgent"
        ::= 4060


   --
   -- TRAP for table: smscFax3srv
   --
    smscFax3srvCriticalTrapOld TRAP-TYPE
        ENTERPRISE  smscAgent
        VARIABLES  {trapNotificationId, trapSeverity, trapData
                , smscFax3srvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFax3srv
            MANAGEDOBJECT-DEFAULT: smscAgent"
        ::= 4061


   --
   -- TRAP for table: smscFax3srv
   --
    smscFax3srvMajorTrapOld TRAP-TYPE
        ENTERPRISE  smscAgent
        VARIABLES  {trapNotificationId, trapSeverity, trapData
                , smscFax3srvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFax3srv
            MANAGEDOBJECT-DEFAULT: smscAgent"
        ::= 4062


   --
   -- TRAP for table: smscFax3srv
   --
    smscFax3srvMinorTrapOld TRAP-TYPE
        ENTERPRISE  smscAgent
        VARIABLES  {trapNotificationId, trapSeverity, trapData
                , smscFax3srvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFax3srv
            MANAGEDOBJECT-DEFAULT: smscAgent"
        ::= 4063


   --
   -- TRAP for table: smscFax3srv
   --
    smscFax3srvWarningTrapOld TRAP-TYPE
        ENTERPRISE  smscAgent
        VARIABLES  {trapNotificationId, trapSeverity, trapData
                , smscFax3srvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFax3srv
            MANAGEDOBJECT-DEFAULT: smscAgent"
        ::= 4064


   --
   -- TRAP for table: smscFax3srv
   --
    smscFax3srvClearTrapOld TRAP-TYPE
        ENTERPRISE  smscAgent
        VARIABLES  {trapNotificationId, trapSeverity, trapData
                , smscFax3srvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFax3srv
            MANAGEDOBJECT-DEFAULT: smscAgent"
        ::= 4065


   --
   -- TRAP for table: smscEir
   --
    smscEirTrapOld TRAP-TYPE
        ENTERPRISE  smscAgent
        VARIABLES  {trapNotificationId, trapSeverity, trapData
                , smscEirName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEir
            MANAGEDOBJECT-DEFAULT: smscAgent"
        ::= 407


   --
   -- TRAP for table: smscEir
   --
    smscEirIndeterminateTrapOld TRAP-TYPE
        ENTERPRISE  smscAgent
        VARIABLES  {trapNotificationId, trapSeverity, trapData
                , smscEirName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEir
            MANAGEDOBJECT-DEFAULT: smscAgent"
        ::= 4070


   --
   -- TRAP for table: smscEir
   --
    smscEirCriticalTrapOld TRAP-TYPE
        ENTERPRISE  smscAgent
        VARIABLES  {trapNotificationId, trapSeverity, trapData
                , smscEirName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEir
            MANAGEDOBJECT-DEFAULT: smscAgent"
        ::= 4071


   --
   -- TRAP for table: smscEir
   --
    smscEirMajorTrapOld TRAP-TYPE
        ENTERPRISE  smscAgent
        VARIABLES  {trapNotificationId, trapSeverity, trapData
                , smscEirName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEir
            MANAGEDOBJECT-DEFAULT: smscAgent"
        ::= 4072


   --
   -- TRAP for table: smscEir
   --
    smscEirMinorTrapOld TRAP-TYPE
        ENTERPRISE  smscAgent
        VARIABLES  {trapNotificationId, trapSeverity, trapData
                , smscEirName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEir
            MANAGEDOBJECT-DEFAULT: smscAgent"
        ::= 4073


   --
   -- TRAP for table: smscEir
   --
    smscEirWarningTrapOld TRAP-TYPE
        ENTERPRISE  smscAgent
        VARIABLES  {trapNotificationId, trapSeverity, trapData
                , smscEirName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEir
            MANAGEDOBJECT-DEFAULT: smscAgent"
        ::= 4074


   --
   -- TRAP for table: smscEir
   --
    smscEirClearTrapOld TRAP-TYPE
        ENTERPRISE  smscAgent
        VARIABLES  {trapNotificationId, trapSeverity, trapData
                , smscEirName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscEir
            MANAGEDOBJECT-DEFAULT: smscAgent"
        ::= 4075


   --
   -- TRAP for table: smscDlh
   --
    smscDlhTrapOld TRAP-TYPE
        ENTERPRISE  smscAgent
        VARIABLES  {trapNotificationId, trapSeverity, trapData
                , smscDlhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscDlh
            MANAGEDOBJECT-DEFAULT: smscAgent"
        ::= 408


   --
   -- TRAP for table: smscDlh
   --
    smscDlhIndeterminateTrapOld TRAP-TYPE
        ENTERPRISE  smscAgent
        VARIABLES  {trapNotificationId, trapSeverity, trapData
                , smscDlhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscDlh
            MANAGEDOBJECT-DEFAULT: smscAgent"
        ::= 4080


   --
   -- TRAP for table: smscDlh
   --
    smscDlhCriticalTrapOld TRAP-TYPE
        ENTERPRISE  smscAgent
        VARIABLES  {trapNotificationId, trapSeverity, trapData
                , smscDlhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscDlh
            MANAGEDOBJECT-DEFAULT: smscAgent"
        ::= 4081


   --
   -- TRAP for table: smscDlh
   --
    smscDlhMajorTrapOld TRAP-TYPE
        ENTERPRISE  smscAgent
        VARIABLES  {trapNotificationId, trapSeverity, trapData
                , smscDlhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscDlh
            MANAGEDOBJECT-DEFAULT: smscAgent"
        ::= 4082


   --
   -- TRAP for table: smscDlh
   --
    smscDlhMinorTrapOld TRAP-TYPE
        ENTERPRISE  smscAgent
        VARIABLES  {trapNotificationId, trapSeverity, trapData
                , smscDlhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscDlh
            MANAGEDOBJECT-DEFAULT: smscAgent"
        ::= 4083


   --
   -- TRAP for table: smscDlh
   --
    smscDlhWarningTrapOld TRAP-TYPE
        ENTERPRISE  smscAgent
        VARIABLES  {trapNotificationId, trapSeverity, trapData
                , smscDlhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscDlh
            MANAGEDOBJECT-DEFAULT: smscAgent"
        ::= 4084


   --
   -- TRAP for table: smscDlh
   --
    smscDlhClearTrapOld TRAP-TYPE
        ENTERPRISE  smscAgent
        VARIABLES  {trapNotificationId, trapSeverity, trapData
                , smscDlhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscDlh
            MANAGEDOBJECT-DEFAULT: smscAgent"
        ::= 4085


   --
   -- TRAP for table: smscSsd
   --
    smscSsdTrapOld TRAP-TYPE
        ENTERPRISE  smscAgent
        VARIABLES  {trapNotificationId, trapSeverity, trapData
                , smscSsdName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscSsd
            MANAGEDOBJECT-DEFAULT: smscAgent"
        ::= 409


   --
   -- TRAP for table: smscSsd
   --
    smscSsdIndeterminateTrapOld TRAP-TYPE
        ENTERPRISE  smscAgent
        VARIABLES  {trapNotificationId, trapSeverity, trapData
                , smscSsdName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscSsd
            MANAGEDOBJECT-DEFAULT: smscAgent"
        ::= 4090


   --
   -- TRAP for table: smscSsd
   --
    smscSsdCriticalTrapOld TRAP-TYPE
        ENTERPRISE  smscAgent
        VARIABLES  {trapNotificationId, trapSeverity, trapData
                , smscSsdName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscSsd
            MANAGEDOBJECT-DEFAULT: smscAgent"
        ::= 4091


   --
   -- TRAP for table: smscSsd
   --
    smscSsdMajorTrapOld TRAP-TYPE
        ENTERPRISE  smscAgent
        VARIABLES  {trapNotificationId, trapSeverity, trapData
                , smscSsdName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscSsd
            MANAGEDOBJECT-DEFAULT: smscAgent"
        ::= 4092


   --
   -- TRAP for table: smscSsd
   --
    smscSsdMinorTrapOld TRAP-TYPE
        ENTERPRISE  smscAgent
        VARIABLES  {trapNotificationId, trapSeverity, trapData
                , smscSsdName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscSsd
            MANAGEDOBJECT-DEFAULT: smscAgent"
        ::= 4093


   --
   -- TRAP for table: smscSsd
   --
    smscSsdWarningTrapOld TRAP-TYPE
        ENTERPRISE  smscAgent
        VARIABLES  {trapNotificationId, trapSeverity, trapData
                , smscSsdName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscSsd
            MANAGEDOBJECT-DEFAULT: smscAgent"
        ::= 4094


   --
   -- TRAP for table: smscSsd
   --
    smscSsdClearTrapOld TRAP-TYPE
        ENTERPRISE  smscAgent
        VARIABLES  {trapNotificationId, trapSeverity, trapData
                , smscSsdName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscSsd
            MANAGEDOBJECT-DEFAULT: smscAgent"
        ::= 4095


   --
   -- TRAP for table: smscPrh
   --
    smscPrhTrapOld TRAP-TYPE
        ENTERPRISE  smscAgent
        VARIABLES  {trapNotificationId, trapSeverity, trapData
                , smscPrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPrh
            MANAGEDOBJECT-DEFAULT: smscAgent"
        ::= 410


   --
   -- TRAP for table: smscPrh
   --
    smscPrhIndeterminateTrapOld TRAP-TYPE
        ENTERPRISE  smscAgent
        VARIABLES  {trapNotificationId, trapSeverity, trapData
                , smscPrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPrh
            MANAGEDOBJECT-DEFAULT: smscAgent"
        ::= 4100


   --
   -- TRAP for table: smscPrh
   --
    smscPrhCriticalTrapOld TRAP-TYPE
        ENTERPRISE  smscAgent
        VARIABLES  {trapNotificationId, trapSeverity, trapData
                , smscPrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPrh
            MANAGEDOBJECT-DEFAULT: smscAgent"
        ::= 4101


   --
   -- TRAP for table: smscPrh
   --
    smscPrhMajorTrapOld TRAP-TYPE
        ENTERPRISE  smscAgent
        VARIABLES  {trapNotificationId, trapSeverity, trapData
                , smscPrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPrh
            MANAGEDOBJECT-DEFAULT: smscAgent"
        ::= 4102


   --
   -- TRAP for table: smscPrh
   --
    smscPrhMinorTrapOld TRAP-TYPE
        ENTERPRISE  smscAgent
        VARIABLES  {trapNotificationId, trapSeverity, trapData
                , smscPrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPrh
            MANAGEDOBJECT-DEFAULT: smscAgent"
        ::= 4103


   --
   -- TRAP for table: smscPrh
   --
    smscPrhWarningTrapOld TRAP-TYPE
        ENTERPRISE  smscAgent
        VARIABLES  {trapNotificationId, trapSeverity, trapData
                , smscPrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPrh
            MANAGEDOBJECT-DEFAULT: smscAgent"
        ::= 4104


   --
   -- TRAP for table: smscPrh
   --
    smscPrhClearTrapOld TRAP-TYPE
        ENTERPRISE  smscAgent
        VARIABLES  {trapNotificationId, trapSeverity, trapData
                , smscPrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPrh
            MANAGEDOBJECT-DEFAULT: smscAgent"
        ::= 4105


   --
   -- TRAP for table: smscFrh
   --
    smscFrhTrapOld TRAP-TYPE
        ENTERPRISE  smscAgent
        VARIABLES  {trapNotificationId, trapSeverity, trapData
                , smscFrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFrh
            MANAGEDOBJECT-DEFAULT: smscAgent"
        ::= 411


   --
   -- TRAP for table: smscFrh
   --
    smscFrhIndeterminateTrapOld TRAP-TYPE
        ENTERPRISE  smscAgent
        VARIABLES  {trapNotificationId, trapSeverity, trapData
                , smscFrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFrh
            MANAGEDOBJECT-DEFAULT: smscAgent"
        ::= 4110


   --
   -- TRAP for table: smscFrh
   --
    smscFrhCriticalTrapOld TRAP-TYPE
        ENTERPRISE  smscAgent
        VARIABLES  {trapNotificationId, trapSeverity, trapData
                , smscFrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFrh
            MANAGEDOBJECT-DEFAULT: smscAgent"
        ::= 4111


   --
   -- TRAP for table: smscFrh
   --
    smscFrhMajorTrapOld TRAP-TYPE
        ENTERPRISE  smscAgent
        VARIABLES  {trapNotificationId, trapSeverity, trapData
                , smscFrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFrh
            MANAGEDOBJECT-DEFAULT: smscAgent"
        ::= 4112


   --
   -- TRAP for table: smscFrh
   --
    smscFrhMinorTrapOld TRAP-TYPE
        ENTERPRISE  smscAgent
        VARIABLES  {trapNotificationId, trapSeverity, trapData
                , smscFrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFrh
            MANAGEDOBJECT-DEFAULT: smscAgent"
        ::= 4113


   --
   -- TRAP for table: smscFrh
   --
    smscFrhWarningTrapOld TRAP-TYPE
        ENTERPRISE  smscAgent
        VARIABLES  {trapNotificationId, trapSeverity, trapData
                , smscFrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFrh
            MANAGEDOBJECT-DEFAULT: smscAgent"
        ::= 4114


   --
   -- TRAP for table: smscFrh
   --
    smscFrhClearTrapOld TRAP-TYPE
        ENTERPRISE  smscAgent
        VARIABLES  {trapNotificationId, trapSeverity, trapData
                , smscFrhName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscFrh
            MANAGEDOBJECT-DEFAULT: smscAgent"
        ::= 4115


   --
   -- TRAP for table: smscIsdn
   --
    smscIsdnTrapOld TRAP-TYPE
        ENTERPRISE  smscAgent
        VARIABLES  {trapNotificationId, trapSeverity, trapData
                , smscIsdnName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIsdn
            MANAGEDOBJECT-DEFAULT: smscAgent"
        ::= 412


   --
   -- TRAP for table: smscIsdn
   --
    smscIsdnIndeterminateTrapOld TRAP-TYPE
        ENTERPRISE  smscAgent
        VARIABLES  {trapNotificationId, trapSeverity, trapData
                , smscIsdnName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIsdn
            MANAGEDOBJECT-DEFAULT: smscAgent"
        ::= 4120


   --
   -- TRAP for table: smscIsdn
   --
    smscIsdnCriticalTrapOld TRAP-TYPE
        ENTERPRISE  smscAgent
        VARIABLES  {trapNotificationId, trapSeverity, trapData
                , smscIsdnName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIsdn
            MANAGEDOBJECT-DEFAULT: smscAgent"
        ::= 4121


   --
   -- TRAP for table: smscIsdn
   --
    smscIsdnMajorTrapOld TRAP-TYPE
        ENTERPRISE  smscAgent
        VARIABLES  {trapNotificationId, trapSeverity, trapData
                , smscIsdnName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIsdn
            MANAGEDOBJECT-DEFAULT: smscAgent"
        ::= 4122


   --
   -- TRAP for table: smscIsdn
   --
    smscIsdnMinorTrapOld TRAP-TYPE
        ENTERPRISE  smscAgent
        VARIABLES  {trapNotificationId, trapSeverity, trapData
                , smscIsdnName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIsdn
            MANAGEDOBJECT-DEFAULT: smscAgent"
        ::= 4123


   --
   -- TRAP for table: smscIsdn
   --
    smscIsdnWarningTrapOld TRAP-TYPE
        ENTERPRISE  smscAgent
        VARIABLES  {trapNotificationId, trapSeverity, trapData
                , smscIsdnName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIsdn
            MANAGEDOBJECT-DEFAULT: smscAgent"
        ::= 4124


   --
   -- TRAP for table: smscIsdn
   --
    smscIsdnClearTrapOld TRAP-TYPE
        ENTERPRISE  smscAgent
        VARIABLES  {trapNotificationId, trapSeverity, trapData
                , smscIsdnName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIsdn
            MANAGEDOBJECT-DEFAULT: smscAgent"
        ::= 4125


   --
   -- TRAP for table: smscLogsrv
   --
    smscLogsrvTrapOld TRAP-TYPE
        ENTERPRISE  smscAgent
        VARIABLES  {trapNotificationId, trapSeverity, trapData
                , smscLogsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscLogsrv
            MANAGEDOBJECT-DEFAULT: smscAgent"
        ::= 413


   --
   -- TRAP for table: smscLogsrv
   --
    smscLogsrvIndeterminateTrapOld TRAP-TYPE
        ENTERPRISE  smscAgent
        VARIABLES  {trapNotificationId, trapSeverity, trapData
                , smscLogsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscLogsrv
            MANAGEDOBJECT-DEFAULT: smscAgent"
        ::= 4130


   --
   -- TRAP for table: smscLogsrv
   --
    smscLogsrvCriticalTrapOld TRAP-TYPE
        ENTERPRISE  smscAgent
        VARIABLES  {trapNotificationId, trapSeverity, trapData
                , smscLogsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscLogsrv
            MANAGEDOBJECT-DEFAULT: smscAgent"
        ::= 4131


   --
   -- TRAP for table: smscLogsrv
   --
    smscLogsrvMajorTrapOld TRAP-TYPE
        ENTERPRISE  smscAgent
        VARIABLES  {trapNotificationId, trapSeverity, trapData
                , smscLogsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscLogsrv
            MANAGEDOBJECT-DEFAULT: smscAgent"
        ::= 4132


   --
   -- TRAP for table: smscLogsrv
   --
    smscLogsrvMinorTrapOld TRAP-TYPE
        ENTERPRISE  smscAgent
        VARIABLES  {trapNotificationId, trapSeverity, trapData
                , smscLogsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscLogsrv
            MANAGEDOBJECT-DEFAULT: smscAgent"
        ::= 4133


   --
   -- TRAP for table: smscLogsrv
   --
    smscLogsrvWarningTrapOld TRAP-TYPE
        ENTERPRISE  smscAgent
        VARIABLES  {trapNotificationId, trapSeverity, trapData
                , smscLogsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscLogsrv
            MANAGEDOBJECT-DEFAULT: smscAgent"
        ::= 4134


   --
   -- TRAP for table: smscLogsrv
   --
    smscLogsrvClearTrapOld TRAP-TYPE
        ENTERPRISE  smscAgent
        VARIABLES  {trapNotificationId, trapSeverity, trapData
                , smscLogsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscLogsrv
            MANAGEDOBJECT-DEFAULT: smscAgent"
        ::= 4135


   --
   -- TRAP for table: smscTrcsrv
   --
    smscTrcsrvTrapOld TRAP-TYPE
        ENTERPRISE  smscAgent
        VARIABLES  {trapNotificationId, trapSeverity, trapData
                , smscTrcsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTrcsrv
            MANAGEDOBJECT-DEFAULT: smscAgent"
        ::= 414


   --
   -- TRAP for table: smscTrcsrv
   --
    smscTrcsrvIndeterminateTrapOld TRAP-TYPE
        ENTERPRISE  smscAgent
        VARIABLES  {trapNotificationId, trapSeverity, trapData
                , smscTrcsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTrcsrv
            MANAGEDOBJECT-DEFAULT: smscAgent"
        ::= 4140


   --
   -- TRAP for table: smscTrcsrv
   --
    smscTrcsrvCriticalTrapOld TRAP-TYPE
        ENTERPRISE  smscAgent
        VARIABLES  {trapNotificationId, trapSeverity, trapData
                , smscTrcsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTrcsrv
            MANAGEDOBJECT-DEFAULT: smscAgent"
        ::= 4141


   --
   -- TRAP for table: smscTrcsrv
   --
    smscTrcsrvMajorTrapOld TRAP-TYPE
        ENTERPRISE  smscAgent
        VARIABLES  {trapNotificationId, trapSeverity, trapData
                , smscTrcsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTrcsrv
            MANAGEDOBJECT-DEFAULT: smscAgent"
        ::= 4142


   --
   -- TRAP for table: smscTrcsrv
   --
    smscTrcsrvMinorTrapOld TRAP-TYPE
        ENTERPRISE  smscAgent
        VARIABLES  {trapNotificationId, trapSeverity, trapData
                , smscTrcsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTrcsrv
            MANAGEDOBJECT-DEFAULT: smscAgent"
        ::= 4143


   --
   -- TRAP for table: smscTrcsrv
   --
    smscTrcsrvWarningTrapOld TRAP-TYPE
        ENTERPRISE  smscAgent
        VARIABLES  {trapNotificationId, trapSeverity, trapData
                , smscTrcsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTrcsrv
            MANAGEDOBJECT-DEFAULT: smscAgent"
        ::= 4144


   --
   -- TRAP for table: smscTrcsrv
   --
    smscTrcsrvClearTrapOld TRAP-TYPE
        ENTERPRISE  smscAgent
        VARIABLES  {trapNotificationId, trapSeverity, trapData
                , smscTrcsrvName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscTrcsrv
            MANAGEDOBJECT-DEFAULT: smscAgent"
        ::= 4145


   --
   -- TRAP for table: smscIs41
   --
    smscIs41TrapOld TRAP-TYPE
        ENTERPRISE  smscAgent
        VARIABLES  {trapNotificationId, trapSeverity, trapData
                , smscIs41Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIs41
            MANAGEDOBJECT-DEFAULT: smscAgent"
        ::= 415


   --
   -- TRAP for table: smscIs41
   --
    smscIs41IndeterminateTrapOld TRAP-TYPE
        ENTERPRISE  smscAgent
        VARIABLES  {trapNotificationId, trapSeverity, trapData
                , smscIs41Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIs41
            MANAGEDOBJECT-DEFAULT: smscAgent"
        ::= 4150


   --
   -- TRAP for table: smscIs41
   --
    smscIs41CriticalTrapOld TRAP-TYPE
        ENTERPRISE  smscAgent
        VARIABLES  {trapNotificationId, trapSeverity, trapData
                , smscIs41Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIs41
            MANAGEDOBJECT-DEFAULT: smscAgent"
        ::= 4151


   --
   -- TRAP for table: smscIs41
   --
    smscIs41MajorTrapOld TRAP-TYPE
        ENTERPRISE  smscAgent
        VARIABLES  {trapNotificationId, trapSeverity, trapData
                , smscIs41Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIs41
            MANAGEDOBJECT-DEFAULT: smscAgent"
        ::= 4152


   --
   -- TRAP for table: smscIs41
   --
    smscIs41MinorTrapOld TRAP-TYPE
        ENTERPRISE  smscAgent
        VARIABLES  {trapNotificationId, trapSeverity, trapData
                , smscIs41Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIs41
            MANAGEDOBJECT-DEFAULT: smscAgent"
        ::= 4153


   --
   -- TRAP for table: smscIs41
   --
    smscIs41WarningTrapOld TRAP-TYPE
        ENTERPRISE  smscAgent
        VARIABLES  {trapNotificationId, trapSeverity, trapData
                , smscIs41Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIs41
            MANAGEDOBJECT-DEFAULT: smscAgent"
        ::= 4154


   --
   -- TRAP for table: smscIs41
   --
    smscIs41ClearTrapOld TRAP-TYPE
        ENTERPRISE  smscAgent
        VARIABLES  {trapNotificationId, trapSeverity, trapData
                , smscIs41Name, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscIs41
            MANAGEDOBJECT-DEFAULT: smscAgent"
        ::= 4155


   --
   -- TRAP for table: smscPbr
   --
    smscPbrTrapOld TRAP-TYPE
        ENTERPRISE  smscAgent
        VARIABLES  {trapNotificationId, trapSeverity, trapData
                , smscPbrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbr
            MANAGEDOBJECT-DEFAULT: smscAgent"
        ::= 416


   --
   -- TRAP for table: smscPbr
   --
    smscPbrIndeterminateTrapOld TRAP-TYPE
        ENTERPRISE  smscAgent
        VARIABLES  {trapNotificationId, trapSeverity, trapData
                , smscPbrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbr
            MANAGEDOBJECT-DEFAULT: smscAgent"
        ::= 4160


   --
   -- TRAP for table: smscPbr
   --
    smscPbrCriticalTrapOld TRAP-TYPE
        ENTERPRISE  smscAgent
        VARIABLES  {trapNotificationId, trapSeverity, trapData
                , smscPbrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbr
            MANAGEDOBJECT-DEFAULT: smscAgent"
        ::= 4161


   --
   -- TRAP for table: smscPbr
   --
    smscPbrMajorTrapOld TRAP-TYPE
        ENTERPRISE  smscAgent
        VARIABLES  {trapNotificationId, trapSeverity, trapData
                , smscPbrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbr
            MANAGEDOBJECT-DEFAULT: smscAgent"
        ::= 4162


   --
   -- TRAP for table: smscPbr
   --
    smscPbrMinorTrapOld TRAP-TYPE
        ENTERPRISE  smscAgent
        VARIABLES  {trapNotificationId, trapSeverity, trapData
                , smscPbrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbr
            MANAGEDOBJECT-DEFAULT: smscAgent"
        ::= 4163


   --
   -- TRAP for table: smscPbr
   --
    smscPbrWarningTrapOld TRAP-TYPE
        ENTERPRISE  smscAgent
        VARIABLES  {trapNotificationId, trapSeverity, trapData
                , smscPbrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbr
            MANAGEDOBJECT-DEFAULT: smscAgent"
        ::= 4164


   --
   -- TRAP for table: smscPbr
   --
    smscPbrClearTrapOld TRAP-TYPE
        ENTERPRISE  smscAgent
        VARIABLES  {trapNotificationId, trapSeverity, trapData
                , smscPbrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbr
            MANAGEDOBJECT-DEFAULT: smscAgent"
        ::= 4165


   --
   -- TRAP for table: smscRtr
   --
    smscRtrTrapOld TRAP-TYPE
        ENTERPRISE  smscAgent
        VARIABLES  {trapNotificationId, trapSeverity, trapData
                , smscRtrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRtr
            MANAGEDOBJECT-DEFAULT: smscAgent"
        ::= 417


   --
   -- TRAP for table: smscRtr
   --
    smscRtrIndeterminateTrapOld TRAP-TYPE
        ENTERPRISE  smscAgent
        VARIABLES  {trapNotificationId, trapSeverity, trapData
                , smscRtrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRtr
            MANAGEDOBJECT-DEFAULT: smscAgent"
        ::= 4170


   --
   -- TRAP for table: smscRtr
   --
    smscRtrCriticalTrapOld TRAP-TYPE
        ENTERPRISE  smscAgent
        VARIABLES  {trapNotificationId, trapSeverity, trapData
                , smscRtrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRtr
            MANAGEDOBJECT-DEFAULT: smscAgent"
        ::= 4171


   --
   -- TRAP for table: smscRtr
   --
    smscRtrMajorTrapOld TRAP-TYPE
        ENTERPRISE  smscAgent
        VARIABLES  {trapNotificationId, trapSeverity, trapData
                , smscRtrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRtr
            MANAGEDOBJECT-DEFAULT: smscAgent"
        ::= 4172


   --
   -- TRAP for table: smscRtr
   --
    smscRtrMinorTrapOld TRAP-TYPE
        ENTERPRISE  smscAgent
        VARIABLES  {trapNotificationId, trapSeverity, trapData
                , smscRtrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRtr
            MANAGEDOBJECT-DEFAULT: smscAgent"
        ::= 4173


   --
   -- TRAP for table: smscRtr
   --
    smscRtrWarningTrapOld TRAP-TYPE
        ENTERPRISE  smscAgent
        VARIABLES  {trapNotificationId, trapSeverity, trapData
                , smscRtrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRtr
            MANAGEDOBJECT-DEFAULT: smscAgent"
        ::= 4174


   --
   -- TRAP for table: smscRtr
   --
    smscRtrClearTrapOld TRAP-TYPE
        ENTERPRISE  smscAgent
        VARIABLES  {trapNotificationId, trapSeverity, trapData
                , smscRtrName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRtr
            MANAGEDOBJECT-DEFAULT: smscAgent"
        ::= 4175


   --
   -- TRAP for table: smscRas
   --
    smscRasTrapOld TRAP-TYPE
        ENTERPRISE  smscAgent
        VARIABLES  {trapNotificationId, trapSeverity, trapData
                , smscRasName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRas
            MANAGEDOBJECT-DEFAULT: smscAgent"
        ::= 418


   --
   -- TRAP for table: smscRas
   --
    smscRasIndeterminateTrapOld TRAP-TYPE
        ENTERPRISE  smscAgent
        VARIABLES  {trapNotificationId, trapSeverity, trapData
                , smscRasName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRas
            MANAGEDOBJECT-DEFAULT: smscAgent"
        ::= 4180


   --
   -- TRAP for table: smscRas
   --
    smscRasCriticalTrapOld TRAP-TYPE
        ENTERPRISE  smscAgent
        VARIABLES  {trapNotificationId, trapSeverity, trapData
                , smscRasName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRas
            MANAGEDOBJECT-DEFAULT: smscAgent"
        ::= 4181


   --
   -- TRAP for table: smscRas
   --
    smscRasMajorTrapOld TRAP-TYPE
        ENTERPRISE  smscAgent
        VARIABLES  {trapNotificationId, trapSeverity, trapData
                , smscRasName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRas
            MANAGEDOBJECT-DEFAULT: smscAgent"
        ::= 4182


   --
   -- TRAP for table: smscRas
   --
    smscRasMinorTrapOld TRAP-TYPE
        ENTERPRISE  smscAgent
        VARIABLES  {trapNotificationId, trapSeverity, trapData
                , smscRasName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRas
            MANAGEDOBJECT-DEFAULT: smscAgent"
        ::= 4183


   --
   -- TRAP for table: smscRas
   --
    smscRasWarningTrapOld TRAP-TYPE
        ENTERPRISE  smscAgent
        VARIABLES  {trapNotificationId, trapSeverity, trapData
                , smscRasName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRas
            MANAGEDOBJECT-DEFAULT: smscAgent"
        ::= 4184


   --
   -- TRAP for table: smscRas
   --
    smscRasClearTrapOld TRAP-TYPE
        ENTERPRISE  smscAgent
        VARIABLES  {trapNotificationId, trapSeverity, trapData
                , smscRasName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscRas
            MANAGEDOBJECT-DEFAULT: smscAgent"
        ::= 4185


   --
   -- TRAP for table: smscPbb
   --
    smscPbbTrapOld TRAP-TYPE
        ENTERPRISE  smscAgent
        VARIABLES  {trapNotificationId, trapSeverity, trapData
                , smscPbbName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbb
            MANAGEDOBJECT-DEFAULT: smscAgent"
        ::= 419


   --
   -- TRAP for table: smscPbb
   --
    smscPbbIndeterminateTrapOld TRAP-TYPE
        ENTERPRISE  smscAgent
        VARIABLES  {trapNotificationId, trapSeverity, trapData
                , smscPbbName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbb
            MANAGEDOBJECT-DEFAULT: smscAgent"
        ::= 4190


   --
   -- TRAP for table: smscPbb
   --
    smscPbbCriticalTrapOld TRAP-TYPE
        ENTERPRISE  smscAgent
        VARIABLES  {trapNotificationId, trapSeverity, trapData
                , smscPbbName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbb
            MANAGEDOBJECT-DEFAULT: smscAgent"
        ::= 4191


   --
   -- TRAP for table: smscPbb
   --
    smscPbbMajorTrapOld TRAP-TYPE
        ENTERPRISE  smscAgent
        VARIABLES  {trapNotificationId, trapSeverity, trapData
                , smscPbbName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbb
            MANAGEDOBJECT-DEFAULT: smscAgent"
        ::= 4192


   --
   -- TRAP for table: smscPbb
   --
    smscPbbMinorTrapOld TRAP-TYPE
        ENTERPRISE  smscAgent
        VARIABLES  {trapNotificationId, trapSeverity, trapData
                , smscPbbName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbb
            MANAGEDOBJECT-DEFAULT: smscAgent"
        ::= 4193


    --
    -- TRAP for table: smscPbb
    --
    smscPbbWarningTrapOld TRAP-TYPE
        ENTERPRISE  smscAgent
        VARIABLES  {trapNotificationId, trapSeverity, trapData
                , smscPbbName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbb
            MANAGEDOBJECT-DEFAULT: smscAgent"
        ::= 4194

    --
    -- TRAP for table: smscPbb
    --
    smscPbbClearTrapOld TRAP-TYPE
        ENTERPRISE  smscAgent
        VARIABLES  {trapNotificationId, trapSeverity, trapData
                , smscPbbName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscPbb
            MANAGEDOBJECT-DEFAULT: smscAgent"
        ::= 4195


    --
    -- TRAP for table: smscCmlog
    --
    smscCmlogTrapOld TRAP-TYPE
        ENTERPRISE  smscAgent
        VARIABLES  {trapNotificationId, trapSeverity, trapData
                , smscCmlogName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscCmlog
            MANAGEDOBJECT-DEFAULT: smscAgent"
        ::= 420


    --
    -- TRAP for table: smscCmlog
    --
    smscCmlogIndeterminateTrapOld TRAP-TYPE
        ENTERPRISE  smscAgent
        VARIABLES  {trapNotificationId, trapSeverity, trapData
                , smscCmlogName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscCmlog
            MANAGEDOBJECT-DEFAULT: smscAgent"
        ::= 4200


    --
    -- TRAP for table: smscCmlog
    --
    smscCmlogCriticalTrapOld TRAP-TYPE
        ENTERPRISE  smscAgent
        VARIABLES  {trapNotificationId, trapSeverity, trapData
                , smscCmlogName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscCmlog
            MANAGEDOBJECT-DEFAULT: smscAgent"
        ::= 4201


   --
   -- TRAP for table: smscCmlog
   --
    smscCmlogMajorTrapOld TRAP-TYPE
        ENTERPRISE  smscAgent
        VARIABLES  {trapNotificationId, trapSeverity, trapData
                , smscCmlogName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscCmlog
            MANAGEDOBJECT-DEFAULT: smscAgent"
        ::= 4202


    --
    -- TRAP for table: smscCmlog
    --
    smscCmlogMinorTrapOld TRAP-TYPE
        ENTERPRISE  smscAgent
        VARIABLES  {trapNotificationId, trapSeverity, trapData
                , smscCmlogName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscCmlog
            MANAGEDOBJECT-DEFAULT: smscAgent"
        ::= 4203

 
    --
    -- TRAP for table: smscCmlog
    --
    smscCmlogWarningTrapOld TRAP-TYPE
        ENTERPRISE  smscAgent
        VARIABLES  {trapNotificationId, trapSeverity, trapData
                , smscCmlogName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscCmlog
            MANAGEDOBJECT-DEFAULT: smscAgent"
        ::= 4204


    --
    -- TRAP for table: smscCmlog
    --
    smscCmlogClearTrapOld TRAP-TYPE
        ENTERPRISE  smscAgent
        VARIABLES  {trapNotificationId, trapSeverity, trapData
                , smscCmlogName, trapTimeStamp, trapNodeName}
        DESCRIPTION
            "This is the trap definition to handle an SMSC entity events. This
            trap belongs to a specific entity class indicated in the following
            TeMIP specific clauses.
            NOTIFICATIONID-VARIABLE: trapNotificationId
            SEVERITY-VARIABLE: trapSeverity
            ADDITIONAL-TEXT-VARIABLES: {trapData}
            MANAGEDOBJECT-TABLE: smscCmlog
            MANAGEDOBJECT-DEFAULT: smscAgent"
        ::= 4205


    --
    -- TRAP for table: smscMd
    --
    smscMdTrapOld TRAP-TYPE
        ENTERPRISE  smscAgent
        VARIABLES  {trapNotificationId, trapSeverity, trapData
                , smscMdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 500


    --
    -- TRAP for table: smscMd
    --
    smscMdIndeterminateTrapOld TRAP-TYPE
        ENTERPRISE  smscAgent
        VARIABLES  {trapNotificationId, trapSeverity, trapData
                , smscMdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 5000


    --
    -- TRAP for table: smscMd
    --
    smscMdCriticalTrapOld TRAP-TYPE
        ENTERPRISE  smscAgent
        VARIABLES  {trapNotificationId, trapSeverity, trapData
                , smscMdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 5001


    --
    -- TRAP for table: smscMd
    --
    smscMdMajorTrapOld TRAP-TYPE
        ENTERPRISE  smscAgent
        VARIABLES  {trapNotificationId, trapSeverity, trapData
                , smscMdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 5002


    --
    -- TRAP for table: smscMd
    --
    smscMdMinorTrapOld TRAP-TYPE
        ENTERPRISE  smscAgent
        VARIABLES  {trapNotificationId, trapSeverity, trapData
                , smscMdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 5003


    --
    -- TRAP for table: smscMd
    --
    smscMdWarningTrapOld TRAP-TYPE
        ENTERPRISE  smscAgent
        VARIABLES  {trapNotificationId, trapSeverity, trapData
                , smscMdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 5004


    --
    -- TRAP for table: smscMd
    --
    smscMdClearTrapOld TRAP-TYPE
        ENTERPRISE  smscAgent
        VARIABLES  {trapNotificationId, trapSeverity, trapData
                , smscMdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 5005


    --
    -- TRAP for table: smscAd
    --
    smscAdTrapOld TRAP-TYPE
        ENTERPRISE  smscAgent
        VARIABLES  {trapNotificationId, trapSeverity, trapData
                , smscAdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 501


    --
    -- TRAP for table: smscAd
    --
    smscAdIndeterminateTrapOld TRAP-TYPE
        ENTERPRISE  smscAgent
        VARIABLES  {trapNotificationId, trapSeverity, trapData
                , smscAdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 5010


    --
    -- TRAP for table: smscAd
    --
    smscAdCriticalTrapOld TRAP-TYPE
        ENTERPRISE  smscAgent
        VARIABLES  {trapNotificationId, trapSeverity, trapData
                , smscAdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 5011


    --
    -- TRAP for table: smscAd
    --
    smscAdMajorTrapOld TRAP-TYPE
        ENTERPRISE  smscAgent
        VARIABLES  {trapNotificationId, trapSeverity, trapData
                , smscAdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 5012


    --
    -- TRAP for table: smscAd
    --
    smscAdMinorTrapOld TRAP-TYPE
        ENTERPRISE  smscAgent
        VARIABLES  {trapNotificationId, trapSeverity, trapData
                , smscAdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 5013


    --
    -- TRAP for table: smscAd
    --
    smscAdWarningTrapOld TRAP-TYPE
        ENTERPRISE  smscAgent
        VARIABLES  {trapNotificationId, trapSeverity, trapData
                , smscAdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 5014


    --
    -- TRAP for table: smscAd
    --
    smscAdClearTrapOld TRAP-TYPE
        ENTERPRISE  smscAgent
        VARIABLES  {trapNotificationId, trapSeverity, trapData
                , smscAdName, trapTimeStamp, trapNodeName}
        DESCRIPTION
            "This is the trap definition to handle an SMSC entity events. This
            trap belongs to a specific entityclass indicated in the
            following TeMIP specific clauses.
            NOTIFICATIONID-VARIABLE: trapNotificationId
            SEVERITY-VARIABLE: trapSeverity
            ADDITIONAL-TEXT-VARIABLES: {trapData}
            MANAGEDOBJECT-DEFAULT: smscAgent"
        ::= 5015
    
    --
    -- End of the Obsolete Section
    --

    --
    -- Unknown External Traps received from the SMSC
    --
    smscUnknownExternalTrapTrap TRAP-TYPE
        ENTERPRISE  smscAgent
        VARIABLES  {trapNotificationId, trapSeverity, trapData, smscSmhName, trapTimeStamp, trapNodeName}
        DESCRIPTION
            "Internal status information of the agent which is not known
            NOTIFICATIONID-VARIABLE: trapNotificationId
            SEVERITY-VARIABLE: trapSeverity
            ADDITIONAL-TEXT-VARIABLES: {trapData}
            MANAGEDOBJECT-DEFAULT: smscAgent"
        ::= 999
             
    --
    -- Unknown External Traps received from the SMSC
    --
    smscUnknownExternalIndeterminateTrap TRAP-TYPE
        ENTERPRISE  smscAgent
        VARIABLES  {trapNotificationId, trapSeverity, trapData, smscSmhName, trapTimeStamp, trapNodeName}
        DESCRIPTION
            "Internal status information of the agent which is not known
            NOTIFICATIONID-VARIABLE: trapNotificationId
            SEVERITY-VARIABLE: trapSeverity
            ADDITIONAL-TEXT-VARIABLES: {trapData}
            MANAGEDOBJECT-DEFAULT: smscAgent"
        ::= 9990


    --
    -- Unknown External Traps received from the SMSC
    --
    smscUnknownExternalCriticalTrap TRAP-TYPE
        ENTERPRISE  smscAgent
        VARIABLES  {trapNotificationId, trapSeverity, trapData, smscSmhName, trapTimeStamp, trapNodeName}
        DESCRIPTION
            "Internal status information of the agent which is not known
            NOTIFICATIONID-VARIABLE: trapNotificationId
            SEVERITY-VARIABLE: trapSeverity
            ADDITIONAL-TEXT-VARIABLES: {trapData}
            MANAGEDOBJECT-DEFAULT: smscAgent"
        ::= 9991

    --
    -- Unknown External Traps received from the SMSC
    --
    smscUnknownExternalMajorTrap TRAP-TYPE
        ENTERPRISE  smscAgent
        VARIABLES  {trapNotificationId, trapSeverity, trapData, smscSmhName, trapTimeStamp, trapNodeName}
        DESCRIPTION
            "Internal status information of the agent which is not known
            NOTIFICATIONID-VARIABLE: trapNotificationId
            SEVERITY-VARIABLE: trapSeverity
            ADDITIONAL-TEXT-VARIABLES: {trapData}
            MANAGEDOBJECT-DEFAULT: smscAgent"
        ::= 9992


    --
    -- Unknown External Traps received from the SMSC
    --
    smscUnknownExternalMinorTrap TRAP-TYPE
        ENTERPRISE  smscAgent
        VARIABLES  {trapNotificationId, trapSeverity, trapData, smscSmhName, trapTimeStamp, trapNodeName}
        DESCRIPTION
            "Internal status information of the agent which is not known
            NOTIFICATIONID-VARIABLE: trapNotificationId
            SEVERITY-VARIABLE: trapSeverity
            ADDITIONAL-TEXT-VARIABLES: {trapData}
            MANAGEDOBJECT-DEFAULT: smscAgent"
        ::= 9993

    --
    -- Unknown External Traps received from the SMSC
    --
    smscUnknownExternalWarningTrap TRAP-TYPE
        ENTERPRISE  smscAgent
        VARIABLES  {trapNotificationId, trapSeverity, trapData, smscSmhName, trapTimeStamp, trapNodeName}
        DESCRIPTION
            "Internal status information of the agent which is not known
            NOTIFICATIONID-VARIABLE: trapNotificationId
            SEVERITY-VARIABLE: trapSeverity
            ADDITIONAL-TEXT-VARIABLES: {trapData}
            MANAGEDOBJECT-DEFAULT: smscAgent"
        ::= 9994


    --
    -- Unknown External Traps received from the SMSC
    --
    smscUnknownExternalClearTrap TRAP-TYPE
        ENTERPRISE  smscAgent
        VARIABLES  {trapNotificationId, trapSeverity, trapData, smscSmhName, trapTimeStamp, trapNodeName}
        DESCRIPTION
            "Internal status information of the agent which is not known
            NOTIFICATIONID-VARIABLE: trapNotificationId
            SEVERITY-VARIABLE: trapSeverity
            ADDITIONAL-TEXT-VARIABLES: {trapData}
            MANAGEDOBJECT-DEFAULT: smscAgent"
        ::= 9995
                                
-- ---------------------------------------------
-- LA Data Store BEGIN
-- ---------------------------------------------

smscDataStore   OBJECT IDENTIFIER ::= { smscAgent 14 }

ucpLa           OBJECT IDENTIFIER ::= { smscDataStore 1 }
smppLa          OBJECT IDENTIFIER ::= { smscDataStore 2 }

--
-- UCP LARGE ACCOUNTS
--
    ucpLaTable OBJECT-TYPE
 	SYNTAX          SEQUENCE OF UcpLaEntry
 	MAX-ACCESS      not-accessible
 	STATUS          current
 	DESCRIPTION     "The list/table of UCP Large Accounts of the SMSC."
    ::= { ucpLa  1 }

    UcpLaEntry ::= SEQUENCE 
    {
	ucpLaId         INTEGER,
	ucpLaSessions   INTEGER
    }

    ucpLaEntry OBJECT-TYPE
  	SYNTAX          UcpLaEntry
  	MAX-ACCESS      not-accessible
  	STATUS          current
  	DESCRIPTION     "An entry (row) in the UCP Large Account table."
  	INDEX           { IMPLIED ucpLaId }
    ::= { ucpLaTable 1 }

    ucpLaId OBJECT-TYPE
  	SYNTAX          INTEGER
  	MAX-ACCESS      read-only
  	STATUS          current
  	DESCRIPTION     "Identifies the Large Account."
     ::= { ucpLaEntry 1 }

    ucpLaSessions OBJECT-TYPE
  	SYNTAX          INTEGER
  	MAX-ACCESS      read-only
  	STATUS          current
  	DESCRIPTION     "The number of open Large Account sessions."
     ::= { ucpLaEntry 2 }

--
-- UCP OPERATIONS
--
    ucpOpIdx OBJECT-TYPE
  	SYNTAX          INTEGER {
                            ucpTotRX    ( 1),   ucpTotTX( 2), 
                            ucpUnsuppRX ( 3),   ucp01RX ( 4),
                            ucp01TX     ( 5),   ucp02RX ( 6),   
                            ucp03RX     ( 7),   ucp30RX ( 8),
                            ucp31RX     ( 9),   ucp32RX (10),   
                            ucp33RX     (11),   ucp34TX (12),
                            ucp36TX     (13),   ucp38RX (14),  
                            ucp40RX     (15),   ucp41RX (16), 
                            ucp42TX     (17),   ucp43TX (18),  
                            ucp51RX     (19),   ucp52TX (20),
                            ucp53TX     (21),   ucp54RX (22),  
                            ucp55RX     (23),   ucp56RX (24),
                            ucp57TX     (25),   ucp58TX (26),  
                            ucp60RX     (27),   ucp61RX (28),
                            ucp93RX     (29),   ucp93TX (30)  }

 	MAX-ACCESS      not-accessible
  	STATUS          current
  	DESCRIPTION     "Value List of UCP Operation Types."
     ::= { ucpLa 2 }

--
-- UCP COUNTER TYPES
--
    ucpCntIdx OBJECT-TYPE
  	SYNTAX          INTEGER { ok(1), fail(2), timeout(3) }
 	MAX-ACCESS      not-accessible
  	STATUS          current
  	DESCRIPTION     "Value List of UCP Operation Counter Types."
     ::= { ucpLa 3 }

--
-- UCP LA OPERATION COUNTERS
--
    ucpLaOpCntTable OBJECT-TYPE
 	SYNTAX          SEQUENCE OF UcpLaOpCntEntry
 	MAX-ACCESS      not-accessible
 	STATUS          current
 	DESCRIPTION     "The list/table of UCP Operation Counter Values."
    ::= { ucpLa 4 }

    UcpLaOpCntEntry ::= SEQUENCE 
    {
	ucpLaOpCntValue INTEGER
    }

    ucpLaOpCntEntry OBJECT-TYPE
  	SYNTAX          UcpLaOpCntEntry
  	MAX-ACCESS      not-accessible
  	STATUS          current
  	DESCRIPTION     "An entry (row) in the UCP Operation Counter Table."
  	INDEX           { ucpLaId, ucpOpIdx, ucpCntIdx }
    ::= { ucpLaOpCntTable 1 }

    ucpLaOpCntValue OBJECT-TYPE
  	SYNTAX          INTEGER
  	MAX-ACCESS      read-only
  	STATUS          current
  	DESCRIPTION     "The value of a UCP Operation Counter."
     ::= { ucpLaOpCntEntry 1 }

--
-- SMPP LARGE ACCOUNTS
--
    smppLaTable OBJECT-TYPE
 	SYNTAX          SEQUENCE OF SmppLaEntry
 	MAX-ACCESS      not-accessible
 	STATUS          current
 	DESCRIPTION     "The list/table of SMPP Large Accounts of the SMSC."
    ::= { smppLa  1 }

    SmppLaEntry ::= SEQUENCE 
    {
	smppLaId         INTEGER,
	smppLaSessions   INTEGER
    }

    smppLaEntry OBJECT-TYPE
  	SYNTAX          SmppLaEntry
  	MAX-ACCESS      not-accessible
  	STATUS          current
  	DESCRIPTION     "An entry (row) in the SMPP Large Account table."
  	INDEX           { IMPLIED smppLaId }
    ::= { smppLaTable 1 }

    smppLaId OBJECT-TYPE
  	SYNTAX          INTEGER
  	MAX-ACCESS      read-only
  	STATUS          current
  	DESCRIPTION     "Identifies the Large Account."
     ::= { smppLaEntry 1 }

    smppLaSessions OBJECT-TYPE
  	SYNTAX          INTEGER
  	MAX-ACCESS      read-only
  	STATUS          current
  	DESCRIPTION     "The number of open Large Account sessions."
     ::= { smppLaEntry 2 }

--
-- SMPP OPERATIONS
--
    smppOpIdx OBJECT-TYPE
  	SYNTAX          INTEGER {
                            smppTotRX   ( 1),   smppTotTX   ( 2), 
                            smppUnsuppRX( 3),   bindTranRX  ( 4),
                            bindTranTX  ( 5),   bindRecvRX  ( 6),
                            bindRecvTX  ( 7),   bindTrcvRX  ( 8),
                            bindTrcvTX  ( 9),   outbind     (10),
                            unbindRX    (11),   unbindTX    (12),
                            submitRX    (13),   submitTXisr (14),
                            submitMulti (15),   dataSMRX    (16),   
                            dataSMTX    (17),   deliverTX   (18),   
                            deliverRXisr(19),   query       (20),
                            cancel      (21),   replace     (22),    
                            enqLinkRX   (23),   enqLinkTX   (24),
                            alert       (25) }

  	MAX-ACCESS      not-accessible
  	STATUS          current
  	DESCRIPTION     "Value List of SMPP Operation Types."
     ::= { smppLa 2 }

--
-- SMPP COUNTER TYPES
--
    smppCntIdx OBJECT-TYPE
      	SYNTAX          INTEGER { ok(1), fail(2), timeout(3) }
  	MAX-ACCESS      not-accessible
  	STATUS          current
  	DESCRIPTION     "Value List of SMPP Operation Counter Types."
     ::= { smppLa 3 }

--
-- SMPP LA OPERATION COUNTERS
--
    smppLaOpCntTable OBJECT-TYPE
 	SYNTAX          SEQUENCE OF SmppLaOpCntEntry
 	MAX-ACCESS      not-accessible
 	STATUS          current
 	DESCRIPTION     "The list/table of SMPP Operation Counter Values."
    ::= { smppLa 4 }

    SmppLaOpCntEntry ::= SEQUENCE 
    {
	smppLaOpCntValue INTEGER
    }

    smppLaOpCntEntry OBJECT-TYPE
  	SYNTAX          SmppLaOpCntEntry
  	MAX-ACCESS      not-accessible
  	STATUS          current
  	DESCRIPTION     "An entry (row) in the SMPP Operation Counter Table."
  	INDEX           { smppLaId, smppOpIdx, smppCntIdx }
    ::= { smppLaOpCntTable 1 }

    smppLaOpCntValue OBJECT-TYPE
  	SYNTAX          INTEGER
  	MAX-ACCESS      read-only
  	STATUS          current
  	DESCRIPTION     "The value of a SMPP Operation Counter."
     ::= { smppLaOpCntEntry 1 }

-- ---------------------------------------------
-- LA Data Store END
-- ---------------------------------------------
--
-- Trap for table: smscSmh
--
smscSmhTrap TRAP-TYPE
	ENTERPRISE  smscAgent
	VARIABLES  {trapNotificationId, trapSeverity, trapData,
		smscSmhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSmh
		MANAGEDOBJECT-DEFAULT: smscAgent"
   ::= 	100

--

-- End of definition

--
-- Trap for table: smscSmhIndeterminate
--
smscSmhIndeterminateTrap TRAP-TYPE
	ENTERPRISE  smscAgent
	VARIABLES  {trapNotificationId, trapSeverity, trapData,
		smscSmhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSmhIndeterminate
		MANAGEDOBJECT-DEFAULT: smscAgent"
   ::= 	1000

--

-- End of definition

--
-- Trap for table: smscSmhCritical
--
smscSmhCriticalTrap TRAP-TYPE
	ENTERPRISE  smscAgent
	VARIABLES  {trapNotificationId, trapSeverity, trapData,
		smscSmhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSmhCritical
		MANAGEDOBJECT-DEFAULT: smscAgent"
   ::= 	1001

--

-- End of definition

--
-- Trap for table: smscSmhMajor
--
smscSmhMajorTrap TRAP-TYPE
	ENTERPRISE  smscAgent
	VARIABLES  {trapNotificationId, trapSeverity, trapData,
		smscSmhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSmhMajor
		MANAGEDOBJECT-DEFAULT: smscAgent"
   ::= 	1002

--

-- End of definition

--
-- Trap for table: smscSmhMinor
--
smscSmhMinorTrap TRAP-TYPE
	ENTERPRISE  smscAgent
	VARIABLES  {trapNotificationId, trapSeverity, trapData,
		smscSmhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSmhMinor
		MANAGEDOBJECT-DEFAULT: smscAgent"
   ::= 	1003

--

-- End of definition

--
-- Trap for table: smscSmhWarning
--
smscSmhWarningTrap TRAP-TYPE
	ENTERPRISE  smscAgent
	VARIABLES  {trapNotificationId, trapSeverity, trapData,
		smscSmhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSmhWarning
		MANAGEDOBJECT-DEFAULT: smscAgent"
   ::= 	1004

--

-- End of definition

--
-- Trap for table: smscSmhClear
--
smscSmhClearTrap TRAP-TYPE
	ENTERPRISE  smscAgent
	VARIABLES  {trapNotificationId, trapSeverity, trapData,
		smscSmhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSmhClear
		MANAGEDOBJECT-DEFAULT: smscAgent"
   ::= 	1005

--

-- End of definition

--
-- Trap for table: smscSiwmenu
--
smscSiwmenuTrap TRAP-TYPE
	ENTERPRISE  smscAgent
	VARIABLES  {trapNotificationId, trapSeverity, trapData,
		smscSiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwmenu
		MANAGEDOBJECT-DEFAULT: smscAgent"
   ::= 	200

--

-- End of definition

--
-- Trap for table: smscSiwmenuIndeterminate
--
smscSiwmenuIndeterminateTrap TRAP-TYPE
	ENTERPRISE  smscAgent
	VARIABLES  {trapNotificationId, trapSeverity, trapData,
		smscSiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwmenuIndeterminate
		MANAGEDOBJECT-DEFAULT: smscAgent"
   ::= 	2000

--

-- End of definition

--
-- Trap for table: smscSiwmenuCritical
--
smscSiwmenuCriticalTrap TRAP-TYPE
	ENTERPRISE  smscAgent
	VARIABLES  {trapNotificationId, trapSeverity, trapData,
		smscSiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwmenuCritical
		MANAGEDOBJECT-DEFAULT: smscAgent"
   ::= 	2001

--

-- End of definition

--
-- Trap for table: smscSiwmenuMajor
--
smscSiwmenuMajorTrap TRAP-TYPE
	ENTERPRISE  smscAgent
	VARIABLES  {trapNotificationId, trapSeverity, trapData,
		smscSiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwmenuMajor
		MANAGEDOBJECT-DEFAULT: smscAgent"
   ::= 	2002

--

-- End of definition

--
-- Trap for table: smscSiwmenuMinor
--
smscSiwmenuMinorTrap TRAP-TYPE
	ENTERPRISE  smscAgent
	VARIABLES  {trapNotificationId, trapSeverity, trapData,
		smscSiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwmenuMinor
		MANAGEDOBJECT-DEFAULT: smscAgent"
   ::= 	2003

--

-- End of definition

--
-- Trap for table: smscSiwmenuWarning
--
smscSiwmenuWarningTrap TRAP-TYPE
	ENTERPRISE  smscAgent
	VARIABLES  {trapNotificationId, trapSeverity, trapData,
		smscSiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwmenuWarning
		MANAGEDOBJECT-DEFAULT: smscAgent"
   ::= 	2004

--

-- End of definition

--
-- Trap for table: smscSiwmenuClear
--
smscSiwmenuClearTrap TRAP-TYPE
	ENTERPRISE  smscAgent
	VARIABLES  {trapNotificationId, trapSeverity, trapData,
		smscSiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwmenuClear
		MANAGEDOBJECT-DEFAULT: smscAgent"
   ::= 	2005

--

-- End of definition

--
-- Trap for table: smscSiwpc
--
smscSiwpcTrap TRAP-TYPE
	ENTERPRISE  smscAgent
	VARIABLES  {trapNotificationId, trapSeverity, trapData,
		smscSiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwpc
		MANAGEDOBJECT-DEFAULT: smscAgent"
   ::= 	201

--

-- End of definition

--
-- Trap for table: smscSiwpcIndeterminate
--
smscSiwpcIndeterminateTrap TRAP-TYPE
	ENTERPRISE  smscAgent
	VARIABLES  {trapNotificationId, trapSeverity, trapData,
		smscSiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwpcIndeterminate
		MANAGEDOBJECT-DEFAULT: smscAgent"
   ::= 	2010

--

-- End of definition

--
-- Trap for table: smscSiwpcCritical
--
smscSiwpcCriticalTrap TRAP-TYPE
	ENTERPRISE  smscAgent
	VARIABLES  {trapNotificationId, trapSeverity, trapData,
		smscSiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwpcCritical
		MANAGEDOBJECT-DEFAULT: smscAgent"
   ::= 	2011

--

-- End of definition

--
-- Trap for table: smscSiwpcMajor
--
smscSiwpcMajorTrap TRAP-TYPE
	ENTERPRISE  smscAgent
	VARIABLES  {trapNotificationId, trapSeverity, trapData,
		smscSiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwpcMajor
		MANAGEDOBJECT-DEFAULT: smscAgent"
   ::= 	2012

--

-- End of definition

--
-- Trap for table: smscSiwpcMinor
--
smscSiwpcMinorTrap TRAP-TYPE
	ENTERPRISE  smscAgent
	VARIABLES  {trapNotificationId, trapSeverity, trapData,
		smscSiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwpcMinor
		MANAGEDOBJECT-DEFAULT: smscAgent"
   ::= 	2013

--

-- End of definition

--
-- Trap for table: smscSiwpcWarning
--
smscSiwpcWarningTrap TRAP-TYPE
	ENTERPRISE  smscAgent
	VARIABLES  {trapNotificationId, trapSeverity, trapData,
		smscSiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwpcWarning
		MANAGEDOBJECT-DEFAULT: smscAgent"
   ::= 	2014

--

-- End of definition

--
-- Trap for table: smscSiwpcClear
--
smscSiwpcClearTrap TRAP-TYPE
	ENTERPRISE  smscAgent
	VARIABLES  {trapNotificationId, trapSeverity, trapData,
		smscSiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwpcClear
		MANAGEDOBJECT-DEFAULT: smscAgent"
   ::= 	2015

--

-- End of definition

--
-- Trap for table: smscSiwplmn
--
smscSiwplmnTrap TRAP-TYPE
	ENTERPRISE  smscAgent
	VARIABLES  {trapNotificationId, trapSeverity, trapData,
		smscSiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwplmn
		MANAGEDOBJECT-DEFAULT: smscAgent"
   ::= 	202

--

-- End of definition

--
-- Trap for table: smscSiwplmnIndeterminate
--
smscSiwplmnIndeterminateTrap TRAP-TYPE
	ENTERPRISE  smscAgent
	VARIABLES  {trapNotificationId, trapSeverity, trapData,
		smscSiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwplmnIndeterminate
		MANAGEDOBJECT-DEFAULT: smscAgent"
   ::= 	2020

--

-- End of definition

--
-- Trap for table: smscSiwplmnCritical
--
smscSiwplmnCriticalTrap TRAP-TYPE
	ENTERPRISE  smscAgent
	VARIABLES  {trapNotificationId, trapSeverity, trapData,
		smscSiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwplmnCritical
		MANAGEDOBJECT-DEFAULT: smscAgent"
   ::= 	2021

--

-- End of definition

--
-- Trap for table: smscSiwplmnMajor
--
smscSiwplmnMajorTrap TRAP-TYPE
	ENTERPRISE  smscAgent
	VARIABLES  {trapNotificationId, trapSeverity, trapData,
		smscSiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwplmnMajor
		MANAGEDOBJECT-DEFAULT: smscAgent"
   ::= 	2022

--

-- End of definition

--
-- Trap for table: smscSiwplmnMinor
--
smscSiwplmnMinorTrap TRAP-TYPE
	ENTERPRISE  smscAgent
	VARIABLES  {trapNotificationId, trapSeverity, trapData,
		smscSiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwplmnMinor
		MANAGEDOBJECT-DEFAULT: smscAgent"
   ::= 	2023

--

-- End of definition

--
-- Trap for table: smscSiwplmnWarning
--
smscSiwplmnWarningTrap TRAP-TYPE
	ENTERPRISE  smscAgent
	VARIABLES  {trapNotificationId, trapSeverity, trapData,
		smscSiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwplmnWarning
		MANAGEDOBJECT-DEFAULT: smscAgent"
   ::= 	2024

--

-- End of definition

--
-- Trap for table: smscSiwplmnClear
--
smscSiwplmnClearTrap TRAP-TYPE
	ENTERPRISE  smscAgent
	VARIABLES  {trapNotificationId, trapSeverity, trapData,
		smscSiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwplmnClear
		MANAGEDOBJECT-DEFAULT: smscAgent"
   ::= 	2025

--

-- End of definition

--
-- Trap for table: smscSiwimport
--
smscSiwimportTrap TRAP-TYPE
	ENTERPRISE  smscAgent
	VARIABLES  {trapNotificationId, trapSeverity, trapData,
		smscSiwimportName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwimport
		MANAGEDOBJECT-DEFAULT: smscAgent"
   ::= 	203

--

-- End of definition

--
-- Trap for table: smscSiwimportIndeterminate
--
smscSiwimportIndeterminateTrap TRAP-TYPE
	ENTERPRISE  smscAgent
	VARIABLES  {trapNotificationId, trapSeverity, trapData,
		smscSiwimportName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwimportIndeterminate
		MANAGEDOBJECT-DEFAULT: smscAgent"
   ::= 	2030

--

-- End of definition

--
-- Trap for table: smscSiwimportCritical
--
smscSiwimportCriticalTrap TRAP-TYPE
	ENTERPRISE  smscAgent
	VARIABLES  {trapNotificationId, trapSeverity, trapData,
		smscSiwimportName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwimportCritical
		MANAGEDOBJECT-DEFAULT: smscAgent"
   ::= 	2031

--

-- End of definition

--
-- Trap for table: smscSiwimportMajor
--
smscSiwimportMajorTrap TRAP-TYPE
	ENTERPRISE  smscAgent
	VARIABLES  {trapNotificationId, trapSeverity, trapData,
		smscSiwimportName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwimportMajor
		MANAGEDOBJECT-DEFAULT: smscAgent"
   ::= 	2032

--

-- End of definition

--
-- Trap for table: smscSiwimportMinor
--
smscSiwimportMinorTrap TRAP-TYPE
	ENTERPRISE  smscAgent
	VARIABLES  {trapNotificationId, trapSeverity, trapData,
		smscSiwimportName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwimportMinor
		MANAGEDOBJECT-DEFAULT: smscAgent"
   ::= 	2033

--

-- End of definition

--
-- Trap for table: smscSiwimportWarning
--
smscSiwimportWarningTrap TRAP-TYPE
	ENTERPRISE  smscAgent
	VARIABLES  {trapNotificationId, trapSeverity, trapData,
		smscSiwimportName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwimportWarning
		MANAGEDOBJECT-DEFAULT: smscAgent"
   ::= 	2034

--

-- End of definition

--
-- Trap for table: smscSiwimportClear
--
smscSiwimportClearTrap TRAP-TYPE
	ENTERPRISE  smscAgent
	VARIABLES  {trapNotificationId, trapSeverity, trapData,
		smscSiwimportName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwimportClear
		MANAGEDOBJECT-DEFAULT: smscAgent"
   ::= 	2035

--

-- End of definition

--
-- Trap for table: smscSiwvms
--
smscSiwvmsTrap TRAP-TYPE
	ENTERPRISE  smscAgent
	VARIABLES  {trapNotificationId, trapSeverity, trapData,
		smscSiwvmsName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvms
		MANAGEDOBJECT-DEFAULT: smscAgent"
   ::= 	204

--

-- End of definition

--
-- Trap for table: smscSiwvmsIndeterminate
--
smscSiwvmsIndeterminateTrap TRAP-TYPE
	ENTERPRISE  smscAgent
	VARIABLES  {trapNotificationId, trapSeverity, trapData,
		smscSiwvmsName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvmsIndeterminate
		MANAGEDOBJECT-DEFAULT: smscAgent"
   ::= 	2040

--

-- End of definition

--
-- Trap for table: smscSiwvmsCritical
--
smscSiwvmsCriticalTrap TRAP-TYPE
	ENTERPRISE  smscAgent
	VARIABLES  {trapNotificationId, trapSeverity, trapData,
		smscSiwvmsName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvmsCritical
		MANAGEDOBJECT-DEFAULT: smscAgent"
   ::= 	2041

--

-- End of definition

--
-- Trap for table: smscSiwvmsMajor
--
smscSiwvmsMajorTrap TRAP-TYPE
	ENTERPRISE  smscAgent
	VARIABLES  {trapNotificationId, trapSeverity, trapData,
		smscSiwvmsName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvmsMajor
		MANAGEDOBJECT-DEFAULT: smscAgent"
   ::= 	2042

--

-- End of definition

--
-- Trap for table: smscSiwvmsMinor
--
smscSiwvmsMinorTrap TRAP-TYPE
	ENTERPRISE  smscAgent
	VARIABLES  {trapNotificationId, trapSeverity, trapData,
		smscSiwvmsName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvmsMinor
		MANAGEDOBJECT-DEFAULT: smscAgent"
   ::= 	2043

--

-- End of definition

--
-- Trap for table: smscSiwvmsWarning
--
smscSiwvmsWarningTrap TRAP-TYPE
	ENTERPRISE  smscAgent
	VARIABLES  {trapNotificationId, trapSeverity, trapData,
		smscSiwvmsName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvmsWarning
		MANAGEDOBJECT-DEFAULT: smscAgent"
   ::= 	2044

--

-- End of definition

--
-- Trap for table: smscSiwvmsClear
--
smscSiwvmsClearTrap TRAP-TYPE
	ENTERPRISE  smscAgent
	VARIABLES  {trapNotificationId, trapSeverity, trapData,
		smscSiwvmsName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvmsClear
		MANAGEDOBJECT-DEFAULT: smscAgent"
   ::= 	2045

--

-- End of definition

--
-- Trap for table: smscSiwivr
--
smscSiwivrTrap TRAP-TYPE
	ENTERPRISE  smscAgent
	VARIABLES  {trapNotificationId, trapSeverity, trapData,
		smscSiwivrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwivr
		MANAGEDOBJECT-DEFAULT: smscAgent"
   ::= 	205

--

-- End of definition

--
-- Trap for table: smscSiwivrIndeterminate
--
smscSiwivrIndeterminateTrap TRAP-TYPE
	ENTERPRISE  smscAgent
	VARIABLES  {trapNotificationId, trapSeverity, trapData,
		smscSiwivrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwivrIndeterminate
		MANAGEDOBJECT-DEFAULT: smscAgent"
   ::= 	2050

--

-- End of definition

--
-- Trap for table: smscSiwivrCritical
--
smscSiwivrCriticalTrap TRAP-TYPE
	ENTERPRISE  smscAgent
	VARIABLES  {trapNotificationId, trapSeverity, trapData,
		smscSiwivrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwivrCritical
		MANAGEDOBJECT-DEFAULT: smscAgent"
   ::= 	2051

--

-- End of definition

--
-- Trap for table: smscSiwivrMajor
--
smscSiwivrMajorTrap TRAP-TYPE
	ENTERPRISE  smscAgent
	VARIABLES  {trapNotificationId, trapSeverity, trapData,
		smscSiwivrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwivrMajor
		MANAGEDOBJECT-DEFAULT: smscAgent"
   ::= 	2052

--

-- End of definition

--
-- Trap for table: smscSiwivrMinor
--
smscSiwivrMinorTrap TRAP-TYPE
	ENTERPRISE  smscAgent
	VARIABLES  {trapNotificationId, trapSeverity, trapData,
		smscSiwivrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwivrMinor
		MANAGEDOBJECT-DEFAULT: smscAgent"
   ::= 	2053

--

-- End of definition

--
-- Trap for table: smscSiwivrWarning
--
smscSiwivrWarningTrap TRAP-TYPE
	ENTERPRISE  smscAgent
	VARIABLES  {trapNotificationId, trapSeverity, trapData,
		smscSiwivrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwivrWarning
		MANAGEDOBJECT-DEFAULT: smscAgent"
   ::= 	2054

--

-- End of definition

--
-- Trap for table: smscSiwivrClear
--
smscSiwivrClearTrap TRAP-TYPE
	ENTERPRISE  smscAgent
	VARIABLES  {trapNotificationId, trapSeverity, trapData,
		smscSiwivrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwivrClear
		MANAGEDOBJECT-DEFAULT: smscAgent"
   ::= 	2055

--

-- End of definition

--
-- Trap for table: smscSiwvsmpp
--
smscSiwvsmppTrap TRAP-TYPE
	ENTERPRISE  smscAgent
	VARIABLES  {trapNotificationId, trapSeverity, trapData,
		smscSiwvsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvsmpp
		MANAGEDOBJECT-DEFAULT: smscAgent"
   ::= 	206

--

-- End of definition

--
-- Trap for table: smscSiwvsmppIndeterminate
--
smscSiwvsmppIndeterminateTrap TRAP-TYPE
	ENTERPRISE  smscAgent
	VARIABLES  {trapNotificationId, trapSeverity, trapData,
		smscSiwvsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvsmppIndeterminate
		MANAGEDOBJECT-DEFAULT: smscAgent"
   ::= 	2060

--

-- End of definition

--
-- Trap for table: smscSiwvsmppCritical
--
smscSiwvsmppCriticalTrap TRAP-TYPE
	ENTERPRISE  smscAgent
	VARIABLES  {trapNotificationId, trapSeverity, trapData,
		smscSiwvsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvsmppCritical
		MANAGEDOBJECT-DEFAULT: smscAgent"
   ::= 	2061

--

-- End of definition

--
-- Trap for table: smscSiwvsmppMajor
--
smscSiwvsmppMajorTrap TRAP-TYPE
	ENTERPRISE  smscAgent
	VARIABLES  {trapNotificationId, trapSeverity, trapData,
		smscSiwvsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvsmppMajor
		MANAGEDOBJECT-DEFAULT: smscAgent"
   ::= 	2062

--

-- End of definition

--
-- Trap for table: smscSiwvsmppMinor
--
smscSiwvsmppMinorTrap TRAP-TYPE
	ENTERPRISE  smscAgent
	VARIABLES  {trapNotificationId, trapSeverity, trapData,
		smscSiwvsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvsmppMinor
		MANAGEDOBJECT-DEFAULT: smscAgent"
   ::= 	2063

--

-- End of definition

--
-- Trap for table: smscSiwvsmppWarning
--
smscSiwvsmppWarningTrap TRAP-TYPE
	ENTERPRISE  smscAgent
	VARIABLES  {trapNotificationId, trapSeverity, trapData,
		smscSiwvsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvsmppWarning
		MANAGEDOBJECT-DEFAULT: smscAgent"
   ::= 	2064

--

-- End of definition

--
-- Trap for table: smscSiwvsmppClear
--
smscSiwvsmppClearTrap TRAP-TYPE
	ENTERPRISE  smscAgent
	VARIABLES  {trapNotificationId, trapSeverity, trapData,
		smscSiwvsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwvsmppClear
		MANAGEDOBJECT-DEFAULT: smscAgent"
   ::= 	2065

--

-- End of definition

--
-- Trap for table: smscSiwtap
--
smscSiwtapTrap TRAP-TYPE
	ENTERPRISE  smscAgent
	VARIABLES  {trapNotificationId, trapSeverity, trapData,
		smscSiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtap
		MANAGEDOBJECT-DEFAULT: smscAgent"
   ::= 	207

--

-- End of definition

--
-- Trap for table: smscSiwtapIndeterminate
--
smscSiwtapIndeterminateTrap TRAP-TYPE
	ENTERPRISE  smscAgent
	VARIABLES  {trapNotificationId, trapSeverity, trapData,
		smscSiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtapIndeterminate
		MANAGEDOBJECT-DEFAULT: smscAgent"
   ::= 	2070

--

-- End of definition

--
-- Trap for table: smscSiwtapCritical
--
smscSiwtapCriticalTrap TRAP-TYPE
	ENTERPRISE  smscAgent
	VARIABLES  {trapNotificationId, trapSeverity, trapData,
		smscSiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtapCritical
		MANAGEDOBJECT-DEFAULT: smscAgent"
   ::= 	2071

--

-- End of definition

--
-- Trap for table: smscSiwtapMajor
--
smscSiwtapMajorTrap TRAP-TYPE
	ENTERPRISE  smscAgent
	VARIABLES  {trapNotificationId, trapSeverity, trapData,
		smscSiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtapMajor
		MANAGEDOBJECT-DEFAULT: smscAgent"
   ::= 	2072

--

-- End of definition

--
-- Trap for table: smscSiwtapMinor
--
smscSiwtapMinorTrap TRAP-TYPE
	ENTERPRISE  smscAgent
	VARIABLES  {trapNotificationId, trapSeverity, trapData,
		smscSiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtapMinor
		MANAGEDOBJECT-DEFAULT: smscAgent"
   ::= 	2073

--

-- End of definition

--
-- Trap for table: smscSiwtapWarning
--
smscSiwtapWarningTrap TRAP-TYPE
	ENTERPRISE  smscAgent
	VARIABLES  {trapNotificationId, trapSeverity, trapData,
		smscSiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtapWarning
		MANAGEDOBJECT-DEFAULT: smscAgent"
   ::= 	2074

--

-- End of definition

--
-- Trap for table: smscSiwtapClear
--
smscSiwtapClearTrap TRAP-TYPE
	ENTERPRISE  smscAgent
	VARIABLES  {trapNotificationId, trapSeverity, trapData,
		smscSiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtapClear
		MANAGEDOBJECT-DEFAULT: smscAgent"
   ::= 	2075

--

-- End of definition

--
-- Trap for table: smscSiwsmpp
--
smscSiwsmppTrap TRAP-TYPE
	ENTERPRISE  smscAgent
	VARIABLES  {trapNotificationId, trapSeverity, trapData,
		smscSiwsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwsmpp
		MANAGEDOBJECT-DEFAULT: smscAgent"
   ::= 	208

--

-- End of definition

--
-- Trap for table: smscSiwsmppIndeterminate
--
smscSiwsmppIndeterminateTrap TRAP-TYPE
	ENTERPRISE  smscAgent
	VARIABLES  {trapNotificationId, trapSeverity, trapData,
		smscSiwsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwsmppIndeterminate
		MANAGEDOBJECT-DEFAULT: smscAgent"
   ::= 	2080

--

-- End of definition

--
-- Trap for table: smscSiwsmppCritical
--
smscSiwsmppCriticalTrap TRAP-TYPE
	ENTERPRISE  smscAgent
	VARIABLES  {trapNotificationId, trapSeverity, trapData,
		smscSiwsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwsmppCritical
		MANAGEDOBJECT-DEFAULT: smscAgent"
   ::= 	2081

--

-- End of definition

--
-- Trap for table: smscSiwsmppMajor
--
smscSiwsmppMajorTrap TRAP-TYPE
	ENTERPRISE  smscAgent
	VARIABLES  {trapNotificationId, trapSeverity, trapData,
		smscSiwsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwsmppMajor
		MANAGEDOBJECT-DEFAULT: smscAgent"
   ::= 	2082

--

-- End of definition

--
-- Trap for table: smscSiwsmppMinor
--
smscSiwsmppMinorTrap TRAP-TYPE
	ENTERPRISE  smscAgent
	VARIABLES  {trapNotificationId, trapSeverity, trapData,
		smscSiwsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwsmppMinor
		MANAGEDOBJECT-DEFAULT: smscAgent"
   ::= 	2083

--

-- End of definition

--
-- Trap for table: smscSiwsmppWarning
--
smscSiwsmppWarningTrap TRAP-TYPE
	ENTERPRISE  smscAgent
	VARIABLES  {trapNotificationId, trapSeverity, trapData,
		smscSiwsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwsmppWarning
		MANAGEDOBJECT-DEFAULT: smscAgent"
   ::= 	2084

--

-- End of definition

--
-- Trap for table: smscSiwsmppClear
--
smscSiwsmppClearTrap TRAP-TYPE
	ENTERPRISE  smscAgent
	VARIABLES  {trapNotificationId, trapSeverity, trapData,
		smscSiwsmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwsmppClear
		MANAGEDOBJECT-DEFAULT: smscAgent"
   ::= 	2085

--

-- End of definition

--
-- Trap for table: smscSiwois
--
smscSiwoisTrap TRAP-TYPE
	ENTERPRISE  smscAgent
	VARIABLES  {trapNotificationId, trapSeverity, trapData,
		smscSiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwois
		MANAGEDOBJECT-DEFAULT: smscAgent"
   ::= 	209

--

-- End of definition

--
-- Trap for table: smscSiwoisIndeterminate
--
smscSiwoisIndeterminateTrap TRAP-TYPE
	ENTERPRISE  smscAgent
	VARIABLES  {trapNotificationId, trapSeverity, trapData,
		smscSiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwoisIndeterminate
		MANAGEDOBJECT-DEFAULT: smscAgent"
   ::= 	2090

--

-- End of definition

--
-- Trap for table: smscSiwoisCritical
--
smscSiwoisCriticalTrap TRAP-TYPE
	ENTERPRISE  smscAgent
	VARIABLES  {trapNotificationId, trapSeverity, trapData,
		smscSiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwoisCritical
		MANAGEDOBJECT-DEFAULT: smscAgent"
   ::= 	2091

--

-- End of definition

--
-- Trap for table: smscSiwoisMajor
--
smscSiwoisMajorTrap TRAP-TYPE
	ENTERPRISE  smscAgent
	VARIABLES  {trapNotificationId, trapSeverity, trapData,
		smscSiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwoisMajor
		MANAGEDOBJECT-DEFAULT: smscAgent"
   ::= 	2092

--

-- End of definition

--
-- Trap for table: smscSiwoisMinor
--
smscSiwoisMinorTrap TRAP-TYPE
	ENTERPRISE  smscAgent
	VARIABLES  {trapNotificationId, trapSeverity, trapData,
		smscSiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwoisMinor
		MANAGEDOBJECT-DEFAULT: smscAgent"
   ::= 	2093

--

-- End of definition

--
-- Trap for table: smscSiwoisWarning
--
smscSiwoisWarningTrap TRAP-TYPE
	ENTERPRISE  smscAgent
	VARIABLES  {trapNotificationId, trapSeverity, trapData,
		smscSiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwoisWarning
		MANAGEDOBJECT-DEFAULT: smscAgent"
   ::= 	2094

--

-- End of definition

--
-- Trap for table: smscSiwoisClear
--
smscSiwoisClearTrap TRAP-TYPE
	ENTERPRISE  smscAgent
	VARIABLES  {trapNotificationId, trapSeverity, trapData,
		smscSiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwoisClear
		MANAGEDOBJECT-DEFAULT: smscAgent"
   ::= 	2095

--

-- End of definition

--
-- Trap for table: smscSiwcdma
--
smscSiwcdmaTrap TRAP-TYPE
	ENTERPRISE  smscAgent
	VARIABLES  {trapNotificationId, trapSeverity, trapData,
		smscSiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwcdma
		MANAGEDOBJECT-DEFAULT: smscAgent"
   ::= 	210

--

-- End of definition

--
-- Trap for table: smscSiwcdmaIndeterminate
--
smscSiwcdmaIndeterminateTrap TRAP-TYPE
	ENTERPRISE  smscAgent
	VARIABLES  {trapNotificationId, trapSeverity, trapData,
		smscSiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwcdmaIndeterminate
		MANAGEDOBJECT-DEFAULT: smscAgent"
   ::= 	2100

--

-- End of definition

--
-- Trap for table: smscSiwcdmaCritical
--
smscSiwcdmaCriticalTrap TRAP-TYPE
	ENTERPRISE  smscAgent
	VARIABLES  {trapNotificationId, trapSeverity, trapData,
		smscSiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwcdmaCritical
		MANAGEDOBJECT-DEFAULT: smscAgent"
   ::= 	2101

--

-- End of definition

--
-- Trap for table: smscSiwcdmaMajor
--
smscSiwcdmaMajorTrap TRAP-TYPE
	ENTERPRISE  smscAgent
	VARIABLES  {trapNotificationId, trapSeverity, trapData,
		smscSiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwcdmaMajor
		MANAGEDOBJECT-DEFAULT: smscAgent"
   ::= 	2102

--

-- End of definition

--
-- Trap for table: smscSiwcdmaMinor
--
smscSiwcdmaMinorTrap TRAP-TYPE
	ENTERPRISE  smscAgent
	VARIABLES  {trapNotificationId, trapSeverity, trapData,
		smscSiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwcdmaMinor
		MANAGEDOBJECT-DEFAULT: smscAgent"
   ::= 	2103

--

-- End of definition

--
-- Trap for table: smscSiwcdmaWarning
--
smscSiwcdmaWarningTrap TRAP-TYPE
	ENTERPRISE  smscAgent
	VARIABLES  {trapNotificationId, trapSeverity, trapData,
		smscSiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwcdmaWarning
		MANAGEDOBJECT-DEFAULT: smscAgent"
   ::= 	2104

--

-- End of definition

--
-- Trap for table: smscSiwcdmaClear
--
smscSiwcdmaClearTrap TRAP-TYPE
	ENTERPRISE  smscAgent
	VARIABLES  {trapNotificationId, trapSeverity, trapData,
		smscSiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwcdmaClear
		MANAGEDOBJECT-DEFAULT: smscAgent"
   ::= 	2105

--

-- End of definition

--
-- Trap for table: smscSiwota
--
smscSiwotaTrap TRAP-TYPE
	ENTERPRISE  smscAgent
	VARIABLES  {trapNotificationId, trapSeverity, trapData,
		smscSiwotaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwota
		MANAGEDOBJECT-DEFAULT: smscAgent"
   ::= 	211

--

-- End of definition

--
-- Trap for table: smscSiwotaIndeterminate
--
smscSiwotaIndeterminateTrap TRAP-TYPE
	ENTERPRISE  smscAgent
	VARIABLES  {trapNotificationId, trapSeverity, trapData,
		smscSiwotaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwotaIndeterminate
		MANAGEDOBJECT-DEFAULT: smscAgent"
   ::= 	2110

--

-- End of definition

--
-- Trap for table: smscSiwotaCritical
--
smscSiwotaCriticalTrap TRAP-TYPE
	ENTERPRISE  smscAgent
	VARIABLES  {trapNotificationId, trapSeverity, trapData,
		smscSiwotaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwotaCritical
		MANAGEDOBJECT-DEFAULT: smscAgent"
   ::= 	2111

--

-- End of definition

--
-- Trap for table: smscSiwotaMajor
--
smscSiwotaMajorTrap TRAP-TYPE
	ENTERPRISE  smscAgent
	VARIABLES  {trapNotificationId, trapSeverity, trapData,
		smscSiwotaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwotaMajor
		MANAGEDOBJECT-DEFAULT: smscAgent"
   ::= 	2112

--

-- End of definition

--
-- Trap for table: smscSiwotaMinor
--
smscSiwotaMinorTrap TRAP-TYPE
	ENTERPRISE  smscAgent
	VARIABLES  {trapNotificationId, trapSeverity, trapData,
		smscSiwotaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwotaMinor
		MANAGEDOBJECT-DEFAULT: smscAgent"
   ::= 	2113

--

-- End of definition

--
-- Trap for table: smscSiwotaWarning
--
smscSiwotaWarningTrap TRAP-TYPE
	ENTERPRISE  smscAgent
	VARIABLES  {trapNotificationId, trapSeverity, trapData,
		smscSiwotaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwotaWarning
		MANAGEDOBJECT-DEFAULT: smscAgent"
   ::= 	2114

--

-- End of definition

--
-- Trap for table: smscSiwotaClear
--
smscSiwotaClearTrap TRAP-TYPE
	ENTERPRISE  smscAgent
	VARIABLES  {trapNotificationId, trapSeverity, trapData,
		smscSiwotaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwotaClear
		MANAGEDOBJECT-DEFAULT: smscAgent"
   ::= 	2115

--

-- End of definition

--
-- Trap for table: smscSiwtdma
--
smscSiwtdmaTrap TRAP-TYPE
	ENTERPRISE  smscAgent
	VARIABLES  {trapNotificationId, trapSeverity, trapData,
		smscSiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtdma
		MANAGEDOBJECT-DEFAULT: smscAgent"
   ::= 	212

--

-- End of definition

--
-- Trap for table: smscSiwtdmaIndeterminate
--
smscSiwtdmaIndeterminateTrap TRAP-TYPE
	ENTERPRISE  smscAgent
	VARIABLES  {trapNotificationId, trapSeverity, trapData,
		smscSiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtdmaIndeterminate
		MANAGEDOBJECT-DEFAULT: smscAgent"
   ::= 	2120

--

-- End of definition

--
-- Trap for table: smscSiwtdmaCritical
--
smscSiwtdmaCriticalTrap TRAP-TYPE
	ENTERPRISE  smscAgent
	VARIABLES  {trapNotificationId, trapSeverity, trapData,
		smscSiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtdmaCritical
		MANAGEDOBJECT-DEFAULT: smscAgent"
   ::= 	2121

--

-- End of definition

--
-- Trap for table: smscSiwtdmaMajor
--
smscSiwtdmaMajorTrap TRAP-TYPE
	ENTERPRISE  smscAgent
	VARIABLES  {trapNotificationId, trapSeverity, trapData,
		smscSiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtdmaMajor
		MANAGEDOBJECT-DEFAULT: smscAgent"
   ::= 	2122

--

-- End of definition

--
-- Trap for table: smscSiwtdmaMinor
--
smscSiwtdmaMinorTrap TRAP-TYPE
	ENTERPRISE  smscAgent
	VARIABLES  {trapNotificationId, trapSeverity, trapData,
		smscSiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtdmaMinor
		MANAGEDOBJECT-DEFAULT: smscAgent"
   ::= 	2123

--

-- End of definition

--
-- Trap for table: smscSiwtdmaWarning
--
smscSiwtdmaWarningTrap TRAP-TYPE
	ENTERPRISE  smscAgent
	VARIABLES  {trapNotificationId, trapSeverity, trapData,
		smscSiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtdmaWarning
		MANAGEDOBJECT-DEFAULT: smscAgent"
   ::= 	2124

--

-- End of definition

--
-- Trap for table: smscSiwtdmaClear
--
smscSiwtdmaClearTrap TRAP-TYPE
	ENTERPRISE  smscAgent
	VARIABLES  {trapNotificationId, trapSeverity, trapData,
		smscSiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSiwtdmaClear
		MANAGEDOBJECT-DEFAULT: smscAgent"
   ::= 	2125

--

-- End of definition

--
-- Trap for table: smscDiwmenu
--
smscDiwmenuTrap TRAP-TYPE
	ENTERPRISE  smscAgent
	VARIABLES  {trapNotificationId, trapSeverity, trapData,
		smscDiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwmenu
		MANAGEDOBJECT-DEFAULT: smscAgent"
   ::= 	300

--

-- End of definition

--
-- Trap for table: smscDiwmenuIndeterminate
--
smscDiwmenuIndeterminateTrap TRAP-TYPE
	ENTERPRISE  smscAgent
	VARIABLES  {trapNotificationId, trapSeverity, trapData,
		smscDiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwmenuIndeterminate
		MANAGEDOBJECT-DEFAULT: smscAgent"
   ::= 	3000

--

-- End of definition

--
-- Trap for table: smscDiwmenuCritical
--
smscDiwmenuCriticalTrap TRAP-TYPE
	ENTERPRISE  smscAgent
	VARIABLES  {trapNotificationId, trapSeverity, trapData,
		smscDiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwmenuCritical
		MANAGEDOBJECT-DEFAULT: smscAgent"
   ::= 	3001

--

-- End of definition

--
-- Trap for table: smscDiwmenuMajor
--
smscDiwmenuMajorTrap TRAP-TYPE
	ENTERPRISE  smscAgent
	VARIABLES  {trapNotificationId, trapSeverity, trapData,
		smscDiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwmenuMajor
		MANAGEDOBJECT-DEFAULT: smscAgent"
   ::= 	3002

--

-- End of definition

--
-- Trap for table: smscDiwmenuMinor
--
smscDiwmenuMinorTrap TRAP-TYPE
	ENTERPRISE  smscAgent
	VARIABLES  {trapNotificationId, trapSeverity, trapData,
		smscDiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwmenuMinor
		MANAGEDOBJECT-DEFAULT: smscAgent"
   ::= 	3003

--

-- End of definition

--
-- Trap for table: smscDiwmenuWarning
--
smscDiwmenuWarningTrap TRAP-TYPE
	ENTERPRISE  smscAgent
	VARIABLES  {trapNotificationId, trapSeverity, trapData,
		smscDiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwmenuWarning
		MANAGEDOBJECT-DEFAULT: smscAgent"
   ::= 	3004

--

-- End of definition

--
-- Trap for table: smscDiwmenuClear
--
smscDiwmenuClearTrap TRAP-TYPE
	ENTERPRISE  smscAgent
	VARIABLES  {trapNotificationId, trapSeverity, trapData,
		smscDiwmenuName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwmenuClear
		MANAGEDOBJECT-DEFAULT: smscAgent"
   ::= 	3005

--

-- End of definition

--
-- Trap for table: smscDiwpc
--
smscDiwpcTrap TRAP-TYPE
	ENTERPRISE  smscAgent
	VARIABLES  {trapNotificationId, trapSeverity, trapData,
		smscDiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwpc
		MANAGEDOBJECT-DEFAULT: smscAgent"
   ::= 	301

--

-- End of definition

--
-- Trap for table: smscDiwpcIndeterminate
--
smscDiwpcIndeterminateTrap TRAP-TYPE
	ENTERPRISE  smscAgent
	VARIABLES  {trapNotificationId, trapSeverity, trapData,
		smscDiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwpcIndeterminate
		MANAGEDOBJECT-DEFAULT: smscAgent"
   ::= 	3010

--

-- End of definition

--
-- Trap for table: smscDiwpcCritical
--
smscDiwpcCriticalTrap TRAP-TYPE
	ENTERPRISE  smscAgent
	VARIABLES  {trapNotificationId, trapSeverity, trapData,
		smscDiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwpcCritical
		MANAGEDOBJECT-DEFAULT: smscAgent"
   ::= 	3011

--

-- End of definition

--
-- Trap for table: smscDiwpcMajor
--
smscDiwpcMajorTrap TRAP-TYPE
	ENTERPRISE  smscAgent
	VARIABLES  {trapNotificationId, trapSeverity, trapData,
		smscDiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwpcMajor
		MANAGEDOBJECT-DEFAULT: smscAgent"
   ::= 	3012

--

-- End of definition

--
-- Trap for table: smscDiwpcMinor
--
smscDiwpcMinorTrap TRAP-TYPE
	ENTERPRISE  smscAgent
	VARIABLES  {trapNotificationId, trapSeverity, trapData,
		smscDiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwpcMinor
		MANAGEDOBJECT-DEFAULT: smscAgent"
   ::= 	3013

--

-- End of definition

--
-- Trap for table: smscDiwpcWarning
--
smscDiwpcWarningTrap TRAP-TYPE
	ENTERPRISE  smscAgent
	VARIABLES  {trapNotificationId, trapSeverity, trapData,
		smscDiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwpcWarning
		MANAGEDOBJECT-DEFAULT: smscAgent"
   ::= 	3014

--

-- End of definition

--
-- Trap for table: smscDiwpcClear
--
smscDiwpcClearTrap TRAP-TYPE
	ENTERPRISE  smscAgent
	VARIABLES  {trapNotificationId, trapSeverity, trapData,
		smscDiwpcName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwpcClear
		MANAGEDOBJECT-DEFAULT: smscAgent"
   ::= 	3015

--

-- End of definition

--
-- Trap for table: smscDiwplmn
--
smscDiwplmnTrap TRAP-TYPE
	ENTERPRISE  smscAgent
	VARIABLES  {trapNotificationId, trapSeverity, trapData,
		smscDiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwplmn
		MANAGEDOBJECT-DEFAULT: smscAgent"
   ::= 	302

--

-- End of definition

--
-- Trap for table: smscDiwplmnIndeterminate
--
smscDiwplmnIndeterminateTrap TRAP-TYPE
	ENTERPRISE  smscAgent
	VARIABLES  {trapNotificationId, trapSeverity, trapData,
		smscDiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwplmnIndeterminate
		MANAGEDOBJECT-DEFAULT: smscAgent"
   ::= 	3020

--

-- End of definition

--
-- Trap for table: smscDiwplmnCritical
--
smscDiwplmnCriticalTrap TRAP-TYPE
	ENTERPRISE  smscAgent
	VARIABLES  {trapNotificationId, trapSeverity, trapData,
		smscDiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwplmnCritical
		MANAGEDOBJECT-DEFAULT: smscAgent"
   ::= 	3021

--

-- End of definition

--
-- Trap for table: smscDiwplmnMajor
--
smscDiwplmnMajorTrap TRAP-TYPE
	ENTERPRISE  smscAgent
	VARIABLES  {trapNotificationId, trapSeverity, trapData,
		smscDiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwplmnMajor
		MANAGEDOBJECT-DEFAULT: smscAgent"
   ::= 	3022

--

-- End of definition

--
-- Trap for table: smscDiwplmnMinor
--
smscDiwplmnMinorTrap TRAP-TYPE
	ENTERPRISE  smscAgent
	VARIABLES  {trapNotificationId, trapSeverity, trapData,
		smscDiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwplmnMinor
		MANAGEDOBJECT-DEFAULT: smscAgent"
   ::= 	3023

--

-- End of definition

--
-- Trap for table: smscDiwplmnWarning
--
smscDiwplmnWarningTrap TRAP-TYPE
	ENTERPRISE  smscAgent
	VARIABLES  {trapNotificationId, trapSeverity, trapData,
		smscDiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwplmnWarning
		MANAGEDOBJECT-DEFAULT: smscAgent"
   ::= 	3024

--

-- End of definition

--
-- Trap for table: smscDiwplmnClear
--
smscDiwplmnClearTrap TRAP-TYPE
	ENTERPRISE  smscAgent
	VARIABLES  {trapNotificationId, trapSeverity, trapData,
		smscDiwplmnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwplmnClear
		MANAGEDOBJECT-DEFAULT: smscAgent"
   ::= 	3025

--

-- End of definition

--
-- Trap for table: smscDiwfax
--
smscDiwfaxTrap TRAP-TYPE
	ENTERPRISE  smscAgent
	VARIABLES  {trapNotificationId, trapSeverity, trapData,
		smscDiwfaxName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwfax
		MANAGEDOBJECT-DEFAULT: smscAgent"
   ::= 	303

--

-- End of definition

--
-- Trap for table: smscDiwfaxIndeterminate
--
smscDiwfaxIndeterminateTrap TRAP-TYPE
	ENTERPRISE  smscAgent
	VARIABLES  {trapNotificationId, trapSeverity, trapData,
		smscDiwfaxName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwfaxIndeterminate
		MANAGEDOBJECT-DEFAULT: smscAgent"
   ::= 	3030

--

-- End of definition

--
-- Trap for table: smscDiwfaxCritical
--
smscDiwfaxCriticalTrap TRAP-TYPE
	ENTERPRISE  smscAgent
	VARIABLES  {trapNotificationId, trapSeverity, trapData,
		smscDiwfaxName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwfaxCritical
		MANAGEDOBJECT-DEFAULT: smscAgent"
   ::= 	3031

--

-- End of definition

--
-- Trap for table: smscDiwfaxMajor
--
smscDiwfaxMajorTrap TRAP-TYPE
	ENTERPRISE  smscAgent
	VARIABLES  {trapNotificationId, trapSeverity, trapData,
		smscDiwfaxName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwfaxMajor
		MANAGEDOBJECT-DEFAULT: smscAgent"
   ::= 	3032

--

-- End of definition

--
-- Trap for table: smscDiwfaxMinor
--
smscDiwfaxMinorTrap TRAP-TYPE
	ENTERPRISE  smscAgent
	VARIABLES  {trapNotificationId, trapSeverity, trapData,
		smscDiwfaxName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwfaxMinor
		MANAGEDOBJECT-DEFAULT: smscAgent"
   ::= 	3033

--

-- End of definition

--
-- Trap for table: smscDiwfaxWarning
--
smscDiwfaxWarningTrap TRAP-TYPE
	ENTERPRISE  smscAgent
	VARIABLES  {trapNotificationId, trapSeverity, trapData,
		smscDiwfaxName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwfaxWarning
		MANAGEDOBJECT-DEFAULT: smscAgent"
   ::= 	3034

--

-- End of definition

--
-- Trap for table: smscDiwfaxClear
--
smscDiwfaxClearTrap TRAP-TYPE
	ENTERPRISE  smscAgent
	VARIABLES  {trapNotificationId, trapSeverity, trapData,
		smscDiwfaxName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwfaxClear
		MANAGEDOBJECT-DEFAULT: smscAgent"
   ::= 	3035

--

-- End of definition

--
-- Trap for table: smscDiwermes
--
smscDiwermesTrap TRAP-TYPE
	ENTERPRISE  smscAgent
	VARIABLES  {trapNotificationId, trapSeverity, trapData,
		smscDiwermesName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwermes
		MANAGEDOBJECT-DEFAULT: smscAgent"
   ::= 	304

--

-- End of definition

--
-- Trap for table: smscDiwermesIndeterminate
--
smscDiwermesIndeterminateTrap TRAP-TYPE
	ENTERPRISE  smscAgent
	VARIABLES  {trapNotificationId, trapSeverity, trapData,
		smscDiwermesName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwermesIndeterminate
		MANAGEDOBJECT-DEFAULT: smscAgent"
   ::= 	3040

--

-- End of definition

--
-- Trap for table: smscDiwermesCritical
--
smscDiwermesCriticalTrap TRAP-TYPE
	ENTERPRISE  smscAgent
	VARIABLES  {trapNotificationId, trapSeverity, trapData,
		smscDiwermesName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwermesCritical
		MANAGEDOBJECT-DEFAULT: smscAgent"
   ::= 	3041

--

-- End of definition

--
-- Trap for table: smscDiwermesMajor
--
smscDiwermesMajorTrap TRAP-TYPE
	ENTERPRISE  smscAgent
	VARIABLES  {trapNotificationId, trapSeverity, trapData,
		smscDiwermesName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwermesMajor
		MANAGEDOBJECT-DEFAULT: smscAgent"
   ::= 	3042

--

-- End of definition

--
-- Trap for table: smscDiwermesMinor
--
smscDiwermesMinorTrap TRAP-TYPE
	ENTERPRISE  smscAgent
	VARIABLES  {trapNotificationId, trapSeverity, trapData,
		smscDiwermesName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwermesMinor
		MANAGEDOBJECT-DEFAULT: smscAgent"
   ::= 	3043

--

-- End of definition

--
-- Trap for table: smscDiwermesWarning
--
smscDiwermesWarningTrap TRAP-TYPE
	ENTERPRISE  smscAgent
	VARIABLES  {trapNotificationId, trapSeverity, trapData,
		smscDiwermesName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwermesWarning
		MANAGEDOBJECT-DEFAULT: smscAgent"
   ::= 	3044

--

-- End of definition

--
-- Trap for table: smscDiwermesClear
--
smscDiwermesClearTrap TRAP-TYPE
	ENTERPRISE  smscAgent
	VARIABLES  {trapNotificationId, trapSeverity, trapData,
		smscDiwermesName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwermesClear
		MANAGEDOBJECT-DEFAULT: smscAgent"
   ::= 	3045

--

-- End of definition

--
-- Trap for table: smscDiwtap
--
smscDiwtapTrap TRAP-TYPE
	ENTERPRISE  smscAgent
	VARIABLES  {trapNotificationId, trapSeverity, trapData,
		smscDiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtap
		MANAGEDOBJECT-DEFAULT: smscAgent"
   ::= 	305

--

-- End of definition

--
-- Trap for table: smscDiwtapIndeterminate
--
smscDiwtapIndeterminateTrap TRAP-TYPE
	ENTERPRISE  smscAgent
	VARIABLES  {trapNotificationId, trapSeverity, trapData,
		smscDiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtapIndeterminate
		MANAGEDOBJECT-DEFAULT: smscAgent"
   ::= 	3050

--

-- End of definition

--
-- Trap for table: smscDiwtapCritical
--
smscDiwtapCriticalTrap TRAP-TYPE
	ENTERPRISE  smscAgent
	VARIABLES  {trapNotificationId, trapSeverity, trapData,
		smscDiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtapCritical
		MANAGEDOBJECT-DEFAULT: smscAgent"
   ::= 	3051

--

-- End of definition

--
-- Trap for table: smscDiwtapMajor
--
smscDiwtapMajorTrap TRAP-TYPE
	ENTERPRISE  smscAgent
	VARIABLES  {trapNotificationId, trapSeverity, trapData,
		smscDiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtapMajor
		MANAGEDOBJECT-DEFAULT: smscAgent"
   ::= 	3052

--

-- End of definition

--
-- Trap for table: smscDiwtapMinor
--
smscDiwtapMinorTrap TRAP-TYPE
	ENTERPRISE  smscAgent
	VARIABLES  {trapNotificationId, trapSeverity, trapData,
		smscDiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtapMinor
		MANAGEDOBJECT-DEFAULT: smscAgent"
   ::= 	3053

--

-- End of definition

--
-- Trap for table: smscDiwtapWarning
--
smscDiwtapWarningTrap TRAP-TYPE
	ENTERPRISE  smscAgent
	VARIABLES  {trapNotificationId, trapSeverity, trapData,
		smscDiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtapWarning
		MANAGEDOBJECT-DEFAULT: smscAgent"
   ::= 	3054

--

-- End of definition

--
-- Trap for table: smscDiwtapClear
--
smscDiwtapClearTrap TRAP-TYPE
	ENTERPRISE  smscAgent
	VARIABLES  {trapNotificationId, trapSeverity, trapData,
		smscDiwtapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtapClear
		MANAGEDOBJECT-DEFAULT: smscAgent"
   ::= 	3055

--

-- End of definition

--
-- Trap for table: smscDiwois
--
smscDiwoisTrap TRAP-TYPE
	ENTERPRISE  smscAgent
	VARIABLES  {trapNotificationId, trapSeverity, trapData,
		smscDiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwois
		MANAGEDOBJECT-DEFAULT: smscAgent"
   ::= 	306

--

-- End of definition

--
-- Trap for table: smscDiwoisIndeterminate
--
smscDiwoisIndeterminateTrap TRAP-TYPE
	ENTERPRISE  smscAgent
	VARIABLES  {trapNotificationId, trapSeverity, trapData,
		smscDiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwoisIndeterminate
		MANAGEDOBJECT-DEFAULT: smscAgent"
   ::= 	3060

--

-- End of definition

--
-- Trap for table: smscDiwoisCritical
--
smscDiwoisCriticalTrap TRAP-TYPE
	ENTERPRISE  smscAgent
	VARIABLES  {trapNotificationId, trapSeverity, trapData,
		smscDiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwoisCritical
		MANAGEDOBJECT-DEFAULT: smscAgent"
   ::= 	3061

--

-- End of definition

--
-- Trap for table: smscDiwoisMajor
--
smscDiwoisMajorTrap TRAP-TYPE
	ENTERPRISE  smscAgent
	VARIABLES  {trapNotificationId, trapSeverity, trapData,
		smscDiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwoisMajor
		MANAGEDOBJECT-DEFAULT: smscAgent"
   ::= 	3062

--

-- End of definition

--
-- Trap for table: smscDiwoisMinor
--
smscDiwoisMinorTrap TRAP-TYPE
	ENTERPRISE  smscAgent
	VARIABLES  {trapNotificationId, trapSeverity, trapData,
		smscDiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwoisMinor
		MANAGEDOBJECT-DEFAULT: smscAgent"
   ::= 	3063

--

-- End of definition

--
-- Trap for table: smscDiwoisWarning
--
smscDiwoisWarningTrap TRAP-TYPE
	ENTERPRISE  smscAgent
	VARIABLES  {trapNotificationId, trapSeverity, trapData,
		smscDiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwoisWarning
		MANAGEDOBJECT-DEFAULT: smscAgent"
   ::= 	3064

--

-- End of definition

--
-- Trap for table: smscDiwoisClear
--
smscDiwoisClearTrap TRAP-TYPE
	ENTERPRISE  smscAgent
	VARIABLES  {trapNotificationId, trapSeverity, trapData,
		smscDiwoisName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwoisClear
		MANAGEDOBJECT-DEFAULT: smscAgent"
   ::= 	3065

--

-- End of definition

--
-- Trap for table: smscDiwcdma
--
smscDiwcdmaTrap TRAP-TYPE
	ENTERPRISE  smscAgent
	VARIABLES  {trapNotificationId, trapSeverity, trapData,
		smscDiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwcdma
		MANAGEDOBJECT-DEFAULT: smscAgent"
   ::= 	307

--

-- End of definition

--
-- Trap for table: smscDiwcdmaIndeterminate
--
smscDiwcdmaIndeterminateTrap TRAP-TYPE
	ENTERPRISE  smscAgent
	VARIABLES  {trapNotificationId, trapSeverity, trapData,
		smscDiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwcdmaIndeterminate
		MANAGEDOBJECT-DEFAULT: smscAgent"
   ::= 	3070

--

-- End of definition

--
-- Trap for table: smscDiwcdmaCritical
--
smscDiwcdmaCriticalTrap TRAP-TYPE
	ENTERPRISE  smscAgent
	VARIABLES  {trapNotificationId, trapSeverity, trapData,
		smscDiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwcdmaCritical
		MANAGEDOBJECT-DEFAULT: smscAgent"
   ::= 	3071

--

-- End of definition

--
-- Trap for table: smscDiwcdmaMajor
--
smscDiwcdmaMajorTrap TRAP-TYPE
	ENTERPRISE  smscAgent
	VARIABLES  {trapNotificationId, trapSeverity, trapData,
		smscDiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwcdmaMajor
		MANAGEDOBJECT-DEFAULT: smscAgent"
   ::= 	3072

--

-- End of definition

--
-- Trap for table: smscDiwcdmaMinor
--
smscDiwcdmaMinorTrap TRAP-TYPE
	ENTERPRISE  smscAgent
	VARIABLES  {trapNotificationId, trapSeverity, trapData,
		smscDiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwcdmaMinor
		MANAGEDOBJECT-DEFAULT: smscAgent"
   ::= 	3073

--

-- End of definition

--
-- Trap for table: smscDiwcdmaWarning
--
smscDiwcdmaWarningTrap TRAP-TYPE
	ENTERPRISE  smscAgent
	VARIABLES  {trapNotificationId, trapSeverity, trapData,
		smscDiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwcdmaWarning
		MANAGEDOBJECT-DEFAULT: smscAgent"
   ::= 	3074

--

-- End of definition

--
-- Trap for table: smscDiwcdmaClear
--
smscDiwcdmaClearTrap TRAP-TYPE
	ENTERPRISE  smscAgent
	VARIABLES  {trapNotificationId, trapSeverity, trapData,
		smscDiwcdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwcdmaClear
		MANAGEDOBJECT-DEFAULT: smscAgent"
   ::= 	3075

--

-- End of definition

--
-- Trap for table: smscDiwsmtp
--
smscDiwsmtpTrap TRAP-TYPE
	ENTERPRISE  smscAgent
	VARIABLES  {trapNotificationId, trapSeverity, trapData,
		smscDiwsmtpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwsmtp
		MANAGEDOBJECT-DEFAULT: smscAgent"
   ::= 	308

--

-- End of definition

--
-- Trap for table: smscDiwsmtpIndeterminate
--
smscDiwsmtpIndeterminateTrap TRAP-TYPE
	ENTERPRISE  smscAgent
	VARIABLES  {trapNotificationId, trapSeverity, trapData,
		smscDiwsmtpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwsmtpIndeterminate
		MANAGEDOBJECT-DEFAULT: smscAgent"
   ::= 	3080

--

-- End of definition

--
-- Trap for table: smscDiwsmtpCritical
--
smscDiwsmtpCriticalTrap TRAP-TYPE
	ENTERPRISE  smscAgent
	VARIABLES  {trapNotificationId, trapSeverity, trapData,
		smscDiwsmtpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwsmtpCritical
		MANAGEDOBJECT-DEFAULT: smscAgent"
   ::= 	3081

--

-- End of definition

--
-- Trap for table: smscDiwsmtpMajor
--
smscDiwsmtpMajorTrap TRAP-TYPE
	ENTERPRISE  smscAgent
	VARIABLES  {trapNotificationId, trapSeverity, trapData,
		smscDiwsmtpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwsmtpMajor
		MANAGEDOBJECT-DEFAULT: smscAgent"
   ::= 	3082

--

-- End of definition

--
-- Trap for table: smscDiwsmtpMinor
--
smscDiwsmtpMinorTrap TRAP-TYPE
	ENTERPRISE  smscAgent
	VARIABLES  {trapNotificationId, trapSeverity, trapData,
		smscDiwsmtpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwsmtpMinor
		MANAGEDOBJECT-DEFAULT: smscAgent"
   ::= 	3083

--

-- End of definition

--
-- Trap for table: smscDiwsmtpWarning
--
smscDiwsmtpWarningTrap TRAP-TYPE
	ENTERPRISE  smscAgent
	VARIABLES  {trapNotificationId, trapSeverity, trapData,
		smscDiwsmtpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwsmtpWarning
		MANAGEDOBJECT-DEFAULT: smscAgent"
   ::= 	3084

--

-- End of definition

--
-- Trap for table: smscDiwsmtpClear
--
smscDiwsmtpClearTrap TRAP-TYPE
	ENTERPRISE  smscAgent
	VARIABLES  {trapNotificationId, trapSeverity, trapData,
		smscDiwsmtpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwsmtpClear
		MANAGEDOBJECT-DEFAULT: smscAgent"
   ::= 	3085

--

-- End of definition

--
-- Trap for table: smscDiwtdma
--
smscDiwtdmaTrap TRAP-TYPE
	ENTERPRISE  smscAgent
	VARIABLES  {trapNotificationId, trapSeverity, trapData,
		smscDiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtdma
		MANAGEDOBJECT-DEFAULT: smscAgent"
   ::= 	309

--

-- End of definition

--
-- Trap for table: smscDiwtdmaIndeterminate
--
smscDiwtdmaIndeterminateTrap TRAP-TYPE
	ENTERPRISE  smscAgent
	VARIABLES  {trapNotificationId, trapSeverity, trapData,
		smscDiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtdmaIndeterminate
		MANAGEDOBJECT-DEFAULT: smscAgent"
   ::= 	3090

--

-- End of definition

--
-- Trap for table: smscDiwtdmaCritical
--
smscDiwtdmaCriticalTrap TRAP-TYPE
	ENTERPRISE  smscAgent
	VARIABLES  {trapNotificationId, trapSeverity, trapData,
		smscDiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtdmaCritical
		MANAGEDOBJECT-DEFAULT: smscAgent"
   ::= 	3091

--

-- End of definition

--
-- Trap for table: smscDiwtdmaMajor
--
smscDiwtdmaMajorTrap TRAP-TYPE
	ENTERPRISE  smscAgent
	VARIABLES  {trapNotificationId, trapSeverity, trapData,
		smscDiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtdmaMajor
		MANAGEDOBJECT-DEFAULT: smscAgent"
   ::= 	3092

--

-- End of definition

--
-- Trap for table: smscDiwtdmaMinor
--
smscDiwtdmaMinorTrap TRAP-TYPE
	ENTERPRISE  smscAgent
	VARIABLES  {trapNotificationId, trapSeverity, trapData,
		smscDiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtdmaMinor
		MANAGEDOBJECT-DEFAULT: smscAgent"
   ::= 	3093

--

-- End of definition

--
-- Trap for table: smscDiwtdmaWarning
--
smscDiwtdmaWarningTrap TRAP-TYPE
	ENTERPRISE  smscAgent
	VARIABLES  {trapNotificationId, trapSeverity, trapData,
		smscDiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtdmaWarning
		MANAGEDOBJECT-DEFAULT: smscAgent"
   ::= 	3094

--

-- End of definition

--
-- Trap for table: smscDiwtdmaClear
--
smscDiwtdmaClearTrap TRAP-TYPE
	ENTERPRISE  smscAgent
	VARIABLES  {trapNotificationId, trapSeverity, trapData,
		smscDiwtdmaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDiwtdmaClear
		MANAGEDOBJECT-DEFAULT: smscAgent"
   ::= 	3095

--

-- End of definition

--
-- Trap for table: smscEnum
--
smscEnumTrap TRAP-TYPE
	ENTERPRISE  smscAgent
	VARIABLES  {trapNotificationId, trapSeverity, trapData,
		smscEnumName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEnum
		MANAGEDOBJECT-DEFAULT: smscAgent"
   ::= 	310

--

-- End of definition

--
-- Trap for table: smscEnumIndeterminate
--
smscEnumIndeterminateTrap TRAP-TYPE
	ENTERPRISE  smscAgent
	VARIABLES  {trapNotificationId, trapSeverity, trapData,
		smscEnumName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEnumIndeterminate
		MANAGEDOBJECT-DEFAULT: smscAgent"
   ::= 	3100

--

-- End of definition

--
-- Trap for table: smscEnumCritical
--
smscEnumCriticalTrap TRAP-TYPE
	ENTERPRISE  smscAgent
	VARIABLES  {trapNotificationId, trapSeverity, trapData,
		smscEnumName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEnumCritical
		MANAGEDOBJECT-DEFAULT: smscAgent"
   ::= 	3101

--

-- End of definition

--
-- Trap for table: smscEnumMajor
--
smscEnumMajorTrap TRAP-TYPE
	ENTERPRISE  smscAgent
	VARIABLES  {trapNotificationId, trapSeverity, trapData,
		smscEnumName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEnumMajor
		MANAGEDOBJECT-DEFAULT: smscAgent"
   ::= 	3102

--

-- End of definition

--
-- Trap for table: smscEnumMinor
--
smscEnumMinorTrap TRAP-TYPE
	ENTERPRISE  smscAgent
	VARIABLES  {trapNotificationId, trapSeverity, trapData,
		smscEnumName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEnumMinor
		MANAGEDOBJECT-DEFAULT: smscAgent"
   ::= 	3103

--

-- End of definition

--
-- Trap for table: smscEnumWarning
--
smscEnumWarningTrap TRAP-TYPE
	ENTERPRISE  smscAgent
	VARIABLES  {trapNotificationId, trapSeverity, trapData,
		smscEnumName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEnumWarning
		MANAGEDOBJECT-DEFAULT: smscAgent"
   ::= 	3104

--

-- End of definition

--
-- Trap for table: smscEnumClear
--
smscEnumClearTrap TRAP-TYPE
	ENTERPRISE  smscAgent
	VARIABLES  {trapNotificationId, trapSeverity, trapData,
		smscEnumName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEnumClear
		MANAGEDOBJECT-DEFAULT: smscAgent"
   ::= 	3105

--

-- End of definition

--
-- Trap for table: smscX25
--
smscX25Trap TRAP-TYPE
	ENTERPRISE  smscAgent
	VARIABLES  {trapNotificationId, trapSeverity, trapData,
		smscX25Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX25
		MANAGEDOBJECT-DEFAULT: smscAgent"
   ::= 	600

--

-- End of definition

--
-- Trap for table: smscX25Indeterminate
--
smscX25IndeterminateTrap TRAP-TYPE
	ENTERPRISE  smscAgent
	VARIABLES  {trapNotificationId, trapSeverity, trapData,
		smscX25Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX25Indeterminate
		MANAGEDOBJECT-DEFAULT: smscAgent"
   ::= 	6000

--

-- End of definition

--
-- Trap for table: smscX25Critical
--
smscX25CriticalTrap TRAP-TYPE
	ENTERPRISE  smscAgent
	VARIABLES  {trapNotificationId, trapSeverity, trapData,
		smscX25Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX25Critical
		MANAGEDOBJECT-DEFAULT: smscAgent"
   ::= 	6001

--

-- End of definition

--
-- Trap for table: smscX25Major
--
smscX25MajorTrap TRAP-TYPE
	ENTERPRISE  smscAgent
	VARIABLES  {trapNotificationId, trapSeverity, trapData,
		smscX25Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX25Major
		MANAGEDOBJECT-DEFAULT: smscAgent"
   ::= 	6002

--

-- End of definition

--
-- Trap for table: smscX25Minor
--
smscX25MinorTrap TRAP-TYPE
	ENTERPRISE  smscAgent
	VARIABLES  {trapNotificationId, trapSeverity, trapData,
		smscX25Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX25Minor
		MANAGEDOBJECT-DEFAULT: smscAgent"
   ::= 	6003

--

-- End of definition

--
-- Trap for table: smscX25Warning
--
smscX25WarningTrap TRAP-TYPE
	ENTERPRISE  smscAgent
	VARIABLES  {trapNotificationId, trapSeverity, trapData,
		smscX25Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX25Warning
		MANAGEDOBJECT-DEFAULT: smscAgent"
   ::= 	6004

--

-- End of definition

--
-- Trap for table: smscX25Clear
--
smscX25ClearTrap TRAP-TYPE
	ENTERPRISE  smscAgent
	VARIABLES  {trapNotificationId, trapSeverity, trapData,
		smscX25Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX25Clear
		MANAGEDOBJECT-DEFAULT: smscAgent"
   ::= 	6005

--

-- End of definition

--
-- Trap for table: smscTcp
--
smscTcpTrap TRAP-TYPE
	ENTERPRISE  smscAgent
	VARIABLES  {trapNotificationId, trapSeverity, trapData,
		smscTcpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTcp
		MANAGEDOBJECT-DEFAULT: smscAgent"
   ::= 	601

--

-- End of definition

--
-- Trap for table: smscTcpIndeterminate
--
smscTcpIndeterminateTrap TRAP-TYPE
	ENTERPRISE  smscAgent
	VARIABLES  {trapNotificationId, trapSeverity, trapData,
		smscTcpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTcpIndeterminate
		MANAGEDOBJECT-DEFAULT: smscAgent"
   ::= 	6010

--

-- End of definition

--
-- Trap for table: smscTcpCritical
--
smscTcpCriticalTrap TRAP-TYPE
	ENTERPRISE  smscAgent
	VARIABLES  {trapNotificationId, trapSeverity, trapData,
		smscTcpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTcpCritical
		MANAGEDOBJECT-DEFAULT: smscAgent"
   ::= 	6011

--

-- End of definition

--
-- Trap for table: smscTcpMajor
--
smscTcpMajorTrap TRAP-TYPE
	ENTERPRISE  smscAgent
	VARIABLES  {trapNotificationId, trapSeverity, trapData,
		smscTcpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTcpMajor
		MANAGEDOBJECT-DEFAULT: smscAgent"
   ::= 	6012

--

-- End of definition

--
-- Trap for table: smscTcpMinor
--
smscTcpMinorTrap TRAP-TYPE
	ENTERPRISE  smscAgent
	VARIABLES  {trapNotificationId, trapSeverity, trapData,
		smscTcpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTcpMinor
		MANAGEDOBJECT-DEFAULT: smscAgent"
   ::= 	6013

--

-- End of definition

--
-- Trap for table: smscTcpWarning
--
smscTcpWarningTrap TRAP-TYPE
	ENTERPRISE  smscAgent
	VARIABLES  {trapNotificationId, trapSeverity, trapData,
		smscTcpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTcpWarning
		MANAGEDOBJECT-DEFAULT: smscAgent"
   ::= 	6014

--

-- End of definition

--
-- Trap for table: smscTcpClear
--
smscTcpClearTrap TRAP-TYPE
	ENTERPRISE  smscAgent
	VARIABLES  {trapNotificationId, trapSeverity, trapData,
		smscTcpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTcpClear
		MANAGEDOBJECT-DEFAULT: smscAgent"
   ::= 	6015

--

-- End of definition

--
-- Trap for table: smscX29
--
smscX29Trap TRAP-TYPE
	ENTERPRISE  smscAgent
	VARIABLES  {trapNotificationId, trapSeverity, trapData,
		smscX29Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX29
		MANAGEDOBJECT-DEFAULT: smscAgent"
   ::= 	602

--

-- End of definition

--
-- Trap for table: smscX29Indeterminate
--
smscX29IndeterminateTrap TRAP-TYPE
	ENTERPRISE  smscAgent
	VARIABLES  {trapNotificationId, trapSeverity, trapData,
		smscX29Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX29Indeterminate
		MANAGEDOBJECT-DEFAULT: smscAgent"
   ::= 	6020

--

-- End of definition

--
-- Trap for table: smscX29Critical
--
smscX29CriticalTrap TRAP-TYPE
	ENTERPRISE  smscAgent
	VARIABLES  {trapNotificationId, trapSeverity, trapData,
		smscX29Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX29Critical
		MANAGEDOBJECT-DEFAULT: smscAgent"
   ::= 	6021

--

-- End of definition

--
-- Trap for table: smscX29Major
--
smscX29MajorTrap TRAP-TYPE
	ENTERPRISE  smscAgent
	VARIABLES  {trapNotificationId, trapSeverity, trapData,
		smscX29Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX29Major
		MANAGEDOBJECT-DEFAULT: smscAgent"
   ::= 	6022

--

-- End of definition

--
-- Trap for table: smscX29Minor
--
smscX29MinorTrap TRAP-TYPE
	ENTERPRISE  smscAgent
	VARIABLES  {trapNotificationId, trapSeverity, trapData,
		smscX29Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX29Minor
		MANAGEDOBJECT-DEFAULT: smscAgent"
   ::= 	6023

--

-- End of definition

--
-- Trap for table: smscX29Warning
--
smscX29WarningTrap TRAP-TYPE
	ENTERPRISE  smscAgent
	VARIABLES  {trapNotificationId, trapSeverity, trapData,
		smscX29Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX29Warning
		MANAGEDOBJECT-DEFAULT: smscAgent"
   ::= 	6024

--

-- End of definition

--
-- Trap for table: smscX29Clear
--
smscX29ClearTrap TRAP-TYPE
	ENTERPRISE  smscAgent
	VARIABLES  {trapNotificationId, trapSeverity, trapData,
		smscX29Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscX29Clear
		MANAGEDOBJECT-DEFAULT: smscAgent"
   ::= 	6025

--

-- End of definition

--
-- Trap for table: smscEmap
--
smscEmapTrap TRAP-TYPE
	ENTERPRISE  smscAgent
	VARIABLES  {trapNotificationId, trapSeverity, trapData,
		smscEmapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEmap
		MANAGEDOBJECT-DEFAULT: smscAgent"
   ::= 	603

--

-- End of definition

--
-- Trap for table: smscEmapIndeterminate
--
smscEmapIndeterminateTrap TRAP-TYPE
	ENTERPRISE  smscAgent
	VARIABLES  {trapNotificationId, trapSeverity, trapData,
		smscEmapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEmapIndeterminate
		MANAGEDOBJECT-DEFAULT: smscAgent"
   ::= 	6030

--

-- End of definition

--
-- Trap for table: smscEmapCritical
--
smscEmapCriticalTrap TRAP-TYPE
	ENTERPRISE  smscAgent
	VARIABLES  {trapNotificationId, trapSeverity, trapData,
		smscEmapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEmapCritical
		MANAGEDOBJECT-DEFAULT: smscAgent"
   ::= 	6031

--

-- End of definition

--
-- Trap for table: smscEmapMajor
--
smscEmapMajorTrap TRAP-TYPE
	ENTERPRISE  smscAgent
	VARIABLES  {trapNotificationId, trapSeverity, trapData,
		smscEmapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEmapMajor
		MANAGEDOBJECT-DEFAULT: smscAgent"
   ::= 	6032

--

-- End of definition

--
-- Trap for table: smscEmapMinor
--
smscEmapMinorTrap TRAP-TYPE
	ENTERPRISE  smscAgent
	VARIABLES  {trapNotificationId, trapSeverity, trapData,
		smscEmapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEmapMinor
		MANAGEDOBJECT-DEFAULT: smscAgent"
   ::= 	6033

--

-- End of definition

--
-- Trap for table: smscEmapWarning
--
smscEmapWarningTrap TRAP-TYPE
	ENTERPRISE  smscAgent
	VARIABLES  {trapNotificationId, trapSeverity, trapData,
		smscEmapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEmapWarning
		MANAGEDOBJECT-DEFAULT: smscAgent"
   ::= 	6034

--

-- End of definition

--
-- Trap for table: smscEmapClear
--
smscEmapClearTrap TRAP-TYPE
	ENTERPRISE  smscAgent
	VARIABLES  {trapNotificationId, trapSeverity, trapData,
		smscEmapName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEmapClear
		MANAGEDOBJECT-DEFAULT: smscAgent"
   ::= 	6035

--

-- End of definition

--
-- Trap for table: smscPstna
--
smscPstnaTrap TRAP-TYPE
	ENTERPRISE  smscAgent
	VARIABLES  {trapNotificationId, trapSeverity, trapData,
		smscPstnaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPstna
		MANAGEDOBJECT-DEFAULT: smscAgent"
   ::= 	604

--

-- End of definition

--
-- Trap for table: smscPstnaIndeterminate
--
smscPstnaIndeterminateTrap TRAP-TYPE
	ENTERPRISE  smscAgent
	VARIABLES  {trapNotificationId, trapSeverity, trapData,
		smscPstnaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPstnaIndeterminate
		MANAGEDOBJECT-DEFAULT: smscAgent"
   ::= 	6040

--

-- End of definition

--
-- Trap for table: smscPstnaCritical
--
smscPstnaCriticalTrap TRAP-TYPE
	ENTERPRISE  smscAgent
	VARIABLES  {trapNotificationId, trapSeverity, trapData,
		smscPstnaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPstnaCritical
		MANAGEDOBJECT-DEFAULT: smscAgent"
   ::= 	6041

--

-- End of definition

--
-- Trap for table: smscPstnaMajor
--
smscPstnaMajorTrap TRAP-TYPE
	ENTERPRISE  smscAgent
	VARIABLES  {trapNotificationId, trapSeverity, trapData,
		smscPstnaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPstnaMajor
		MANAGEDOBJECT-DEFAULT: smscAgent"
   ::= 	6042

--

-- End of definition

--
-- Trap for table: smscPstnaMinor
--
smscPstnaMinorTrap TRAP-TYPE
	ENTERPRISE  smscAgent
	VARIABLES  {trapNotificationId, trapSeverity, trapData,
		smscPstnaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPstnaMinor
		MANAGEDOBJECT-DEFAULT: smscAgent"
   ::= 	6043

--

-- End of definition

--
-- Trap for table: smscPstnaWarning
--
smscPstnaWarningTrap TRAP-TYPE
	ENTERPRISE  smscAgent
	VARIABLES  {trapNotificationId, trapSeverity, trapData,
		smscPstnaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPstnaWarning
		MANAGEDOBJECT-DEFAULT: smscAgent"
   ::= 	6044

--

-- End of definition

--
-- Trap for table: smscPstnaClear
--
smscPstnaClearTrap TRAP-TYPE
	ENTERPRISE  smscAgent
	VARIABLES  {trapNotificationId, trapSeverity, trapData,
		smscPstnaName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPstnaClear
		MANAGEDOBJECT-DEFAULT: smscAgent"
   ::= 	6045

--

-- End of definition

--
-- Trap for table: smscGiw
--
smscGiwTrap TRAP-TYPE
	ENTERPRISE  smscAgent
	VARIABLES  {trapNotificationId, trapSeverity, trapData,
		smscGiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGiw
		MANAGEDOBJECT-DEFAULT: smscAgent"
   ::= 	605

--

-- End of definition

--
-- Trap for table: smscGiwIndeterminate
--
smscGiwIndeterminateTrap TRAP-TYPE
	ENTERPRISE  smscAgent
	VARIABLES  {trapNotificationId, trapSeverity, trapData,
		smscGiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGiwIndeterminate
		MANAGEDOBJECT-DEFAULT: smscAgent"
   ::= 	6050

--

-- End of definition

--
-- Trap for table: smscGiwCritical
--
smscGiwCriticalTrap TRAP-TYPE
	ENTERPRISE  smscAgent
	VARIABLES  {trapNotificationId, trapSeverity, trapData,
		smscGiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGiwCritical
		MANAGEDOBJECT-DEFAULT: smscAgent"
   ::= 	6051

--

-- End of definition

--
-- Trap for table: smscGiwMajor
--
smscGiwMajorTrap TRAP-TYPE
	ENTERPRISE  smscAgent
	VARIABLES  {trapNotificationId, trapSeverity, trapData,
		smscGiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGiwMajor
		MANAGEDOBJECT-DEFAULT: smscAgent"
   ::= 	6052

--

-- End of definition

--
-- Trap for table: smscGiwMinor
--
smscGiwMinorTrap TRAP-TYPE
	ENTERPRISE  smscAgent
	VARIABLES  {trapNotificationId, trapSeverity, trapData,
		smscGiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGiwMinor
		MANAGEDOBJECT-DEFAULT: smscAgent"
   ::= 	6053

--

-- End of definition

--
-- Trap for table: smscGiwWarning
--
smscGiwWarningTrap TRAP-TYPE
	ENTERPRISE  smscAgent
	VARIABLES  {trapNotificationId, trapSeverity, trapData,
		smscGiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGiwWarning
		MANAGEDOBJECT-DEFAULT: smscAgent"
   ::= 	6054

--

-- End of definition

--
-- Trap for table: smscGiwClear
--
smscGiwClearTrap TRAP-TYPE
	ENTERPRISE  smscAgent
	VARIABLES  {trapNotificationId, trapSeverity, trapData,
		smscGiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGiwClear
		MANAGEDOBJECT-DEFAULT: smscAgent"
   ::= 	6055

--

-- End of definition

--
-- Trap for table: smscFax3srv
--
smscFax3srvTrap TRAP-TYPE
	ENTERPRISE  smscAgent
	VARIABLES  {trapNotificationId, trapSeverity, trapData,
		smscFax3srvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFax3srv
		MANAGEDOBJECT-DEFAULT: smscAgent"
   ::= 	606

--

-- End of definition

--
-- Trap for table: smscFax3srvIndeterminate
--
smscFax3srvIndeterminateTrap TRAP-TYPE
	ENTERPRISE  smscAgent
	VARIABLES  {trapNotificationId, trapSeverity, trapData,
		smscFax3srvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFax3srvIndeterminate
		MANAGEDOBJECT-DEFAULT: smscAgent"
   ::= 	6060

--

-- End of definition

--
-- Trap for table: smscFax3srvCritical
--
smscFax3srvCriticalTrap TRAP-TYPE
	ENTERPRISE  smscAgent
	VARIABLES  {trapNotificationId, trapSeverity, trapData,
		smscFax3srvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFax3srvCritical
		MANAGEDOBJECT-DEFAULT: smscAgent"
   ::= 	6061

--

-- End of definition

--
-- Trap for table: smscFax3srvMajor
--
smscFax3srvMajorTrap TRAP-TYPE
	ENTERPRISE  smscAgent
	VARIABLES  {trapNotificationId, trapSeverity, trapData,
		smscFax3srvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFax3srvMajor
		MANAGEDOBJECT-DEFAULT: smscAgent"
   ::= 	6062

--

-- End of definition

--
-- Trap for table: smscFax3srvMinor
--
smscFax3srvMinorTrap TRAP-TYPE
	ENTERPRISE  smscAgent
	VARIABLES  {trapNotificationId, trapSeverity, trapData,
		smscFax3srvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFax3srvMinor
		MANAGEDOBJECT-DEFAULT: smscAgent"
   ::= 	6063

--

-- End of definition

--
-- Trap for table: smscFax3srvWarning
--
smscFax3srvWarningTrap TRAP-TYPE
	ENTERPRISE  smscAgent
	VARIABLES  {trapNotificationId, trapSeverity, trapData,
		smscFax3srvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFax3srvWarning
		MANAGEDOBJECT-DEFAULT: smscAgent"
   ::= 	6064

--

-- End of definition

--
-- Trap for table: smscFax3srvClear
--
smscFax3srvClearTrap TRAP-TYPE
	ENTERPRISE  smscAgent
	VARIABLES  {trapNotificationId, trapSeverity, trapData,
		smscFax3srvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFax3srvClear
		MANAGEDOBJECT-DEFAULT: smscAgent"
   ::= 	6065

--

-- End of definition

--
-- Trap for table: smscIsdn
--
smscIsdnTrap TRAP-TYPE
	ENTERPRISE  smscAgent
	VARIABLES  {trapNotificationId, trapSeverity, trapData,
		smscIsdnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIsdn
		MANAGEDOBJECT-DEFAULT: smscAgent"
   ::= 	607

--

-- End of definition

--
-- Trap for table: smscIsdnIndeterminate
--
smscIsdnIndeterminateTrap TRAP-TYPE
	ENTERPRISE  smscAgent
	VARIABLES  {trapNotificationId, trapSeverity, trapData,
		smscIsdnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIsdnIndeterminate
		MANAGEDOBJECT-DEFAULT: smscAgent"
   ::= 	6070

--

-- End of definition

--
-- Trap for table: smscIsdnCritical
--
smscIsdnCriticalTrap TRAP-TYPE
	ENTERPRISE  smscAgent
	VARIABLES  {trapNotificationId, trapSeverity, trapData,
		smscIsdnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIsdnCritical
		MANAGEDOBJECT-DEFAULT: smscAgent"
   ::= 	6071

--

-- End of definition

--
-- Trap for table: smscIsdnMajor
--
smscIsdnMajorTrap TRAP-TYPE
	ENTERPRISE  smscAgent
	VARIABLES  {trapNotificationId, trapSeverity, trapData,
		smscIsdnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIsdnMajor
		MANAGEDOBJECT-DEFAULT: smscAgent"
   ::= 	6072

--

-- End of definition

--
-- Trap for table: smscIsdnMinor
--
smscIsdnMinorTrap TRAP-TYPE
	ENTERPRISE  smscAgent
	VARIABLES  {trapNotificationId, trapSeverity, trapData,
		smscIsdnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIsdnMinor
		MANAGEDOBJECT-DEFAULT: smscAgent"
   ::= 	6073

--

-- End of definition

--
-- Trap for table: smscIsdnWarning
--
smscIsdnWarningTrap TRAP-TYPE
	ENTERPRISE  smscAgent
	VARIABLES  {trapNotificationId, trapSeverity, trapData,
		smscIsdnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIsdnWarning
		MANAGEDOBJECT-DEFAULT: smscAgent"
   ::= 	6074

--

-- End of definition

--
-- Trap for table: smscIsdnClear
--
smscIsdnClearTrap TRAP-TYPE
	ENTERPRISE  smscAgent
	VARIABLES  {trapNotificationId, trapSeverity, trapData,
		smscIsdnName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIsdnClear
		MANAGEDOBJECT-DEFAULT: smscAgent"
   ::= 	6075

--

-- End of definition

--
-- Trap for table: smscIs41
--
smscIs41Trap TRAP-TYPE
	ENTERPRISE  smscAgent
	VARIABLES  {trapNotificationId, trapSeverity, trapData,
		smscIs41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIs41
		MANAGEDOBJECT-DEFAULT: smscAgent"
   ::= 	608

--

-- End of definition

--
-- Trap for table: smscIs41Indeterminate
--
smscIs41IndeterminateTrap TRAP-TYPE
	ENTERPRISE  smscAgent
	VARIABLES  {trapNotificationId, trapSeverity, trapData,
		smscIs41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIs41Indeterminate
		MANAGEDOBJECT-DEFAULT: smscAgent"
   ::= 	6080

--

-- End of definition

--
-- Trap for table: smscIs41Critical
--
smscIs41CriticalTrap TRAP-TYPE
	ENTERPRISE  smscAgent
	VARIABLES  {trapNotificationId, trapSeverity, trapData,
		smscIs41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIs41Critical
		MANAGEDOBJECT-DEFAULT: smscAgent"
   ::= 	6081

--

-- End of definition

--
-- Trap for table: smscIs41Major
--
smscIs41MajorTrap TRAP-TYPE
	ENTERPRISE  smscAgent
	VARIABLES  {trapNotificationId, trapSeverity, trapData,
		smscIs41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIs41Major
		MANAGEDOBJECT-DEFAULT: smscAgent"
   ::= 	6082

--

-- End of definition

--
-- Trap for table: smscIs41Minor
--
smscIs41MinorTrap TRAP-TYPE
	ENTERPRISE  smscAgent
	VARIABLES  {trapNotificationId, trapSeverity, trapData,
		smscIs41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIs41Minor
		MANAGEDOBJECT-DEFAULT: smscAgent"
   ::= 	6083

--

-- End of definition

--
-- Trap for table: smscIs41Warning
--
smscIs41WarningTrap TRAP-TYPE
	ENTERPRISE  smscAgent
	VARIABLES  {trapNotificationId, trapSeverity, trapData,
		smscIs41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIs41Warning
		MANAGEDOBJECT-DEFAULT: smscAgent"
   ::= 	6084

--

-- End of definition

--
-- Trap for table: smscIs41Clear
--
smscIs41ClearTrap TRAP-TYPE
	ENTERPRISE  smscAgent
	VARIABLES  {trapNotificationId, trapSeverity, trapData,
		smscIs41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIs41Clear
		MANAGEDOBJECT-DEFAULT: smscAgent"
   ::= 	6085

--

-- End of definition

--
-- Trap for table: smscRtr
--
smscRtrTrap TRAP-TYPE
	ENTERPRISE  smscAgent
	VARIABLES  {trapNotificationId, trapSeverity, trapData,
		smscRtrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRtr
		MANAGEDOBJECT-DEFAULT: smscAgent"
   ::= 	609

--

-- End of definition

--
-- Trap for table: smscRtrIndeterminate
--
smscRtrIndeterminateTrap TRAP-TYPE
	ENTERPRISE  smscAgent
	VARIABLES  {trapNotificationId, trapSeverity, trapData,
		smscRtrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRtrIndeterminate
		MANAGEDOBJECT-DEFAULT: smscAgent"
   ::= 	6090

--

-- End of definition

--
-- Trap for table: smscRtrCritical
--
smscRtrCriticalTrap TRAP-TYPE
	ENTERPRISE  smscAgent
	VARIABLES  {trapNotificationId, trapSeverity, trapData,
		smscRtrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRtrCritical
		MANAGEDOBJECT-DEFAULT: smscAgent"
   ::= 	6091

--

-- End of definition

--
-- Trap for table: smscRtrMajor
--
smscRtrMajorTrap TRAP-TYPE
	ENTERPRISE  smscAgent
	VARIABLES  {trapNotificationId, trapSeverity, trapData,
		smscRtrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRtrMajor
		MANAGEDOBJECT-DEFAULT: smscAgent"
   ::= 	6092

--

-- End of definition

--
-- Trap for table: smscRtrMinor
--
smscRtrMinorTrap TRAP-TYPE
	ENTERPRISE  smscAgent
	VARIABLES  {trapNotificationId, trapSeverity, trapData,
		smscRtrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRtrMinor
		MANAGEDOBJECT-DEFAULT: smscAgent"
   ::= 	6093

--

-- End of definition

--
-- Trap for table: smscRtrWarning
--
smscRtrWarningTrap TRAP-TYPE
	ENTERPRISE  smscAgent
	VARIABLES  {trapNotificationId, trapSeverity, trapData,
		smscRtrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRtrWarning
		MANAGEDOBJECT-DEFAULT: smscAgent"
   ::= 	6094

--

-- End of definition

--
-- Trap for table: smscRtrClear
--
smscRtrClearTrap TRAP-TYPE
	ENTERPRISE  smscAgent
	VARIABLES  {trapNotificationId, trapSeverity, trapData,
		smscRtrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRtrClear
		MANAGEDOBJECT-DEFAULT: smscAgent"
   ::= 	6095

--

-- End of definition

--
-- Trap for table: smscRas
--
smscRasTrap TRAP-TYPE
	ENTERPRISE  smscAgent
	VARIABLES  {trapNotificationId, trapSeverity, trapData,
		smscRasName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRas
		MANAGEDOBJECT-DEFAULT: smscAgent"
   ::= 	610

--

-- End of definition

--
-- Trap for table: smscRasIndeterminate
--
smscRasIndeterminateTrap TRAP-TYPE
	ENTERPRISE  smscAgent
	VARIABLES  {trapNotificationId, trapSeverity, trapData,
		smscRasName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRasIndeterminate
		MANAGEDOBJECT-DEFAULT: smscAgent"
   ::= 	6100

--

-- End of definition

--
-- Trap for table: smscRasCritical
--
smscRasCriticalTrap TRAP-TYPE
	ENTERPRISE  smscAgent
	VARIABLES  {trapNotificationId, trapSeverity, trapData,
		smscRasName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRasCritical
		MANAGEDOBJECT-DEFAULT: smscAgent"
   ::= 	6101

--

-- End of definition

--
-- Trap for table: smscRasMajor
--
smscRasMajorTrap TRAP-TYPE
	ENTERPRISE  smscAgent
	VARIABLES  {trapNotificationId, trapSeverity, trapData,
		smscRasName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRasMajor
		MANAGEDOBJECT-DEFAULT: smscAgent"
   ::= 	6102

--

-- End of definition

--
-- Trap for table: smscRasMinor
--
smscRasMinorTrap TRAP-TYPE
	ENTERPRISE  smscAgent
	VARIABLES  {trapNotificationId, trapSeverity, trapData,
		smscRasName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRasMinor
		MANAGEDOBJECT-DEFAULT: smscAgent"
   ::= 	6103

--

-- End of definition

--
-- Trap for table: smscRasWarning
--
smscRasWarningTrap TRAP-TYPE
	ENTERPRISE  smscAgent
	VARIABLES  {trapNotificationId, trapSeverity, trapData,
		smscRasName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRasWarning
		MANAGEDOBJECT-DEFAULT: smscAgent"
   ::= 	6104

--

-- End of definition

--
-- Trap for table: smscRasClear
--
smscRasClearTrap TRAP-TYPE
	ENTERPRISE  smscAgent
	VARIABLES  {trapNotificationId, trapSeverity, trapData,
		smscRasName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscRasClear
		MANAGEDOBJECT-DEFAULT: smscAgent"
   ::= 	6105

--

-- End of definition

--
-- Trap for table: smscGhlr
--
smscGhlrTrap TRAP-TYPE
	ENTERPRISE  smscAgent
	VARIABLES  {trapNotificationId, trapSeverity, trapData,
		smscGhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGhlr
		MANAGEDOBJECT-DEFAULT: smscAgent"
   ::= 	611

--

-- End of definition

--
-- Trap for table: smscGhlrIndeterminate
--
smscGhlrIndeterminateTrap TRAP-TYPE
	ENTERPRISE  smscAgent
	VARIABLES  {trapNotificationId, trapSeverity, trapData,
		smscGhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGhlrIndeterminate
		MANAGEDOBJECT-DEFAULT: smscAgent"
   ::= 	6110

--

-- End of definition

--
-- Trap for table: smscGhlrCritical
--
smscGhlrCriticalTrap TRAP-TYPE
	ENTERPRISE  smscAgent
	VARIABLES  {trapNotificationId, trapSeverity, trapData,
		smscGhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGhlrCritical
		MANAGEDOBJECT-DEFAULT: smscAgent"
   ::= 	6111

--

-- End of definition

--
-- Trap for table: smscGhlrMajor
--
smscGhlrMajorTrap TRAP-TYPE
	ENTERPRISE  smscAgent
	VARIABLES  {trapNotificationId, trapSeverity, trapData,
		smscGhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGhlrMajor
		MANAGEDOBJECT-DEFAULT: smscAgent"
   ::= 	6112

--

-- End of definition

--
-- Trap for table: smscGhlrMinor
--
smscGhlrMinorTrap TRAP-TYPE
	ENTERPRISE  smscAgent
	VARIABLES  {trapNotificationId, trapSeverity, trapData,
		smscGhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGhlrMinor
		MANAGEDOBJECT-DEFAULT: smscAgent"
   ::= 	6113

--

-- End of definition

--
-- Trap for table: smscGhlrWarning
--
smscGhlrWarningTrap TRAP-TYPE
	ENTERPRISE  smscAgent
	VARIABLES  {trapNotificationId, trapSeverity, trapData,
		smscGhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGhlrWarning
		MANAGEDOBJECT-DEFAULT: smscAgent"
   ::= 	6114

--

-- End of definition

--
-- Trap for table: smscGhlrClear
--
smscGhlrClearTrap TRAP-TYPE
	ENTERPRISE  smscAgent
	VARIABLES  {trapNotificationId, trapSeverity, trapData,
		smscGhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscGhlrClear
		MANAGEDOBJECT-DEFAULT: smscAgent"
   ::= 	6115

--

-- End of definition

--
-- Trap for table: smscOtais41
--
smscOtais41Trap TRAP-TYPE
	ENTERPRISE  smscAgent
	VARIABLES  {trapNotificationId, trapSeverity, trapData,
		smscOtais41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscOtais41
		MANAGEDOBJECT-DEFAULT: smscAgent"
   ::= 	612

--

-- End of definition

--
-- Trap for table: smscOtais41Indeterminate
--
smscOtais41IndeterminateTrap TRAP-TYPE
	ENTERPRISE  smscAgent
	VARIABLES  {trapNotificationId, trapSeverity, trapData,
		smscOtais41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscOtais41Indeterminate
		MANAGEDOBJECT-DEFAULT: smscAgent"
   ::= 	6120

--

-- End of definition

--
-- Trap for table: smscOtais41Critical
--
smscOtais41CriticalTrap TRAP-TYPE
	ENTERPRISE  smscAgent
	VARIABLES  {trapNotificationId, trapSeverity, trapData,
		smscOtais41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscOtais41Critical
		MANAGEDOBJECT-DEFAULT: smscAgent"
   ::= 	6121

--

-- End of definition

--
-- Trap for table: smscOtais41Major
--
smscOtais41MajorTrap TRAP-TYPE
	ENTERPRISE  smscAgent
	VARIABLES  {trapNotificationId, trapSeverity, trapData,
		smscOtais41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscOtais41Major
		MANAGEDOBJECT-DEFAULT: smscAgent"
   ::= 	6122

--

-- End of definition

--
-- Trap for table: smscOtais41Minor
--
smscOtais41MinorTrap TRAP-TYPE
	ENTERPRISE  smscAgent
	VARIABLES  {trapNotificationId, trapSeverity, trapData,
		smscOtais41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscOtais41Minor
		MANAGEDOBJECT-DEFAULT: smscAgent"
   ::= 	6123

--

-- End of definition

--
-- Trap for table: smscOtais41Warning
--
smscOtais41WarningTrap TRAP-TYPE
	ENTERPRISE  smscAgent
	VARIABLES  {trapNotificationId, trapSeverity, trapData,
		smscOtais41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscOtais41Warning
		MANAGEDOBJECT-DEFAULT: smscAgent"
   ::= 	6124

--

-- End of definition

--
-- Trap for table: smscOtais41Clear
--
smscOtais41ClearTrap TRAP-TYPE
	ENTERPRISE  smscAgent
	VARIABLES  {trapNotificationId, trapSeverity, trapData,
		smscOtais41Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscOtais41Clear
		MANAGEDOBJECT-DEFAULT: smscAgent"
   ::= 	6125

--

-- End of definition

--
-- Trap for table: smscPhlr
--
smscPhlrTrap TRAP-TYPE
	ENTERPRISE  smscAgent
	VARIABLES  {trapNotificationId, trapSeverity, trapData,
		smscPhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPhlr
		MANAGEDOBJECT-DEFAULT: smscAgent"
   ::= 	613

--

-- End of definition

--
-- Trap for table: smscPhlrIndeterminate
--
smscPhlrIndeterminateTrap TRAP-TYPE
	ENTERPRISE  smscAgent
	VARIABLES  {trapNotificationId, trapSeverity, trapData,
		smscPhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPhlrIndeterminate
		MANAGEDOBJECT-DEFAULT: smscAgent"
   ::= 	6130

--

-- End of definition

--
-- Trap for table: smscPhlrCritical
--
smscPhlrCriticalTrap TRAP-TYPE
	ENTERPRISE  smscAgent
	VARIABLES  {trapNotificationId, trapSeverity, trapData,
		smscPhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPhlrCritical
		MANAGEDOBJECT-DEFAULT: smscAgent"
   ::= 	6131

--

-- End of definition

--
-- Trap for table: smscPhlrMajor
--
smscPhlrMajorTrap TRAP-TYPE
	ENTERPRISE  smscAgent
	VARIABLES  {trapNotificationId, trapSeverity, trapData,
		smscPhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPhlrMajor
		MANAGEDOBJECT-DEFAULT: smscAgent"
   ::= 	6132

--

-- End of definition

--
-- Trap for table: smscPhlrMinor
--
smscPhlrMinorTrap TRAP-TYPE
	ENTERPRISE  smscAgent
	VARIABLES  {trapNotificationId, trapSeverity, trapData,
		smscPhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPhlrMinor
		MANAGEDOBJECT-DEFAULT: smscAgent"
   ::= 	6133

--

-- End of definition

--
-- Trap for table: smscPhlrWarning
--
smscPhlrWarningTrap TRAP-TYPE
	ENTERPRISE  smscAgent
	VARIABLES  {trapNotificationId, trapSeverity, trapData,
		smscPhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPhlrWarning
		MANAGEDOBJECT-DEFAULT: smscAgent"
   ::= 	6134

--

-- End of definition

--
-- Trap for table: smscPhlrClear
--
smscPhlrClearTrap TRAP-TYPE
	ENTERPRISE  smscAgent
	VARIABLES  {trapNotificationId, trapSeverity, trapData,
		smscPhlrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPhlrClear
		MANAGEDOBJECT-DEFAULT: smscAgent"
   ::= 	6135

--

-- End of definition

--
-- Trap for table: smscEir
--
smscEirTrap TRAP-TYPE
	ENTERPRISE  smscAgent
	VARIABLES  {trapNotificationId, trapSeverity, trapData,
		smscEirName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEir
		MANAGEDOBJECT-DEFAULT: smscAgent"
   ::= 	700

--

-- End of definition

--
-- Trap for table: smscEirIndeterminate
--
smscEirIndeterminateTrap TRAP-TYPE
	ENTERPRISE  smscAgent
	VARIABLES  {trapNotificationId, trapSeverity, trapData,
		smscEirName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEirIndeterminate
		MANAGEDOBJECT-DEFAULT: smscAgent"
   ::= 	7000

--

-- End of definition

--
-- Trap for table: smscEirCritical
--
smscEirCriticalTrap TRAP-TYPE
	ENTERPRISE  smscAgent
	VARIABLES  {trapNotificationId, trapSeverity, trapData,
		smscEirName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEirCritical
		MANAGEDOBJECT-DEFAULT: smscAgent"
   ::= 	7001

--

-- End of definition

--
-- Trap for table: smscEirMajor
--
smscEirMajorTrap TRAP-TYPE
	ENTERPRISE  smscAgent
	VARIABLES  {trapNotificationId, trapSeverity, trapData,
		smscEirName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEirMajor
		MANAGEDOBJECT-DEFAULT: smscAgent"
   ::= 	7002

--

-- End of definition

--
-- Trap for table: smscEirMinor
--
smscEirMinorTrap TRAP-TYPE
	ENTERPRISE  smscAgent
	VARIABLES  {trapNotificationId, trapSeverity, trapData,
		smscEirName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEirMinor
		MANAGEDOBJECT-DEFAULT: smscAgent"
   ::= 	7003

--

-- End of definition

--
-- Trap for table: smscEirWarning
--
smscEirWarningTrap TRAP-TYPE
	ENTERPRISE  smscAgent
	VARIABLES  {trapNotificationId, trapSeverity, trapData,
		smscEirName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEirWarning
		MANAGEDOBJECT-DEFAULT: smscAgent"
   ::= 	7004

--

-- End of definition

--
-- Trap for table: smscEirClear
--
smscEirClearTrap TRAP-TYPE
	ENTERPRISE  smscAgent
	VARIABLES  {trapNotificationId, trapSeverity, trapData,
		smscEirName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscEirClear
		MANAGEDOBJECT-DEFAULT: smscAgent"
   ::= 	7005

--

-- End of definition

--
-- Trap for table: smscDlh
--
smscDlhTrap TRAP-TYPE
	ENTERPRISE  smscAgent
	VARIABLES  {trapNotificationId, trapSeverity, trapData,
		smscDlhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDlh
		MANAGEDOBJECT-DEFAULT: smscAgent"
   ::= 	701

--

-- End of definition

--
-- Trap for table: smscDlhIndeterminate
--
smscDlhIndeterminateTrap TRAP-TYPE
	ENTERPRISE  smscAgent
	VARIABLES  {trapNotificationId, trapSeverity, trapData,
		smscDlhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDlhIndeterminate
		MANAGEDOBJECT-DEFAULT: smscAgent"
   ::= 	7010

--

-- End of definition

--
-- Trap for table: smscDlhCritical
--
smscDlhCriticalTrap TRAP-TYPE
	ENTERPRISE  smscAgent
	VARIABLES  {trapNotificationId, trapSeverity, trapData,
		smscDlhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDlhCritical
		MANAGEDOBJECT-DEFAULT: smscAgent"
   ::= 	7011

--

-- End of definition

--
-- Trap for table: smscDlhMajor
--
smscDlhMajorTrap TRAP-TYPE
	ENTERPRISE  smscAgent
	VARIABLES  {trapNotificationId, trapSeverity, trapData,
		smscDlhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDlhMajor
		MANAGEDOBJECT-DEFAULT: smscAgent"
   ::= 	7012

--

-- End of definition

--
-- Trap for table: smscDlhMinor
--
smscDlhMinorTrap TRAP-TYPE
	ENTERPRISE  smscAgent
	VARIABLES  {trapNotificationId, trapSeverity, trapData,
		smscDlhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDlhMinor
		MANAGEDOBJECT-DEFAULT: smscAgent"
   ::= 	7013

--

-- End of definition

--
-- Trap for table: smscDlhWarning
--
smscDlhWarningTrap TRAP-TYPE
	ENTERPRISE  smscAgent
	VARIABLES  {trapNotificationId, trapSeverity, trapData,
		smscDlhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDlhWarning
		MANAGEDOBJECT-DEFAULT: smscAgent"
   ::= 	7014

--

-- End of definition

--
-- Trap for table: smscDlhClear
--
smscDlhClearTrap TRAP-TYPE
	ENTERPRISE  smscAgent
	VARIABLES  {trapNotificationId, trapSeverity, trapData,
		smscDlhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscDlhClear
		MANAGEDOBJECT-DEFAULT: smscAgent"
   ::= 	7015

--

-- End of definition

--
-- Trap for table: smscSsd
--
smscSsdTrap TRAP-TYPE
	ENTERPRISE  smscAgent
	VARIABLES  {trapNotificationId, trapSeverity, trapData,
		smscSsdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSsd
		MANAGEDOBJECT-DEFAULT: smscAgent"
   ::= 	702

--

-- End of definition

--
-- Trap for table: smscSsdIndeterminate
--
smscSsdIndeterminateTrap TRAP-TYPE
	ENTERPRISE  smscAgent
	VARIABLES  {trapNotificationId, trapSeverity, trapData,
		smscSsdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSsdIndeterminate
		MANAGEDOBJECT-DEFAULT: smscAgent"
   ::= 	7020

--

-- End of definition

--
-- Trap for table: smscSsdCritical
--
smscSsdCriticalTrap TRAP-TYPE
	ENTERPRISE  smscAgent
	VARIABLES  {trapNotificationId, trapSeverity, trapData,
		smscSsdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSsdCritical
		MANAGEDOBJECT-DEFAULT: smscAgent"
   ::= 	7021

--

-- End of definition

--
-- Trap for table: smscSsdMajor
--
smscSsdMajorTrap TRAP-TYPE
	ENTERPRISE  smscAgent
	VARIABLES  {trapNotificationId, trapSeverity, trapData,
		smscSsdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSsdMajor
		MANAGEDOBJECT-DEFAULT: smscAgent"
   ::= 	7022

--

-- End of definition

--
-- Trap for table: smscSsdMinor
--
smscSsdMinorTrap TRAP-TYPE
	ENTERPRISE  smscAgent
	VARIABLES  {trapNotificationId, trapSeverity, trapData,
		smscSsdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSsdMinor
		MANAGEDOBJECT-DEFAULT: smscAgent"
   ::= 	7023

--

-- End of definition

--
-- Trap for table: smscSsdWarning
--
smscSsdWarningTrap TRAP-TYPE
	ENTERPRISE  smscAgent
	VARIABLES  {trapNotificationId, trapSeverity, trapData,
		smscSsdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSsdWarning
		MANAGEDOBJECT-DEFAULT: smscAgent"
   ::= 	7024

--

-- End of definition

--
-- Trap for table: smscSsdClear
--
smscSsdClearTrap TRAP-TYPE
	ENTERPRISE  smscAgent
	VARIABLES  {trapNotificationId, trapSeverity, trapData,
		smscSsdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscSsdClear
		MANAGEDOBJECT-DEFAULT: smscAgent"
   ::= 	7025

--

-- End of definition

--
-- Trap for table: smscPrh
--
smscPrhTrap TRAP-TYPE
	ENTERPRISE  smscAgent
	VARIABLES  {trapNotificationId, trapSeverity, trapData,
		smscPrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPrh
		MANAGEDOBJECT-DEFAULT: smscAgent"
   ::= 	703

--

-- End of definition

--
-- Trap for table: smscPrhIndeterminate
--
smscPrhIndeterminateTrap TRAP-TYPE
	ENTERPRISE  smscAgent
	VARIABLES  {trapNotificationId, trapSeverity, trapData,
		smscPrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPrhIndeterminate
		MANAGEDOBJECT-DEFAULT: smscAgent"
   ::= 	7030

--

-- End of definition

--
-- Trap for table: smscPrhCritical
--
smscPrhCriticalTrap TRAP-TYPE
	ENTERPRISE  smscAgent
	VARIABLES  {trapNotificationId, trapSeverity, trapData,
		smscPrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPrhCritical
		MANAGEDOBJECT-DEFAULT: smscAgent"
   ::= 	7031

--

-- End of definition

--
-- Trap for table: smscPrhMajor
--
smscPrhMajorTrap TRAP-TYPE
	ENTERPRISE  smscAgent
	VARIABLES  {trapNotificationId, trapSeverity, trapData,
		smscPrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPrhMajor
		MANAGEDOBJECT-DEFAULT: smscAgent"
   ::= 	7032

--

-- End of definition

--
-- Trap for table: smscPrhMinor
--
smscPrhMinorTrap TRAP-TYPE
	ENTERPRISE  smscAgent
	VARIABLES  {trapNotificationId, trapSeverity, trapData,
		smscPrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPrhMinor
		MANAGEDOBJECT-DEFAULT: smscAgent"
   ::= 	7033

--

-- End of definition

--
-- Trap for table: smscPrhWarning
--
smscPrhWarningTrap TRAP-TYPE
	ENTERPRISE  smscAgent
	VARIABLES  {trapNotificationId, trapSeverity, trapData,
		smscPrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPrhWarning
		MANAGEDOBJECT-DEFAULT: smscAgent"
   ::= 	7034

--

-- End of definition

--
-- Trap for table: smscPrhClear
--
smscPrhClearTrap TRAP-TYPE
	ENTERPRISE  smscAgent
	VARIABLES  {trapNotificationId, trapSeverity, trapData,
		smscPrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPrhClear
		MANAGEDOBJECT-DEFAULT: smscAgent"
   ::= 	7035

--

-- End of definition

--
-- Trap for table: smscFrh
--
smscFrhTrap TRAP-TYPE
	ENTERPRISE  smscAgent
	VARIABLES  {trapNotificationId, trapSeverity, trapData,
		smscFrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFrh
		MANAGEDOBJECT-DEFAULT: smscAgent"
   ::= 	704

--

-- End of definition

--
-- Trap for table: smscFrhIndeterminate
--
smscFrhIndeterminateTrap TRAP-TYPE
	ENTERPRISE  smscAgent
	VARIABLES  {trapNotificationId, trapSeverity, trapData,
		smscFrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFrhIndeterminate
		MANAGEDOBJECT-DEFAULT: smscAgent"
   ::= 	7040

--

-- End of definition

--
-- Trap for table: smscFrhCritical
--
smscFrhCriticalTrap TRAP-TYPE
	ENTERPRISE  smscAgent
	VARIABLES  {trapNotificationId, trapSeverity, trapData,
		smscFrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFrhCritical
		MANAGEDOBJECT-DEFAULT: smscAgent"
   ::= 	7041

--

-- End of definition

--
-- Trap for table: smscFrhMajor
--
smscFrhMajorTrap TRAP-TYPE
	ENTERPRISE  smscAgent
	VARIABLES  {trapNotificationId, trapSeverity, trapData,
		smscFrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFrhMajor
		MANAGEDOBJECT-DEFAULT: smscAgent"
   ::= 	7042

--

-- End of definition

--
-- Trap for table: smscFrhMinor
--
smscFrhMinorTrap TRAP-TYPE
	ENTERPRISE  smscAgent
	VARIABLES  {trapNotificationId, trapSeverity, trapData,
		smscFrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFrhMinor
		MANAGEDOBJECT-DEFAULT: smscAgent"
   ::= 	7043

--

-- End of definition

--
-- Trap for table: smscFrhWarning
--
smscFrhWarningTrap TRAP-TYPE
	ENTERPRISE  smscAgent
	VARIABLES  {trapNotificationId, trapSeverity, trapData,
		smscFrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFrhWarning
		MANAGEDOBJECT-DEFAULT: smscAgent"
   ::= 	7044

--

-- End of definition

--
-- Trap for table: smscFrhClear
--
smscFrhClearTrap TRAP-TYPE
	ENTERPRISE  smscAgent
	VARIABLES  {trapNotificationId, trapSeverity, trapData,
		smscFrhName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscFrhClear
		MANAGEDOBJECT-DEFAULT: smscAgent"
   ::= 	7045

--

-- End of definition

--
-- Trap for table: smscLogsrv
--
smscLogsrvTrap TRAP-TYPE
	ENTERPRISE  smscAgent
	VARIABLES  {trapNotificationId, trapSeverity, trapData,
		smscLogsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLogsrv
		MANAGEDOBJECT-DEFAULT: smscAgent"
   ::= 	705

--

-- End of definition

--
-- Trap for table: smscLogsrvIndeterminate
--
smscLogsrvIndeterminateTrap TRAP-TYPE
	ENTERPRISE  smscAgent
	VARIABLES  {trapNotificationId, trapSeverity, trapData,
		smscLogsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLogsrvIndeterminate
		MANAGEDOBJECT-DEFAULT: smscAgent"
   ::= 	7050

--

-- End of definition

--
-- Trap for table: smscLogsrvCritical
--
smscLogsrvCriticalTrap TRAP-TYPE
	ENTERPRISE  smscAgent
	VARIABLES  {trapNotificationId, trapSeverity, trapData,
		smscLogsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLogsrvCritical
		MANAGEDOBJECT-DEFAULT: smscAgent"
   ::= 	7051

--

-- End of definition

--
-- Trap for table: smscLogsrvMajor
--
smscLogsrvMajorTrap TRAP-TYPE
	ENTERPRISE  smscAgent
	VARIABLES  {trapNotificationId, trapSeverity, trapData,
		smscLogsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLogsrvMajor
		MANAGEDOBJECT-DEFAULT: smscAgent"
   ::= 	7052

--

-- End of definition

--
-- Trap for table: smscLogsrvMinor
--
smscLogsrvMinorTrap TRAP-TYPE
	ENTERPRISE  smscAgent
	VARIABLES  {trapNotificationId, trapSeverity, trapData,
		smscLogsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLogsrvMinor
		MANAGEDOBJECT-DEFAULT: smscAgent"
   ::= 	7053

--

-- End of definition

--
-- Trap for table: smscLogsrvWarning
--
smscLogsrvWarningTrap TRAP-TYPE
	ENTERPRISE  smscAgent
	VARIABLES  {trapNotificationId, trapSeverity, trapData,
		smscLogsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLogsrvWarning
		MANAGEDOBJECT-DEFAULT: smscAgent"
   ::= 	7054

--

-- End of definition

--
-- Trap for table: smscLogsrvClear
--
smscLogsrvClearTrap TRAP-TYPE
	ENTERPRISE  smscAgent
	VARIABLES  {trapNotificationId, trapSeverity, trapData,
		smscLogsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLogsrvClear
		MANAGEDOBJECT-DEFAULT: smscAgent"
   ::= 	7055

--

-- End of definition

--
-- Trap for table: smscTrcsrv
--
smscTrcsrvTrap TRAP-TYPE
	ENTERPRISE  smscAgent
	VARIABLES  {trapNotificationId, trapSeverity, trapData,
		smscTrcsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTrcsrv
		MANAGEDOBJECT-DEFAULT: smscAgent"
   ::= 	706

--

-- End of definition

--
-- Trap for table: smscTrcsrvIndeterminate
--
smscTrcsrvIndeterminateTrap TRAP-TYPE
	ENTERPRISE  smscAgent
	VARIABLES  {trapNotificationId, trapSeverity, trapData,
		smscTrcsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTrcsrvIndeterminate
		MANAGEDOBJECT-DEFAULT: smscAgent"
   ::= 	7060

--

-- End of definition

--
-- Trap for table: smscTrcsrvCritical
--
smscTrcsrvCriticalTrap TRAP-TYPE
	ENTERPRISE  smscAgent
	VARIABLES  {trapNotificationId, trapSeverity, trapData,
		smscTrcsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTrcsrvCritical
		MANAGEDOBJECT-DEFAULT: smscAgent"
   ::= 	7061

--

-- End of definition

--
-- Trap for table: smscTrcsrvMajor
--
smscTrcsrvMajorTrap TRAP-TYPE
	ENTERPRISE  smscAgent
	VARIABLES  {trapNotificationId, trapSeverity, trapData,
		smscTrcsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTrcsrvMajor
		MANAGEDOBJECT-DEFAULT: smscAgent"
   ::= 	7062

--

-- End of definition

--
-- Trap for table: smscTrcsrvMinor
--
smscTrcsrvMinorTrap TRAP-TYPE
	ENTERPRISE  smscAgent
	VARIABLES  {trapNotificationId, trapSeverity, trapData,
		smscTrcsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTrcsrvMinor
		MANAGEDOBJECT-DEFAULT: smscAgent"
   ::= 	7063

--

-- End of definition

--
-- Trap for table: smscTrcsrvWarning
--
smscTrcsrvWarningTrap TRAP-TYPE
	ENTERPRISE  smscAgent
	VARIABLES  {trapNotificationId, trapSeverity, trapData,
		smscTrcsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTrcsrvWarning
		MANAGEDOBJECT-DEFAULT: smscAgent"
   ::= 	7064

--

-- End of definition

--
-- Trap for table: smscTrcsrvClear
--
smscTrcsrvClearTrap TRAP-TYPE
	ENTERPRISE  smscAgent
	VARIABLES  {trapNotificationId, trapSeverity, trapData,
		smscTrcsrvName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscTrcsrvClear
		MANAGEDOBJECT-DEFAULT: smscAgent"
   ::= 	7065

--

-- End of definition

--
-- Trap for table: smscPbr
--
smscPbrTrap TRAP-TYPE
	ENTERPRISE  smscAgent
	VARIABLES  {trapNotificationId, trapSeverity, trapData,
		smscPbrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbr
		MANAGEDOBJECT-DEFAULT: smscAgent"
   ::= 	707

--

-- End of definition

--
-- Trap for table: smscPbrIndeterminate
--
smscPbrIndeterminateTrap TRAP-TYPE
	ENTERPRISE  smscAgent
	VARIABLES  {trapNotificationId, trapSeverity, trapData,
		smscPbrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbrIndeterminate
		MANAGEDOBJECT-DEFAULT: smscAgent"
   ::= 	7070

--

-- End of definition

--
-- Trap for table: smscPbrCritical
--
smscPbrCriticalTrap TRAP-TYPE
	ENTERPRISE  smscAgent
	VARIABLES  {trapNotificationId, trapSeverity, trapData,
		smscPbrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbrCritical
		MANAGEDOBJECT-DEFAULT: smscAgent"
   ::= 	7071

--

-- End of definition

--
-- Trap for table: smscPbrMajor
--
smscPbrMajorTrap TRAP-TYPE
	ENTERPRISE  smscAgent
	VARIABLES  {trapNotificationId, trapSeverity, trapData,
		smscPbrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbrMajor
		MANAGEDOBJECT-DEFAULT: smscAgent"
   ::= 	7072

--

-- End of definition

--
-- Trap for table: smscPbrMinor
--
smscPbrMinorTrap TRAP-TYPE
	ENTERPRISE  smscAgent
	VARIABLES  {trapNotificationId, trapSeverity, trapData,
		smscPbrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbrMinor
		MANAGEDOBJECT-DEFAULT: smscAgent"
   ::= 	7073

--

-- End of definition

--
-- Trap for table: smscPbrWarning
--
smscPbrWarningTrap TRAP-TYPE
	ENTERPRISE  smscAgent
	VARIABLES  {trapNotificationId, trapSeverity, trapData,
		smscPbrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbrWarning
		MANAGEDOBJECT-DEFAULT: smscAgent"
   ::= 	7074

--

-- End of definition

--
-- Trap for table: smscPbrClear
--
smscPbrClearTrap TRAP-TYPE
	ENTERPRISE  smscAgent
	VARIABLES  {trapNotificationId, trapSeverity, trapData,
		smscPbrName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbrClear
		MANAGEDOBJECT-DEFAULT: smscAgent"
   ::= 	7075

--

-- End of definition

--
-- Trap for table: smscPbb
--
smscPbbTrap TRAP-TYPE
	ENTERPRISE  smscAgent
	VARIABLES  {trapNotificationId, trapSeverity, trapData,
		smscPbbName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbb
		MANAGEDOBJECT-DEFAULT: smscAgent"
   ::= 	708

--

-- End of definition

--
-- Trap for table: smscPbbIndeterminate
--
smscPbbIndeterminateTrap TRAP-TYPE
	ENTERPRISE  smscAgent
	VARIABLES  {trapNotificationId, trapSeverity, trapData,
		smscPbbName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbbIndeterminate
		MANAGEDOBJECT-DEFAULT: smscAgent"
   ::= 	7080

--

-- End of definition

--
-- Trap for table: smscPbbCritical
--
smscPbbCriticalTrap TRAP-TYPE
	ENTERPRISE  smscAgent
	VARIABLES  {trapNotificationId, trapSeverity, trapData,
		smscPbbName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbbCritical
		MANAGEDOBJECT-DEFAULT: smscAgent"
   ::= 	7081

--

-- End of definition

--
-- Trap for table: smscPbbMajor
--
smscPbbMajorTrap TRAP-TYPE
	ENTERPRISE  smscAgent
	VARIABLES  {trapNotificationId, trapSeverity, trapData,
		smscPbbName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbbMajor
		MANAGEDOBJECT-DEFAULT: smscAgent"
   ::= 	7082

--

-- End of definition

--
-- Trap for table: smscPbbMinor
--
smscPbbMinorTrap TRAP-TYPE
	ENTERPRISE  smscAgent
	VARIABLES  {trapNotificationId, trapSeverity, trapData,
		smscPbbName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbbMinor
		MANAGEDOBJECT-DEFAULT: smscAgent"
   ::= 	7083

--

-- End of definition

--
-- Trap for table: smscPbbWarning
--
smscPbbWarningTrap TRAP-TYPE
	ENTERPRISE  smscAgent
	VARIABLES  {trapNotificationId, trapSeverity, trapData,
		smscPbbName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbbWarning
		MANAGEDOBJECT-DEFAULT: smscAgent"
   ::= 	7084

--

-- End of definition

--
-- Trap for table: smscPbbClear
--
smscPbbClearTrap TRAP-TYPE
	ENTERPRISE  smscAgent
	VARIABLES  {trapNotificationId, trapSeverity, trapData,
		smscPbbName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscPbbClear
		MANAGEDOBJECT-DEFAULT: smscAgent"
   ::= 	7085

--

-- End of definition

--
-- Trap for table: smscCmlog
--
smscCmlogTrap TRAP-TYPE
	ENTERPRISE  smscAgent
	VARIABLES  {trapNotificationId, trapSeverity, trapData,
		smscCmlogName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscCmlog
		MANAGEDOBJECT-DEFAULT: smscAgent"
   ::= 	709

--

-- End of definition

--
-- Trap for table: smscCmlogIndeterminate
--
smscCmlogIndeterminateTrap TRAP-TYPE
	ENTERPRISE  smscAgent
	VARIABLES  {trapNotificationId, trapSeverity, trapData,
		smscCmlogName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscCmlogIndeterminate
		MANAGEDOBJECT-DEFAULT: smscAgent"
   ::= 	7090

--

-- End of definition

--
-- Trap for table: smscCmlogCritical
--
smscCmlogCriticalTrap TRAP-TYPE
	ENTERPRISE  smscAgent
	VARIABLES  {trapNotificationId, trapSeverity, trapData,
		smscCmlogName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscCmlogCritical
		MANAGEDOBJECT-DEFAULT: smscAgent"
   ::= 	7091

--

-- End of definition

--
-- Trap for table: smscCmlogMajor
--
smscCmlogMajorTrap TRAP-TYPE
	ENTERPRISE  smscAgent
	VARIABLES  {trapNotificationId, trapSeverity, trapData,
		smscCmlogName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscCmlogMajor
		MANAGEDOBJECT-DEFAULT: smscAgent"
   ::= 	7092

--

-- End of definition

--
-- Trap for table: smscCmlogMinor
--
smscCmlogMinorTrap TRAP-TYPE
	ENTERPRISE  smscAgent
	VARIABLES  {trapNotificationId, trapSeverity, trapData,
		smscCmlogName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscCmlogMinor
		MANAGEDOBJECT-DEFAULT: smscAgent"
   ::= 	7093

--

-- End of definition

--
-- Trap for table: smscCmlogWarning
--
smscCmlogWarningTrap TRAP-TYPE
	ENTERPRISE  smscAgent
	VARIABLES  {trapNotificationId, trapSeverity, trapData,
		smscCmlogName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscCmlogWarning
		MANAGEDOBJECT-DEFAULT: smscAgent"
   ::= 	7094

--

-- End of definition

--
-- Trap for table: smscCmlogClear
--
smscCmlogClearTrap TRAP-TYPE
	ENTERPRISE  smscAgent
	VARIABLES  {trapNotificationId, trapSeverity, trapData,
		smscCmlogName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscCmlogClear
		MANAGEDOBJECT-DEFAULT: smscAgent"
   ::= 	7095

--

-- End of definition

--
-- Trap for table: smscIp7
--
smscIp7Trap TRAP-TYPE
	ENTERPRISE  smscAgent
	VARIABLES  {trapNotificationId, trapSeverity, trapData,
		smscIp7Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIp7
		MANAGEDOBJECT-DEFAULT: smscAgent"
   ::= 	710

--

-- End of definition

--
-- Trap for table: smscIp7Indeterminate
--
smscIp7IndeterminateTrap TRAP-TYPE
	ENTERPRISE  smscAgent
	VARIABLES  {trapNotificationId, trapSeverity, trapData,
		smscIp7Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIp7Indeterminate
		MANAGEDOBJECT-DEFAULT: smscAgent"
   ::= 	7100

--

-- End of definition

--
-- Trap for table: smscIp7Critical
--
smscIp7CriticalTrap TRAP-TYPE
	ENTERPRISE  smscAgent
	VARIABLES  {trapNotificationId, trapSeverity, trapData,
		smscIp7Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIp7Critical
		MANAGEDOBJECT-DEFAULT: smscAgent"
   ::= 	7101

--

-- End of definition

--
-- Trap for table: smscIp7Major
--
smscIp7MajorTrap TRAP-TYPE
	ENTERPRISE  smscAgent
	VARIABLES  {trapNotificationId, trapSeverity, trapData,
		smscIp7Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIp7Major
		MANAGEDOBJECT-DEFAULT: smscAgent"
   ::= 	7102

--

-- End of definition

--
-- Trap for table: smscIp7Minor
--
smscIp7MinorTrap TRAP-TYPE
	ENTERPRISE  smscAgent
	VARIABLES  {trapNotificationId, trapSeverity, trapData,
		smscIp7Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIp7Minor
		MANAGEDOBJECT-DEFAULT: smscAgent"
   ::= 	7103

--

-- End of definition

--
-- Trap for table: smscIp7Warning
--
smscIp7WarningTrap TRAP-TYPE
	ENTERPRISE  smscAgent
	VARIABLES  {trapNotificationId, trapSeverity, trapData,
		smscIp7Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIp7Warning
		MANAGEDOBJECT-DEFAULT: smscAgent"
   ::= 	7104

--

-- End of definition

--
-- Trap for table: smscIp7Clear
--
smscIp7ClearTrap TRAP-TYPE
	ENTERPRISE  smscAgent
	VARIABLES  {trapNotificationId, trapSeverity, trapData,
		smscIp7Name, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscIp7Clear
		MANAGEDOBJECT-DEFAULT: smscAgent"
   ::= 	7105

--

-- End of definition

--
-- Trap for table: smscLiw
--
smscLiwTrap TRAP-TYPE
	ENTERPRISE  smscAgent
	VARIABLES  {trapNotificationId, trapSeverity, trapData,
		smscLiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLiw
		MANAGEDOBJECT-DEFAULT: smscAgent"
   ::= 	711

--

-- End of definition

--
-- Trap for table: smscLiwIndeterminate
--
smscLiwIndeterminateTrap TRAP-TYPE
	ENTERPRISE  smscAgent
	VARIABLES  {trapNotificationId, trapSeverity, trapData,
		smscLiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLiwIndeterminate
		MANAGEDOBJECT-DEFAULT: smscAgent"
   ::= 	7110

--

-- End of definition

--
-- Trap for table: smscLiwCritical
--
smscLiwCriticalTrap TRAP-TYPE
	ENTERPRISE  smscAgent
	VARIABLES  {trapNotificationId, trapSeverity, trapData,
		smscLiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLiwCritical
		MANAGEDOBJECT-DEFAULT: smscAgent"
   ::= 	7111

--

-- End of definition

--
-- Trap for table: smscLiwMajor
--
smscLiwMajorTrap TRAP-TYPE
	ENTERPRISE  smscAgent
	VARIABLES  {trapNotificationId, trapSeverity, trapData,
		smscLiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLiwMajor
		MANAGEDOBJECT-DEFAULT: smscAgent"
   ::= 	7112

--

-- End of definition

--
-- Trap for table: smscLiwMinor
--
smscLiwMinorTrap TRAP-TYPE
	ENTERPRISE  smscAgent
	VARIABLES  {trapNotificationId, trapSeverity, trapData,
		smscLiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLiwMinor
		MANAGEDOBJECT-DEFAULT: smscAgent"
   ::= 	7113

--

-- End of definition

--
-- Trap for table: smscLiwWarning
--
smscLiwWarningTrap TRAP-TYPE
	ENTERPRISE  smscAgent
	VARIABLES  {trapNotificationId, trapSeverity, trapData,
		smscLiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLiwWarning
		MANAGEDOBJECT-DEFAULT: smscAgent"
   ::= 	7114

--

-- End of definition

--
-- Trap for table: smscLiwClear
--
smscLiwClearTrap TRAP-TYPE
	ENTERPRISE  smscAgent
	VARIABLES  {trapNotificationId, trapSeverity, trapData,
		smscLiwName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLiwClear
		MANAGEDOBJECT-DEFAULT: smscAgent"
   ::= 	7115

--

-- End of definition

--
-- Trap for table: smscStore
--
smscStoreTrap TRAP-TYPE
	ENTERPRISE  smscAgent
	VARIABLES  {trapNotificationId, trapSeverity, trapData,
		smscStoreName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscStore
		MANAGEDOBJECT-DEFAULT: smscAgent"
   ::= 	712

--

-- End of definition

--
-- Trap for table: smscStoreIndeterminate
--
smscStoreIndeterminateTrap TRAP-TYPE
	ENTERPRISE  smscAgent
	VARIABLES  {trapNotificationId, trapSeverity, trapData,
		smscStoreName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscStoreIndeterminate
		MANAGEDOBJECT-DEFAULT: smscAgent"
   ::= 	7120

--

-- End of definition

--
-- Trap for table: smscStoreCritical
--
smscStoreCriticalTrap TRAP-TYPE
	ENTERPRISE  smscAgent
	VARIABLES  {trapNotificationId, trapSeverity, trapData,
		smscStoreName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscStoreCritical
		MANAGEDOBJECT-DEFAULT: smscAgent"
   ::= 	7121

--

-- End of definition

--
-- Trap for table: smscStoreMajor
--
smscStoreMajorTrap TRAP-TYPE
	ENTERPRISE  smscAgent
	VARIABLES  {trapNotificationId, trapSeverity, trapData,
		smscStoreName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscStoreMajor
		MANAGEDOBJECT-DEFAULT: smscAgent"
   ::= 	7122

--

-- End of definition

--
-- Trap for table: smscStoreMinor
--
smscStoreMinorTrap TRAP-TYPE
	ENTERPRISE  smscAgent
	VARIABLES  {trapNotificationId, trapSeverity, trapData,
		smscStoreName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscStoreMinor
		MANAGEDOBJECT-DEFAULT: smscAgent"
   ::= 	7123

--

-- End of definition

--
-- Trap for table: smscStoreWarning
--
smscStoreWarningTrap TRAP-TYPE
	ENTERPRISE  smscAgent
	VARIABLES  {trapNotificationId, trapSeverity, trapData,
		smscStoreName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscStoreWarning
		MANAGEDOBJECT-DEFAULT: smscAgent"
   ::= 	7124

--

-- End of definition

--
-- Trap for table: smscStoreClear
--
smscStoreClearTrap TRAP-TYPE
	ENTERPRISE  smscAgent
	VARIABLES  {trapNotificationId, trapSeverity, trapData,
		smscStoreName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscStoreClear
		MANAGEDOBJECT-DEFAULT: smscAgent"
   ::= 	7125

--

-- End of definition

--
-- Trap for table: smscLaucp
--
smscLaucpTrap TRAP-TYPE
	ENTERPRISE  smscAgent
	VARIABLES  {trapNotificationId, trapSeverity, trapData,
		smscLaucpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLaucp
		MANAGEDOBJECT-DEFAULT: smscAgent"
   ::= 	713

--

-- End of definition

--
-- Trap for table: smscLaucpIndeterminate
--
smscLaucpIndeterminateTrap TRAP-TYPE
	ENTERPRISE  smscAgent
	VARIABLES  {trapNotificationId, trapSeverity, trapData,
		smscLaucpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLaucpIndeterminate
		MANAGEDOBJECT-DEFAULT: smscAgent"
   ::= 	7130

--

-- End of definition

--
-- Trap for table: smscLaucpCritical
--
smscLaucpCriticalTrap TRAP-TYPE
	ENTERPRISE  smscAgent
	VARIABLES  {trapNotificationId, trapSeverity, trapData,
		smscLaucpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLaucpCritical
		MANAGEDOBJECT-DEFAULT: smscAgent"
   ::= 	7131

--

-- End of definition

--
-- Trap for table: smscLaucpMajor
--
smscLaucpMajorTrap TRAP-TYPE
	ENTERPRISE  smscAgent
	VARIABLES  {trapNotificationId, trapSeverity, trapData,
		smscLaucpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLaucpMajor
		MANAGEDOBJECT-DEFAULT: smscAgent"
   ::= 	7132

--

-- End of definition

--
-- Trap for table: smscLaucpMinor
--
smscLaucpMinorTrap TRAP-TYPE
	ENTERPRISE  smscAgent
	VARIABLES  {trapNotificationId, trapSeverity, trapData,
		smscLaucpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLaucpMinor
		MANAGEDOBJECT-DEFAULT: smscAgent"
   ::= 	7133

--

-- End of definition

--
-- Trap for table: smscLaucpWarning
--
smscLaucpWarningTrap TRAP-TYPE
	ENTERPRISE  smscAgent
	VARIABLES  {trapNotificationId, trapSeverity, trapData,
		smscLaucpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLaucpWarning
		MANAGEDOBJECT-DEFAULT: smscAgent"
   ::= 	7134

--

-- End of definition

--
-- Trap for table: smscLaucpClear
--
smscLaucpClearTrap TRAP-TYPE
	ENTERPRISE  smscAgent
	VARIABLES  {trapNotificationId, trapSeverity, trapData,
		smscLaucpName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLaucpClear
		MANAGEDOBJECT-DEFAULT: smscAgent"
   ::= 	7135

--

-- End of definition

--
-- Trap for table: smscLasmpp
--
smscLasmppTrap TRAP-TYPE
	ENTERPRISE  smscAgent
	VARIABLES  {trapNotificationId, trapSeverity, trapData,
		smscLasmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLasmpp
		MANAGEDOBJECT-DEFAULT: smscAgent"
   ::= 	714

--

-- End of definition

--
-- Trap for table: smscLasmppIndeterminate
--
smscLasmppIndeterminateTrap TRAP-TYPE
	ENTERPRISE  smscAgent
	VARIABLES  {trapNotificationId, trapSeverity, trapData,
		smscLasmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLasmppIndeterminate
		MANAGEDOBJECT-DEFAULT: smscAgent"
   ::= 	7140

--

-- End of definition

--
-- Trap for table: smscLasmppCritical
--
smscLasmppCriticalTrap TRAP-TYPE
	ENTERPRISE  smscAgent
	VARIABLES  {trapNotificationId, trapSeverity, trapData,
		smscLasmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLasmppCritical
		MANAGEDOBJECT-DEFAULT: smscAgent"
   ::= 	7141

--

-- End of definition

--
-- Trap for table: smscLasmppMajor
--
smscLasmppMajorTrap TRAP-TYPE
	ENTERPRISE  smscAgent
	VARIABLES  {trapNotificationId, trapSeverity, trapData,
		smscLasmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLasmppMajor
		MANAGEDOBJECT-DEFAULT: smscAgent"
   ::= 	7142

--

-- End of definition

--
-- Trap for table: smscLasmppMinor
--
smscLasmppMinorTrap TRAP-TYPE
	ENTERPRISE  smscAgent
	VARIABLES  {trapNotificationId, trapSeverity, trapData,
		smscLasmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLasmppMinor
		MANAGEDOBJECT-DEFAULT: smscAgent"
   ::= 	7143

--

-- End of definition

--
-- Trap for table: smscLasmppWarning
--
smscLasmppWarningTrap TRAP-TYPE
	ENTERPRISE  smscAgent
	VARIABLES  {trapNotificationId, trapSeverity, trapData,
		smscLasmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLasmppWarning
		MANAGEDOBJECT-DEFAULT: smscAgent"
   ::= 	7144

--

-- End of definition

--
-- Trap for table: smscLasmppClear
--
smscLasmppClearTrap TRAP-TYPE
	ENTERPRISE  smscAgent
	VARIABLES  {trapNotificationId, trapSeverity, trapData,
		smscLasmppName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscLasmppClear
		MANAGEDOBJECT-DEFAULT: smscAgent"
   ::= 	7145

--

-- End of definition

--
-- Trap for table: smscMd
--
smscMdTrap TRAP-TYPE
	ENTERPRISE  smscAgent
	VARIABLES  {trapNotificationId, trapSeverity, trapData,
		smscMdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscMd
		MANAGEDOBJECT-DEFAULT: smscAgent"
   ::= 	800

--

-- End of definition

--
-- Trap for table: smscMdIndeterminate
--
smscMdIndeterminateTrap TRAP-TYPE
	ENTERPRISE  smscAgent
	VARIABLES  {trapNotificationId, trapSeverity, trapData,
		smscMdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscMdIndeterminate
		MANAGEDOBJECT-DEFAULT: smscAgent"
   ::= 	8000

--

-- End of definition

--
-- Trap for table: smscMdCritical
--
smscMdCriticalTrap TRAP-TYPE
	ENTERPRISE  smscAgent
	VARIABLES  {trapNotificationId, trapSeverity, trapData,
		smscMdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscMdCritical
		MANAGEDOBJECT-DEFAULT: smscAgent"
   ::= 	8001

--

-- End of definition

--
-- Trap for table: smscMdMajor
--
smscMdMajorTrap TRAP-TYPE
	ENTERPRISE  smscAgent
	VARIABLES  {trapNotificationId, trapSeverity, trapData,
		smscMdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscMdMajor
		MANAGEDOBJECT-DEFAULT: smscAgent"
   ::= 	8002

--

-- End of definition

--
-- Trap for table: smscMdMinor
--
smscMdMinorTrap TRAP-TYPE
	ENTERPRISE  smscAgent
	VARIABLES  {trapNotificationId, trapSeverity, trapData,
		smscMdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscMdMinor
		MANAGEDOBJECT-DEFAULT: smscAgent"
   ::= 	8003

--

-- End of definition

--
-- Trap for table: smscMdWarning
--
smscMdWarningTrap TRAP-TYPE
	ENTERPRISE  smscAgent
	VARIABLES  {trapNotificationId, trapSeverity, trapData,
		smscMdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscMdWarning
		MANAGEDOBJECT-DEFAULT: smscAgent"
   ::= 	8004

--

-- End of definition

--
-- Trap for table: smscMdClear
--
smscMdClearTrap TRAP-TYPE
	ENTERPRISE  smscAgent
	VARIABLES  {trapNotificationId, trapSeverity, trapData,
		smscMdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscMdClear
		MANAGEDOBJECT-DEFAULT: smscAgent"
   ::= 	8005

--

-- End of definition

--
-- Trap for table: smscAd
--
smscAdTrap TRAP-TYPE
	ENTERPRISE  smscAgent
	VARIABLES  {trapNotificationId, trapSeverity, trapData,
		smscAdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscAd
		MANAGEDOBJECT-DEFAULT: smscAgent"
   ::= 	801

--

-- End of definition

--
-- Trap for table: smscAdIndeterminate
--
smscAdIndeterminateTrap TRAP-TYPE
	ENTERPRISE  smscAgent
	VARIABLES  {trapNotificationId, trapSeverity, trapData,
		smscAdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscAdIndeterminate
		MANAGEDOBJECT-DEFAULT: smscAgent"
   ::= 	8010

--

-- End of definition

--
-- Trap for table: smscAdCritical
--
smscAdCriticalTrap TRAP-TYPE
	ENTERPRISE  smscAgent
	VARIABLES  {trapNotificationId, trapSeverity, trapData,
		smscAdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscAdCritical
		MANAGEDOBJECT-DEFAULT: smscAgent"
   ::= 	8011

--

-- End of definition

--
-- Trap for table: smscAdMajor
--
smscAdMajorTrap TRAP-TYPE
	ENTERPRISE  smscAgent
	VARIABLES  {trapNotificationId, trapSeverity, trapData,
		smscAdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscAdMajor
		MANAGEDOBJECT-DEFAULT: smscAgent"
   ::= 	8012

--

-- End of definition

--
-- Trap for table: smscAdMinor
--
smscAdMinorTrap TRAP-TYPE
	ENTERPRISE  smscAgent
	VARIABLES  {trapNotificationId, trapSeverity, trapData,
		smscAdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscAdMinor
		MANAGEDOBJECT-DEFAULT: smscAgent"
   ::= 	8013

--

-- End of definition

--
-- Trap for table: smscAdWarning
--
smscAdWarningTrap TRAP-TYPE
	ENTERPRISE  smscAgent
	VARIABLES  {trapNotificationId, trapSeverity, trapData,
		smscAdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscAdWarning
		MANAGEDOBJECT-DEFAULT: smscAgent"
   ::= 	8014

--

-- End of definition

--
-- Trap for table: smscAdClear
--
smscAdClearTrap TRAP-TYPE
	ENTERPRISE  smscAgent
	VARIABLES  {trapNotificationId, trapSeverity, trapData,
		smscAdName, trapTimeStamp, trapNodeName}
	DESCRIPTION
		"This is the trap definition to handle an SMSC entity events. This
		trap belongs to a specific entity class indicated in the following
		TeMIP specific clauses.
		NOTIFICATIONID-VARIABLE: trapNotificationId
		SEVERITY-VARIABLE: trapSeverity
		ADDITIONAL-TEXT-VARIABLES: {trapData}
		MANAGEDOBJECT-TABLE: smscAdClear
		MANAGEDOBJECT-DEFAULT: smscAgent"
   ::= 	8015

--

-- End of definition


END

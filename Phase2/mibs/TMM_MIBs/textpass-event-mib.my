------------------------------------------------------------------------------
--
-- (c) Copyright 2001-2010 mBalance.
--
--  This MIB is proprietary to and embodies the confidential technology of
--  mBalance. Possession, use, duplication or dissemination of this MIB is
--  authorized only pursuant to a valid written license from mBalance.
--
------------------------------------------------------------------------------
--
-- File    : textpass-event-mib.my
-- Release : R04.01
-- $Id: textpass-event-mib.my,v 1.3 2009/09/30 10:25:34 psheer Exp $
-- $Revision: 1.3 $
------------------------------------------------------------------------------

    TEXTPASS-EVENT-MIB DEFINITIONS ::= BEGIN

    IMPORTS
        Gauge
            FROM RFC1155-SMI
        TEXTUAL-CONVENTION
            FROM SNMPv2-TC
        textpass
            FROM MBALANCE-MIB
        OBJECT-TYPE
            FROM RFC-1212;

    ----------------------------------------------------------------------------
    --                                T Y P E S                               --
    ----------------------------------------------------------------------------

    AdminState ::=
        INTEGER {
            inactive(0),
            active(1),
            destroy(2)
        }

    Boolean ::=
        INTEGER {
            false(0),
            true(1)
        }

    ----------------------------------------------------------------------------
    --  FileSpec specifies a full filename or full directory name.
    ----------------------------------------------------------------------------

    FileSpec ::=
        OCTET STRING (SIZE (0..255))

    ----------------------------------------------------------------------------
    --  NameString defines the string used for names.
    ----------------------------------------------------------------------------

    NameString ::= TEXTUAL-CONVENTION
        DISPLAY-HINT "31a"
        STATUS mandatory
        DESCRIPTION "Represent names to identify objects"
        SYNTAX OCTET STRING (SIZE (1..31))


    ----------------------------------------------------------------------------
    --
    --  EventProfile types:
    --
    --     EventFileSize         -      File size limit range from 1kB to 1GB.
    --     EventFileDuration     -      1 seconds to 1 month.
    --
    ----------------------------------------------------------------------------

    EventProfileTableIndex ::=
        INTEGER (1..100)

    EventLogCopyTableIndex ::=
        INTEGER (1..10)

    EventProfileErrorString ::= TEXTUAL-CONVENTION
        DISPLAY-HINT "0124a"
        STATUS mandatory
        DESCRIPTION "String containing an error message"
        SYNTAX OCTET STRING (SIZE (0..1024))

    EventFileSize ::=
        Gauge(1024..1073741824)

    EventFileDuration ::=
        Gauge(1..2678400)

    EventFileRecords ::=
        Gauge(1..10000000)


    ----------------------------------------------------------------------------
    --                Definition of the event logging subsystem
    ----------------------------------------------------------------------------

    event OBJECT IDENTIFIER ::= { textpass 3 }

    ----------------------------------------------------------------------
    -- the Event Logging group
    ----------------------------------------------------------------------

    eventProperties OBJECT IDENTIFIER ::= { event 1 }

    eventPropResetSequenceNumberOfLoggingProfileUponDestroy OBJECT-TYPE     
        SYNTAX  Boolean
        ACCESS  read-write
        STATUS  mandatory
        DESCRIPTION
            "Boolean specifying whether destroying a logging profile should 
            imply a reset of the associated sequence number in the permanent 
            storage that TextPass maintains for logging profile sequence 
            numbers. Default is 'true'.      
            The sequence number that is maintained for a logging profile is 
            (optionally) used in the names of the CDR files that are generated
            for the logging profile.
            Resetting the logging profile sequence number is required to
            ensure that a newly added logging profile that is mapped to a
            table index that has been used before has a properly initialised
            sequence number (rather than the sequence number of the logging
            profile that was mapped to the same table index before).
            The value 'false' is typically used when a logging profile is
            temporary removed. Not resetting the sequence number will then
            ensure that the sequence number after removal will commence from
            the value before the removal."
        ::= { eventProperties 1 }

    eventProfileTable OBJECT-TYPE
        SYNTAX  SEQUENCE OF EventProfileEntry
        ACCESS  not-accessible
        STATUS  mandatory
        DESCRIPTION
            "A table containing profiles for logging."
        ::= { event 2 }

    eventProfileEntry OBJECT-TYPE
        SYNTAX  EventProfileEntry
        ACCESS  not-accessible
        STATUS  mandatory
        DESCRIPTION
            "Table entry specifying a single logging profile."
        INDEX   { eventProfileIndex }
        ::= { eventProfileTable 1 }

    EventProfileEntry ::=
        SEQUENCE {
            eventProfileIndex                       EventProfileTableIndex,
            eventProfileAdminState                  AdminState,
            eventProfileName                        NameString,
            eventProfileLastIoError                 EventProfileErrorString,
            eventProfileProcessingDirectory         FileSpec,
            eventProfileFinishedDirectory           FileSpec,
            eventProfileFileNameTemplate            FileSpec,
            eventProfileMaxFileSize                 EventFileSize,
            eventProfileMaxFileDuration             EventFileDuration,
            eventProfileMaxFileRecords              EventFileRecords,
            eventProfileStartingSequenceNumber      Gauge
        }

    eventProfileIndex OBJECT-TYPE
        SYNTAX  EventProfileTableIndex
        ACCESS  read-write
        STATUS  mandatory
        DESCRIPTION
            "Index of entry in logging profile table."
        ::= { eventProfileEntry 1 }

    eventProfileAdminState OBJECT-TYPE
        SYNTAX  AdminState
        ACCESS  read-write
        STATUS  mandatory
        DESCRIPTION
            "Administrative state of logging profile. To change to an active
            state, the field eventProfileFileNameTemplate must be set and
            any directories that have been set to non-default values must
            exist and have writable access permissions."
        ::= { eventProfileEntry 2 }

    eventProfileName OBJECT-TYPE
        SYNTAX  NameString
        ACCESS  read-write
        STATUS  mandatory
        DESCRIPTION
            "Name of logging profile. This must unique among all profiles."
        ::= { eventProfileEntry 3 }

    eventProfileLastIoError OBJECT-TYPE
        SYNTAX  EventProfileErrorString
        ACCESS  read-write
        STATUS  mandatory
        DESCRIPTION
            "Information about last I/O error that occurred for the 
            logging profile. The information comprises timestamp, file name,
            and error description."
        ::= { eventProfileEntry 4 }

    eventProfileProcessingDirectory OBJECT-TYPE
        SYNTAX  FileSpec
        ACCESS  read-write
        STATUS  mandatory
        DESCRIPTION
            "Specification of the directory which is used for the logging
            files during the creation of these files. Default is
            /var/TextPass/log/processing.
            Note: this setting can only be changed when the device adminState
            is disabled."
        ::= { eventProfileEntry 5 }

    eventProfileFinishedDirectory OBJECT-TYPE
        SYNTAX  FileSpec
        ACCESS  read-write
        STATUS  mandatory
        DESCRIPTION
            "Specification of the directory where the logging files are stored
            when they are completed. This directory should be on the same disc
            partition as the eventProfileProcessingDirectory.
            Default is /var/TextPass/log/available.
            Note: this setting can only be changed when the device adminState
            is disabled."
        ::= { eventProfileEntry 6 }

    eventProfileFileNameTemplate OBJECT-TYPE
        SYNTAX  FileSpec
        ACCESS  read-write
        STATUS  mandatory
        DESCRIPTION
            "String specifying the format for the name of the logging file.
            The following format specifiers are supported:
            %Y - year specified in four digits (e.g. 2004)
            %y - year specified in two digits (e.g. 04)
            %m - month specified in two digits (e.g. 01 for Jan, 10 for Oct)
            %d - day specified in two digits (e.g 01 for 1st day of month, 31
                                              for last day of month)
            %H - hour specified in two digits (e.g 00 for midnight, 12 for
                                               noon)
            %M - minute specified in two digits
            %S - second specified in two digits
            %h - hostname
            %1 - a one-digit sequence number
            %2 - a two-digit sequence number
            %3 - a three-digit sequence number
            %4 - a four-digit sequence number
            %5 - a five-digit sequence number
            %6 - a six-digit sequence number
            %7 - a seven-digit sequence number
            %8 - a eight-digit sequence number

            Default is: event_%h_%Y%m%d_%H%M%S_%3.dat"
        ::= { eventProfileEntry 7 }

    eventProfileMaxFileSize OBJECT-TYPE
        SYNTAX  EventFileSize
        ACCESS  read-write
        STATUS  mandatory
        DESCRIPTION
            "Specification of maximum length, expressed in bytes, for a
            logging file. Default is 1M."
        ::= { eventProfileEntry 8 }

    eventProfileMaxFileDuration OBJECT-TYPE
        SYNTAX  EventFileDuration
        ACCESS  read-write
        STATUS  mandatory
        DESCRIPTION
            "Specification of maximum duration, expressed in seconds, for a
            logging file. Default is 1 hour."
        ::= { eventProfileEntry 9 }

    eventProfileMaxFileRecords OBJECT-TYPE
        SYNTAX  EventFileRecords
        ACCESS  read-write
        STATUS  mandatory
        DESCRIPTION
            "Specification of maximum number of records in a logging file.
            Default is 10000."
        ::= { eventProfileEntry 10 }

    eventProfileStartingSequenceNumber OBJECT-TYPE
        SYNTAX  Gauge
        ACCESS  read-write
        STATUS  mandatory
        DESCRIPTION
            "Start of range of sequence numbers to be used in the logging
            file name. May only be increased - otherwise the set action is
            ignored. Default is 0."
        ::= { eventProfileEntry 11 }

    eventLogCopyTable OBJECT-TYPE
        SYNTAX  SEQUENCE OF EventLogCopyEntry
        ACCESS  not-accessible
        STATUS  mandatory
        DESCRIPTION
            "Table of directories lists for copies of log records."
        ::= { event 3 }

    eventLogCopyEntry OBJECT-TYPE
        SYNTAX  EventLogCopyEntry
        ACCESS  not-accessible
        STATUS  mandatory
        DESCRIPTION
            "Table entry of directory for copy of log records."
        INDEX   { eventLogCopyIndex1, eventLogCopyIndex2 }
        ::= { eventLogCopyTable 1 }

    EventLogCopyEntry ::=
        SEQUENCE {
            eventLogCopyIndex1                         EventProfileTableIndex,
            eventLogCopyIndex2                         EventLogCopyTableIndex,
            eventLogCopyDirectory                      FileSpec
        }

    eventLogCopyIndex1 OBJECT-TYPE
        SYNTAX  EventProfileTableIndex
        ACCESS  read-write
        STATUS  mandatory
        DESCRIPTION
            "Index of copy directories."
        ::= { eventLogCopyEntry 1 }

    eventLogCopyIndex2 OBJECT-TYPE
        SYNTAX  EventLogCopyTableIndex
        ACCESS  read-write
        STATUS  mandatory
        DESCRIPTION
            "Index of copy directories."
        ::= { eventLogCopyEntry 2 }

    eventLogCopyDirectory OBJECT-TYPE
        SYNTAX  FileSpec
        ACCESS  read-write
        STATUS  mandatory
        DESCRIPTION
            "Specification of a directory in which to create hard links to
            the finished logging files. A hard link is created at the time
            that the logging file is moved from the processing directory to
            the finished directory. 
            The default for this specification is a zero-length string, which 
            implies that no hard links are to be created.
            When a directory is specified, it should reside on the same disc
            partition as the eventProfileProcessingDirectory and 
            eventProfileFinishedDirectory.
            Note: this setting can only be changed when the device adminState
            is disabled."
        ::= { eventLogCopyEntry 3 }
  
END

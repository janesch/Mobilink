-- ----------------------------------------------------------------------------------------------
-- S M I V 1   F O R   G L E N A Y R E   P R O D U C T S
-- 
-- Generated by	: Mahindra British Telecom Ltd. (MBT)
-- Date		: 14 February 2001
-- Description	: This SMI describes the MIB structure for Glenayre products. 
--
-- 	S.No.	| Change Date 	| Change Number		| Author 		| Description
--
--	1    	  17/09/2001                      	         	  	  The field entity instance ID
--	 	 	  					  	 	  changed to octet string
--								  		  to support 64 bit entity
--							 	  		  instance ID.
--				  					  	  Traps related data added for
--								 	  	  trap notification of ASU generated
-- 	2   	  26/09/2002                      	  Ang Yeow Sien	  	  Add SGF Trap Type   	 
--										  Correct errors to allow MIB loading
--	3	  11/12/2002				  Carrie Yeo		  Add 3 new OIDs to support SMU (Fred
--										  extension to SMU)
--										  Change the activeAlarmsTable's OID
--	4	  10/02/2003				  Carrie Yeo		  Add the MIB for Fred's Doc Server(TUI)
--	5	  25/04/2003				  Carrie Yeo/Shuk Hui	  Change Version No from int to string
--										  Change Text Description to 300 bytes max
--										  added SGF MIB (needs verifications)
--      6         23/07/2003				  Carrie Yeo		  Change activeAlarmSend to be a write
--										  only and with IpAddress as syntax
--      7         30/07/2003				  Shuk Hui		  Add CDMS table to and remove lastSgfAlarm
--                                                                                from SGF MIB 
--      8         11/09/2003				  Carrie Yeo 		  Make it more compatible with SMI tools
--      9         29/09/2003				  Carrie Yeo		  ASU traps should be under 1383.1011.2
--	10	  19/04/2004				  Carrie Yeo		  Add two stats var for TUI MIB
--										  Add Trap IDs for 2000.2 to 2000.11
--	11	  30/04/2004				  Carrie Yeo		  Change to MyServices (2000.11) and 
--										  mmvgw (2000.10)
--	12	  31/05/2004				  Shuk Hui		  Changed stats name and removed stats for
--                                                                                TUI MIB
--   
--
-- ----------------------------------------------------------------------------------------------

GLENAYRE-ILSP2-ASU-ALARMS-MIB DEFINITIONS ::= BEGIN

	IMPORTS
		enterprises, Counter, IpAddress
			FROM RFC1155-SMI
		OBJECT-TYPE
			FROM RFC-1212
		TRAP-TYPE
			FROM RFC-1215;

 	glenayre 	OBJECT IDENTIFIER ::= { enterprises 1383 } 
 	asu 		OBJECT IDENTIFIER ::= { glenayre 1011 }
 	sgf 		OBJECT IDENTIFIER ::= { glenayre 1012 }
	fred		OBJECT IDENTIFIER ::= { glenayre 2000 } 
	tui 		OBJECT IDENTIFIER ::= { fred 1 }
	msgdur 		OBJECT IDENTIFIER ::= { fred 2 }
	mrs 		OBJECT IDENTIFIER ::= { fred 3 }
	tsselect	OBJECT IDENTIFIER ::= { fred 4 }
	ons		OBJECT IDENTIFIER ::= { fred 5 }
	fms 		OBJECT IDENTIFIER ::= { fred 6 }
	snmpagent	OBJECT IDENTIFIER ::= { fred 7 }
	ngms 		OBJECT IDENTIFIER ::= { fred 8 }
	ahm 		OBJECT IDENTIFIER ::= { fred 9 }
	mmvgw		OBJECT IDENTIFIER ::= { fred 10 }
	myservices 	OBJECT IDENTIFIER ::= { fred 11 }

	asuActiveAlarms OBJECT IDENTIFIER ::= {asu 1}
	asuTrap OBJECT IDENTIFIER ::= {asu 2}
	
-- ----------------------------------------------------------------------------------------------
-- C O M M O N   D A T A   T Y P E S
-- ----------------------------------------------------------------------------------------------

-- The following are the common data types used in counters for Connection request, 
-- registration request, deregistration request and disconnection requests

	-- Complex Key ID is used to resolve various entires in the table.
	-- This is formed by combination of :
	ComplexKeyId ::= OCTET STRING (SIZE(3..10))

	-- Application Instance id used in alarming allocated dynamically at run-time by ASU
	ApplicationInstanceId ::= INTEGER

	-- Entity Instance id used in alarming to notify the instance of alarm.
        EntityInstanceId ::= OCTET STRING (SIZE(5..15))

        -- Process identity of the alarming entity
        ProcessId ::= INTEGER

        -- Describes the severity of the alarm (CRITICAL, MAJOR, MINOR, INFO)
        AlarmSeverity ::= OCTET STRING (SIZE(3..10))

        -- Describes the actions pertaining to the alarm
        ActionType ::= OCTET STRING (SIZE(3..10))

        -- Describes the status of alarms (RAISE, ACKNOWLEDGE, RETIRE)
        AlarmStatus ::= OCTET STRING (SIZE(3..10))

        -- Gives the testual description of alarm
        TextDescription ::= OCTET STRING (SIZE(3..300))

        -- Describes the list of actions (to be specified)
        ListofAction ::= OCTET STRING (SIZE(3..10))

        -- Event ID represents the identity of event.
        EventId ::= INTEGER
	
	-- The host name used in alarming
	HostName ::= OCTET STRING (SIZE(5..15))
	
	-- Application type used in alarming used here as a alphanumeric string identifier for instance
	Apptype ::= OCTET STRING (SIZE(3..10))

	-- The version number field of applciation
	VersionNo ::= OCTET STRING (SIZE(3..10))     

	-- The location code of the event occurence area.
	LocationCode ::= INTEGER         
        
	-- The time of event occurence.
	Timestamp ::= OCTET STRING (SIZE(3..20))

        -- The general description of alarm; value taken from Event's decription
        EventDescription ::= OCTET STRING (SIZE(3..100))


-- ----------------------------------------------------------------------------------------------
-- ENTERPRISE TRAP TYPE
-- ----------------------------------------------------------------------------------------------

	-- Events classified as critical on the ASU application will assert this trap
	asuCriticalAlarm TRAP-TYPE
		ENTERPRISE asuTrap
		VARIABLES {complexKeyId, applicationInstanceId,	entityInstanceId, processId, alarmSeverity, actionType, alarmStatus, textDescription, listofAction, eventId, hostName, apptype, versionNo, locationCode, timestamp, eventDescription}
		::= 1
	
	-- Events classified as major on the ASU application will assert this trap
	asuMajorAlarm TRAP-TYPE
		ENTERPRISE asuTrap
		VARIABLES {complexKeyId, applicationInstanceId,	entityInstanceId, processId, alarmSeverity, actionType, alarmStatus, textDescription, listofAction, eventId, hostName, apptype, versionNo, locationCode, timestamp, eventDescription}
		::= 2
		
	-- Events classified as minor on the ASU application will assert this trap
	asuMinorAlarm TRAP-TYPE
		ENTERPRISE asuTrap
		VARIABLES {complexKeyId, applicationInstanceId,	entityInstanceId, processId, alarmSeverity, actionType, alarmStatus, textDescription, listofAction, eventId, hostName, apptype, versionNo, locationCode, timestamp, eventDescription}
		::= 3
		
	-- Events classified as notification on the ASU application will assert this trap
	asuNotificationAlarm TRAP-TYPE
		ENTERPRISE asuTrap
		VARIABLES {complexKeyId, applicationInstanceId,	entityInstanceId, processId, alarmSeverity, actionType, alarmStatus, textDescription, listofAction, eventId, hostName, apptype, versionNo, locationCode, timestamp, eventDescription}
		::= 4            

        -- Events classified as critical on the SGF application will assert this trap
        sgfCriticalAlarm TRAP-TYPE
                ENTERPRISE sgf
		VARIABLES {complexKeyId, applicationInstanceId,	entityInstanceId, processId, alarmSeverity, actionType, alarmStatus, textDescription, listofAction, eventId, hostName, apptype, versionNo, locationCode, timestamp, eventDescription}
                ::= 1

        -- Events classified as major on the SGF application will assert this trap
        sgfMajorAlarm TRAP-TYPE
                ENTERPRISE sgf
		VARIABLES {complexKeyId, applicationInstanceId,	entityInstanceId, processId, alarmSeverity, actionType, alarmStatus, textDescription, listofAction, eventId, hostName, apptype, versionNo, locationCode, timestamp, eventDescription}
                ::= 2

        -- Events classified as minor on the SGF application will assert this trap
        sgfMinorAlarm TRAP-TYPE
                ENTERPRISE sgf
		VARIABLES {complexKeyId, applicationInstanceId,	entityInstanceId, processId, alarmSeverity, actionType, alarmStatus, textDescription, listofAction, eventId, hostName, apptype, versionNo, locationCode, timestamp, eventDescription}
               ::= 3

        -- Events classified as notification on the SGF application will assert this trap
        sgfNotificationAlarm TRAP-TYPE
                ENTERPRISE sgf
		VARIABLES {complexKeyId, applicationInstanceId,	entityInstanceId, processId, alarmSeverity, actionType, alarmStatus, textDescription, listofAction, eventId, hostName, apptype, versionNo, locationCode, timestamp, eventDescription}
                ::= 4

        -- Events classified as critical on the TUI application will assert this trap
        tuiCriticalAlarm TRAP-TYPE
                ENTERPRISE tui
		VARIABLES {complexKeyId, applicationInstanceId,	entityInstanceId, processId, alarmSeverity, actionType, alarmStatus, textDescription, listofAction, eventId, hostName, apptype, versionNo, locationCode, timestamp, eventDescription}
                ::= 1

        -- Events classified as major on the TUI application will assert this trap
        tuiMajorAlarm TRAP-TYPE
                ENTERPRISE tui
		VARIABLES {complexKeyId, applicationInstanceId,	entityInstanceId, processId, alarmSeverity, actionType, alarmStatus, textDescription, listofAction, eventId, hostName, apptype, versionNo, locationCode, timestamp, eventDescription}
                ::= 2

        -- Events classified as minor on the TUI application will assert this trap
        tuiMinorAlarm TRAP-TYPE
                ENTERPRISE tui
		VARIABLES {complexKeyId, applicationInstanceId,	entityInstanceId, processId, alarmSeverity, actionType, alarmStatus, textDescription, listofAction, eventId, hostName, apptype, versionNo, locationCode, timestamp, eventDescription}
                ::= 3

        -- Events classified as notification on the TUI application will assert this trap
        tuiNotificationAlarm TRAP-TYPE
                ENTERPRISE tui
		VARIABLES {complexKeyId, applicationInstanceId,	entityInstanceId, processId, alarmSeverity, actionType, alarmStatus, textDescription, listofAction, eventId, hostName, apptype, versionNo, locationCode, timestamp, eventDescription}
                ::= 4

        -- Events classified as critical on the MSGDUR application will assert this trap
        msgdurCriticalAlarm TRAP-TYPE
                ENTERPRISE msgdur
		VARIABLES {complexKeyId, applicationInstanceId,	entityInstanceId, processId, alarmSeverity, actionType, alarmStatus, textDescription, listofAction, eventId, hostName, apptype, versionNo, locationCode, timestamp, eventDescription}
                ::= 1

        -- Events classified as major on the MSGDUR application will assert this trap
        msgdurMajorAlarm TRAP-TYPE
                ENTERPRISE msgdur
		VARIABLES {complexKeyId, applicationInstanceId,	entityInstanceId, processId, alarmSeverity, actionType, alarmStatus, textDescription, listofAction, eventId, hostName, apptype, versionNo, locationCode, timestamp, eventDescription}
                ::= 2

        -- Events classified as minor on the MSGDUR application will assert this trap
        msgdurMinorAlarm TRAP-TYPE
                ENTERPRISE msgdur
		VARIABLES {complexKeyId, applicationInstanceId,	entityInstanceId, processId, alarmSeverity, actionType, alarmStatus, textDescription, listofAction, eventId, hostName, apptype, versionNo, locationCode, timestamp, eventDescription}
                ::= 3

        -- Events classified as notification on the MSGDUR application will assert this trap
        msgdurNotificationAlarm TRAP-TYPE
                ENTERPRISE msgdur
		VARIABLES {complexKeyId, applicationInstanceId,	entityInstanceId, processId, alarmSeverity, actionType, alarmStatus, textDescription, listofAction, eventId, hostName, apptype, versionNo, locationCode, timestamp, eventDescription}
                ::= 4

        -- Events classified as critical on the mrs application will assert this trap
        mrsCriticalAlarm TRAP-TYPE
                ENTERPRISE mrs
		VARIABLES {complexKeyId, applicationInstanceId,	entityInstanceId, processId, alarmSeverity, actionType, alarmStatus, textDescription, listofAction, eventId, hostName, apptype, versionNo, locationCode, timestamp, eventDescription}
                ::= 1

        -- Events classified as major on the mrs application will assert this trap
        mrsMajorAlarm TRAP-TYPE
                ENTERPRISE mrs
		VARIABLES {complexKeyId, applicationInstanceId,	entityInstanceId, processId, alarmSeverity, actionType, alarmStatus, textDescription, listofAction, eventId, hostName, apptype, versionNo, locationCode, timestamp, eventDescription}
                ::= 2

        -- Events classified as minor on the mrs application will assert this trap
        mrsMinorAlarm TRAP-TYPE
                ENTERPRISE mrs
		VARIABLES {complexKeyId, applicationInstanceId,	entityInstanceId, processId, alarmSeverity, actionType, alarmStatus, textDescription, listofAction, eventId, hostName, apptype, versionNo, locationCode, timestamp, eventDescription}
                ::= 3

        -- Events classified as notification on the mrs application will assert this trap
        mrsNotificationAlarm TRAP-TYPE
                ENTERPRISE mrs
		VARIABLES {complexKeyId, applicationInstanceId,	entityInstanceId, processId, alarmSeverity, actionType, alarmStatus, textDescription, listofAction, eventId, hostName, apptype, versionNo, locationCode, timestamp, eventDescription}
                ::= 4

        -- Events classified as critical on the ts-select application will assert this trap
        tsselectCriticalAlarm TRAP-TYPE
                ENTERPRISE tsselect
		VARIABLES {complexKeyId, applicationInstanceId,	entityInstanceId, processId, alarmSeverity, actionType, alarmStatus, textDescription, listofAction, eventId, hostName, apptype, versionNo, locationCode, timestamp, eventDescription}
                ::= 1

        -- Events classified as major on the ts-select application will assert this trap
        tsselectMajorAlarm TRAP-TYPE
                ENTERPRISE tsselect
		VARIABLES {complexKeyId, applicationInstanceId,	entityInstanceId, processId, alarmSeverity, actionType, alarmStatus, textDescription, listofAction, eventId, hostName, apptype, versionNo, locationCode, timestamp, eventDescription}
                ::= 2

        -- Events classified as minor on the ts-select application will assert this trap
        tsselectMinorAlarm TRAP-TYPE
                ENTERPRISE tsselect
		VARIABLES {complexKeyId, applicationInstanceId,	entityInstanceId, processId, alarmSeverity, actionType, alarmStatus, textDescription, listofAction, eventId, hostName, apptype, versionNo, locationCode, timestamp, eventDescription}
                ::= 3

        -- Events classified as notification on the ts-select application will assert this trap
        tsselectNotificationAlarm TRAP-TYPE
                ENTERPRISE tsselect
		VARIABLES {complexKeyId, applicationInstanceId,	entityInstanceId, processId, alarmSeverity, actionType, alarmStatus, textDescription, listofAction, eventId, hostName, apptype, versionNo, locationCode, timestamp, eventDescription}
                ::= 4

        -- Events classified as critical on the ons application will assert this trap
        onsCriticalAlarm TRAP-TYPE
                ENTERPRISE ons 
		VARIABLES {complexKeyId, applicationInstanceId,	entityInstanceId, processId, alarmSeverity, actionType, alarmStatus, textDescription, listofAction, eventId, hostName, apptype, versionNo, locationCode, timestamp, eventDescription}
                ::= 1

        -- Events classified as major on the ons application will assert this trap
        onsMajorAlarm TRAP-TYPE
                ENTERPRISE ons 
		VARIABLES {complexKeyId, applicationInstanceId,	entityInstanceId, processId, alarmSeverity, actionType, alarmStatus, textDescription, listofAction, eventId, hostName, apptype, versionNo, locationCode, timestamp, eventDescription}
                ::= 2

        -- Events classified as minor on the ons application will assert this trap
        onsMinorAlarm TRAP-TYPE
                ENTERPRISE ons 
		VARIABLES {complexKeyId, applicationInstanceId,	entityInstanceId, processId, alarmSeverity, actionType, alarmStatus, textDescription, listofAction, eventId, hostName, apptype, versionNo, locationCode, timestamp, eventDescription}
                ::= 3

        -- Events classified as notification on the ons application will assert this trap
        onsNotificationAlarm TRAP-TYPE
                ENTERPRISE ons 
		VARIABLES {complexKeyId, applicationInstanceId,	entityInstanceId, processId, alarmSeverity, actionType, alarmStatus, textDescription, listofAction, eventId, hostName, apptype, versionNo, locationCode, timestamp, eventDescription}
                ::= 4

        -- Events classified as critical on the fms application will assert this trap
        fmsCriticalAlarm TRAP-TYPE
                ENTERPRISE fms 
		VARIABLES {complexKeyId, applicationInstanceId,	entityInstanceId, processId, alarmSeverity, actionType, alarmStatus, textDescription, listofAction, eventId, hostName, apptype, versionNo, locationCode, timestamp, eventDescription}
                ::= 1

        -- Events classified as major on the fms application will assert this trap
        fmsMajorAlarm TRAP-TYPE
                ENTERPRISE fms 
		VARIABLES {complexKeyId, applicationInstanceId,	entityInstanceId, processId, alarmSeverity, actionType, alarmStatus, textDescription, listofAction, eventId, hostName, apptype, versionNo, locationCode, timestamp, eventDescription}
                ::= 2

        -- Events classified as minor on the fms application will assert this trap
        fmsMinorAlarm TRAP-TYPE
                ENTERPRISE fms 
		VARIABLES {complexKeyId, applicationInstanceId,	entityInstanceId, processId, alarmSeverity, actionType, alarmStatus, textDescription, listofAction, eventId, hostName, apptype, versionNo, locationCode, timestamp, eventDescription}
                ::= 3

        -- Events classified as notification on the fms application will assert this trap
        fmsNotificationAlarm TRAP-TYPE
                ENTERPRISE fms 
		VARIABLES {complexKeyId, applicationInstanceId,	entityInstanceId, processId, alarmSeverity, actionType, alarmStatus, textDescription, listofAction, eventId, hostName, apptype, versionNo, locationCode, timestamp, eventDescription}
                ::= 4

        -- Events classified as critical on the SNMP Agent application will assert this trap
        snmpagentCriticalAlarm TRAP-TYPE
                ENTERPRISE snmpagent
		VARIABLES {complexKeyId, applicationInstanceId,	entityInstanceId, processId, alarmSeverity, actionType, alarmStatus, textDescription, listofAction, eventId, hostName, apptype, versionNo, locationCode, timestamp, eventDescription}
                ::= 1

        -- Events classified as major on the SNMP Agent application will assert this trap
        snmpagentMajorAlarm TRAP-TYPE
                ENTERPRISE snmpagent
		VARIABLES {complexKeyId, applicationInstanceId,	entityInstanceId, processId, alarmSeverity, actionType, alarmStatus, textDescription, listofAction, eventId, hostName, apptype, versionNo, locationCode, timestamp, eventDescription}
                ::= 2

        -- Events classified as minor on the SNMP Agent application will assert this trap
        snmpagentMinorAlarm TRAP-TYPE
                ENTERPRISE snmpagent
		VARIABLES {complexKeyId, applicationInstanceId,	entityInstanceId, processId, alarmSeverity, actionType, alarmStatus, textDescription, listofAction, eventId, hostName, apptype, versionNo, locationCode, timestamp, eventDescription}
                ::= 3

        -- Events classified as notification on the SNMP Agent application will assert this trap
        snmpagentNotificationAlarm TRAP-TYPE
                ENTERPRISE snmpagent
		VARIABLES {complexKeyId, applicationInstanceId,	entityInstanceId, processId, alarmSeverity, actionType, alarmStatus, textDescription, listofAction, eventId, hostName, apptype, versionNo, locationCode, timestamp, eventDescription}
                ::= 4

        -- Events classified as critical on the NGMS application will assert this trap
        ngmsCriticalAlarm TRAP-TYPE
                ENTERPRISE ngms
		VARIABLES {complexKeyId, applicationInstanceId,	entityInstanceId, processId, alarmSeverity, actionType, alarmStatus, textDescription, listofAction, eventId, hostName, apptype, versionNo, locationCode, timestamp, eventDescription}
                ::= 1

        -- Events classified as major on the NGMS Agent application will assert this trap
        ngmsMajorAlarm TRAP-TYPE
                ENTERPRISE ngms
		VARIABLES {complexKeyId, applicationInstanceId,	entityInstanceId, processId, alarmSeverity, actionType, alarmStatus, textDescription, listofAction, eventId, hostName, apptype, versionNo, locationCode, timestamp, eventDescription}
                ::= 2

        -- Events classified as minor on the NGMS Agent application will assert this trap
        ngmsMinorAlarm TRAP-TYPE
                ENTERPRISE ngms
		VARIABLES {complexKeyId, applicationInstanceId,	entityInstanceId, processId, alarmSeverity, actionType, alarmStatus, textDescription, listofAction, eventId, hostName, apptype, versionNo, locationCode, timestamp, eventDescription}
                ::= 3

        -- Events classified as notification on the NGMS Agent application will assert this trap
        ngmsNotificationAlarm TRAP-TYPE
                ENTERPRISE ngms
		VARIABLES {complexKeyId, applicationInstanceId,	entityInstanceId, processId, alarmSeverity, actionType, alarmStatus, textDescription, listofAction, eventId, hostName, apptype, versionNo, locationCode, timestamp, eventDescription}
                ::= 4

        -- Events classified as critical on the AHM application will assert this trap
        ahmCriticalAlarm TRAP-TYPE
                ENTERPRISE ahm
		VARIABLES {complexKeyId, applicationInstanceId,	entityInstanceId, processId, alarmSeverity, actionType, alarmStatus, textDescription, listofAction, eventId, hostName, apptype, versionNo, locationCode, timestamp, eventDescription}
                ::= 1

        -- Events classified as major on the AHM application will assert this trap
        ahmMajorAlarm TRAP-TYPE
                ENTERPRISE ahm
		VARIABLES {complexKeyId, applicationInstanceId,	entityInstanceId, processId, alarmSeverity, actionType, alarmStatus, textDescription, listofAction, eventId, hostName, apptype, versionNo, locationCode, timestamp, eventDescription}
                ::= 2

        -- Events classified as minor on the AHM application will assert this trap
        ahmMinorAlarm TRAP-TYPE
                ENTERPRISE ahm
		VARIABLES {complexKeyId, applicationInstanceId,	entityInstanceId, processId, alarmSeverity, actionType, alarmStatus, textDescription, listofAction, eventId, hostName, apptype, versionNo, locationCode, timestamp, eventDescription}
                ::= 3

        -- Events classified as notification on the AHM application will assert this trap
        ahmNotificationAlarm TRAP-TYPE
                ENTERPRISE ahm
		VARIABLES {complexKeyId, applicationInstanceId,	entityInstanceId, processId, alarmSeverity, actionType, alarmStatus, textDescription, listofAction, eventId, hostName, apptype, versionNo, locationCode, timestamp, eventDescription}
                ::= 4

        -- Events classified as critical on the MMVGW application will assert this trap
        mmvgwCriticalAlarm TRAP-TYPE
                ENTERPRISE mmvgw
		VARIABLES {complexKeyId, applicationInstanceId,	entityInstanceId, processId, alarmSeverity, actionType, alarmStatus, textDescription, listofAction, eventId, hostName, apptype, versionNo, locationCode, timestamp, eventDescription}
                ::= 1

        -- Events classified as major on the MMVGW application will assert this trap
        mmvgwMajorAlarm TRAP-TYPE
                ENTERPRISE mmvgw
		VARIABLES {complexKeyId, applicationInstanceId,	entityInstanceId, processId, alarmSeverity, actionType, alarmStatus, textDescription, listofAction, eventId, hostName, apptype, versionNo, locationCode, timestamp, eventDescription}
                ::= 2

        -- Events classified as minor on the MMVGW application will assert this trap
        mmvgwMinorAlarm TRAP-TYPE
                ENTERPRISE mmvgw
		VARIABLES {complexKeyId, applicationInstanceId,	entityInstanceId, processId, alarmSeverity, actionType, alarmStatus, textDescription, listofAction, eventId, hostName, apptype, versionNo, locationCode, timestamp, eventDescription}
                ::= 3

        -- Events classified as notification on the MMVGW application will assert this trap
        mmvgwNotificationAlarm TRAP-TYPE
                ENTERPRISE mmvgw
		VARIABLES {complexKeyId, applicationInstanceId,	entityInstanceId, processId, alarmSeverity, actionType, alarmStatus, textDescription, listofAction, eventId, hostName, apptype, versionNo, locationCode, timestamp, eventDescription}
                ::= 4

        -- Events classified as critical on the MyServices application will assert this trap
        myservicesCriticalAlarm TRAP-TYPE
                ENTERPRISE myservices
		VARIABLES {complexKeyId, applicationInstanceId,	entityInstanceId, processId, alarmSeverity, actionType, alarmStatus, textDescription, listofAction, eventId, hostName, apptype, versionNo, locationCode, timestamp, eventDescription}
                ::= 1

        -- Events classified as major on the MyServices application will assert this trap
        myservicesMajorAlarm TRAP-TYPE
                ENTERPRISE myservices
		VARIABLES {complexKeyId, applicationInstanceId,	entityInstanceId, processId, alarmSeverity, actionType, alarmStatus, textDescription, listofAction, eventId, hostName, apptype, versionNo, locationCode, timestamp, eventDescription}
                ::= 2

        -- Events classified as minor on the MyServices application will assert this trap
        myservicesMinorAlarm TRAP-TYPE
                ENTERPRISE myservices
		VARIABLES {complexKeyId, applicationInstanceId,	entityInstanceId, processId, alarmSeverity, actionType, alarmStatus, textDescription, listofAction, eventId, hostName, apptype, versionNo, locationCode, timestamp, eventDescription}
                ::= 3

        -- Events classified as notification on the MyServices application will assert this trap
        myservicesNotificationAlarm TRAP-TYPE
                ENTERPRISE myservices
		VARIABLES {complexKeyId, applicationInstanceId,	entityInstanceId, processId, alarmSeverity, actionType, alarmStatus, textDescription, listofAction, eventId, hostName, apptype, versionNo, locationCode, timestamp, eventDescription}
                ::= 4


-- ----------------------------------------------------------------------------------------------
-- TRAP OID
-- ----------------------------------------------------------------------------------------------

        complexKeyId OBJECT-TYPE
                SYNTAX ComplexKeyId
                ACCESS read-only
                STATUS mandatory
                DESCRIPTION "The key for search on table"
                ::= {asuTrap 1}

        applicationInstanceId OBJECT-TYPE
                SYNTAX ApplicationInstanceId
                ACCESS read-only
                STATUS mandatory
                DESCRIPTION "This is generated by ASU & supplied to application"
                ::= {asuTrap 2}

        entityInstanceId OBJECT-TYPE
                SYNTAX EntityInstanceId
                ACCESS read-only
                STATUS mandatory
                DESCRIPTION "This gives specific instance of alarm"
                ::= {asuTrap 3}

        processId OBJECT-TYPE
                SYNTAX ProcessId
                ACCESS read-only
                STATUS mandatory
                DESCRIPTION "This process ID of the entity generating alarm"
                ::= {asuTrap 4}

        alarmSeverity OBJECT-TYPE
                SYNTAX AlarmSeverity
                ACCESS read-only
                STATUS mandatory
                DESCRIPTION "This gives severity of the alarm"
                ::= {asuTrap 5}

        actionType OBJECT-TYPE
                SYNTAX ActionType
                ACCESS read-only
                STATUS mandatory
                DESCRIPTION "This gives type of actions"
                ::= {asuTrap 6}

        alarmStatus OBJECT-TYPE
                SYNTAX AlarmStatus
                ACCESS read-only
                STATUS mandatory
                DESCRIPTION "This gives status of the alarm"
                ::= {asuTrap 7}

        textDescription OBJECT-TYPE
                SYNTAX TextDescription
                ACCESS read-only
                STATUS mandatory
                DESCRIPTION "This gives textual description of the alarm"
                ::= {asuTrap 8}

        listofAction OBJECT-TYPE
                SYNTAX ListofAction
                ACCESS read-only
                STATUS mandatory
                DESCRIPTION "This is list of actions pertaining to this alarms"
                ::= {asuTrap 9}

        eventId OBJECT-TYPE
                SYNTAX EventId
                ACCESS read-only
                STATUS mandatory
                DESCRIPTION "This is event identity"
                ::= {asuTrap 10}

	hostName OBJECT-TYPE
                SYNTAX HostName
                ACCESS read-only
                STATUS mandatory
                DESCRIPTION "This gives the host name"
                ::= {asuTrap 11}

        apptype OBJECT-TYPE
                SYNTAX Apptype
                ACCESS read-only
                STATUS mandatory
                DESCRIPTION "This field presents the application type"
                ::= {asuTrap 12}

        versionNo OBJECT-TYPE
                SYNTAX VersionNo
                ACCESS read-only
                STATUS mandatory
                DESCRIPTION "This field presents the version no. of application"
                ::= {asuTrap 13}

        locationCode OBJECT-TYPE
                SYNTAX LocationCode
                ACCESS read-only
                STATUS mandatory
                DESCRIPTION "This field presents the location code"
                ::= {asuTrap 14}

        timestamp OBJECT-TYPE
                SYNTAX Timestamp
                ACCESS read-only
                STATUS mandatory
                DESCRIPTION "This field presents the time of avent occurence"
                ::= {asuTrap 15}

        eventDescription OBJECT-TYPE
                SYNTAX EventDescription
                ACCESS read-only
                STATUS mandatory
                DESCRIPTION "This field presents the general description of the event"
                ::= {asuTrap 16}

-- ----------------------------------------------------------------------------------------------
-- ASU   E N T I T I E S
-- ----------------------------------------------------------------------------------------------

-- The following table contains the active alarms in the ASU.
	activeAlarmsTable OBJECT-TYPE
		SYNTAX SEQUENCE OF ActiveAlarmEntry
		ACCESS not-accessible
		STATUS mandatory
		DESCRIPTION   "This table contains the active alarms in the ASU"
		::= {asuActiveAlarms 1}

-- Each entry on the activeAlarmTable is of the following type
   	activeAlarmEntry OBJECT-TYPE
		SYNTAX ActiveAlarmEntry
           	ACCESS not-accessible
           	STATUS mandatory
          	DESCRIPTION "Each row of the table contains number of entities statistics data related to one system entity" 
           	INDEX {activeComplexKeyId}
           	::= {activeAlarmsTable 1}


	ActiveAlarmEntry ::= SEQUENCE {
		activeComplexKeyId				ComplexKeyId,
		activeApplicationInstanceId			ApplicationInstanceId,
		activeEntityInstanceId 				EntityInstanceId,
		activeProcessId  				ProcessId,
		activeAlarmSeverity 				AlarmSeverity,
		activeActionType				ActionType,
		activeAlarmStatus				AlarmStatus,
		activeTextDescription				TextDescription,
		activeListofAction				ListofAction,
		activeEventId					EventId,
		activeHostName             			HostName,
		activeApptype					Apptype,
		activeVersionNo					VersionNo,
		activeLocationCode				LocationCode,		
		activeTimestamp					Timestamp
	}

    	activeComplexKeyId OBJECT-TYPE
        	SYNTAX ComplexKeyId
        	ACCESS read-only
        	STATUS mandatory
        	DESCRIPTION "The key for search on table"
        	::= {activeAlarmEntry 1}

    	activeApplicationInstanceId OBJECT-TYPE
        	SYNTAX ApplicationInstanceId
        	ACCESS read-only
        	STATUS mandatory
        	DESCRIPTION "This is generated by ASU & supplied to application"
        	::= {activeAlarmEntry 2}

    	activeEntityInstanceId OBJECT-TYPE
        	SYNTAX EntityInstanceId
        	ACCESS read-only
        	STATUS mandatory
        	DESCRIPTION "This gives specific instance of alarm"
        	::= {activeAlarmEntry 3}

    	activeProcessId OBJECT-TYPE
        	SYNTAX ProcessId
        	ACCESS read-only
        	STATUS mandatory
        	DESCRIPTION "This process ID of the entity generating alarm"
        	::= {activeAlarmEntry 4}

    	activeAlarmSeverity OBJECT-TYPE
        	SYNTAX AlarmSeverity
        	ACCESS read-only
        	STATUS mandatory
        	DESCRIPTION "This gives severity of the alarm"
        	::= {activeAlarmEntry 5}

    	activeActionType OBJECT-TYPE
        	SYNTAX ActionType
        	ACCESS read-only
        	STATUS mandatory
        	DESCRIPTION "This gives type of actions"
        	::= {activeAlarmEntry 6}

    	activeAlarmStatus OBJECT-TYPE
        	SYNTAX AlarmStatus
        	ACCESS read-only
        	STATUS mandatory
        	DESCRIPTION "This gives status of the alarm"
        	::= {activeAlarmEntry 7}

    	activeTextDescription OBJECT-TYPE
        	SYNTAX TextDescription
        	ACCESS read-only
        	STATUS mandatory
        	DESCRIPTION "This gives textual description of the alarm"
        	::= {activeAlarmEntry 8}

    	activeListofAction OBJECT-TYPE
        	SYNTAX ListofAction
        	ACCESS read-only
        	STATUS mandatory
        	DESCRIPTION "This is list of actions pertaining to this alarms"
        	::= {activeAlarmEntry 9}

    	activeEventId OBJECT-TYPE
        	SYNTAX EventId
        	ACCESS read-only
        	STATUS mandatory
        	DESCRIPTION "This is event identity"
        	::= {activeAlarmEntry 10}

    	activeHostName OBJECT-TYPE
        	SYNTAX HostName
        	ACCESS read-only
        	STATUS mandatory
        	DESCRIPTION "This gives the host name"
        	::= {activeAlarmEntry 11}

    	activeApptype OBJECT-TYPE
        	SYNTAX Apptype
        	ACCESS read-only
        	STATUS mandatory
        	DESCRIPTION "This field presents the application type"
        	::= {activeAlarmEntry 12}

    	activeVersionNo OBJECT-TYPE
        	SYNTAX VersionNo
        	ACCESS read-only
        	STATUS mandatory
        	DESCRIPTION "This field presents the version no. of application"
        	::= {activeAlarmEntry 13}

    	activeLocationCode OBJECT-TYPE
        	SYNTAX LocationCode
        	ACCESS read-only
        	STATUS mandatory
        	DESCRIPTION "This field presents the location code"
        	::= {activeAlarmEntry 14}

    	activeTimestamp OBJECT-TYPE
        	SYNTAX Timestamp
        	ACCESS read-only
        	STATUS mandatory
        	DESCRIPTION "This field presents the time of avent occurence"
        	::= {activeAlarmEntry 15}

	activeAlarmAck OBJECT-TYPE
		SYNTAX OCTET STRING (SIZE(3..20))
		ACCESS write-only
		STATUS mandatory
		DESCRIPTION   "This gives the Application OID and Event ID to acknowledge an alarm"
		::= {asuActiveAlarms 2}

	activeAlarmClear OBJECT-TYPE
		SYNTAX OCTET STRING (SIZE(3..20))
		ACCESS write-only
		STATUS mandatory
		DESCRIPTION   "This gives the Application OID and Event ID to clear an alarm"
		::= {asuActiveAlarms 3}

	activeAlarmSend OBJECT-TYPE
		SYNTAX IpAddress
		ACCESS write-only
		STATUS mandatory
		DESCRIPTION   "This request the ASU to send all active alarms as traps to the IP destination specified in the OID value"
		::= {asuActiveAlarms 4}

-- ----------------------------------------------------------------------------------------------
-- SGF   E N T I T I E S
-- ----------------------------------------------------------------------------------------------

-- The following contain the SGF-related management info

	sgfStatistics	OBJECT IDENTIFIER ::= { sgf 1} 

-- The following table contains entity statistics
   	entityCountTable OBJECT-TYPE
                SYNTAX SEQUENCE OF EntityCountEntry 
                ACCESS not-accessible
                STATUS mandatory
                DESCRIPTION "A table consists of entity statistics"
                ::= {sgfStatistics 1}

        entityCountEntry OBJECT-TYPE
                SYNTAX EntityCountEntry 
                ACCESS not-accessible
                STATUS mandatory
                DESCRIPTION "Each row of the table contains entity related statistics"
		INDEX {entityName}
                ::= {entityCountTable 1}

	EntityCountEntry ::= SEQUENCE {
		entityName 					OCTET STRING,
		totalDefined 					Counter,
		totalOperational 				Counter
        }

    	entityName OBJECT-TYPE
        	SYNTAX OCTET STRING (SIZE(0..25))
        	ACCESS read-only
        	STATUS mandatory
        	DESCRIPTION "Entity Name"
        	::= {entityCountEntry 1}

    	totalDefined OBJECT-TYPE
        	SYNTAX Counter
        	ACCESS read-only
        	STATUS mandatory
        	DESCRIPTION "Total defined Entity"
        	::= {entityCountEntry 2}

    	totalOperational OBJECT-TYPE
        	SYNTAX Counter
        	ACCESS read-only
        	STATUS mandatory
        	DESCRIPTION "Total Operational Entity"
        	::= {entityCountEntry 3}

-- The following table contains MVP statistics
   	mvpTable OBJECT-TYPE
                SYNTAX SEQUENCE OF MVPEntry 
                ACCESS not-accessible
                STATUS mandatory
                DESCRIPTION "A table consists of MVP statistics"
                ::= {sgfStatistics 2}

        mvpEntry OBJECT-TYPE
                SYNTAX MVPEntry 
                ACCESS not-accessible
                STATUS mandatory
                DESCRIPTION "Each row of the table contains MVP related statistics"
		INDEX {mvpAlias}
                ::= {mvpTable 1}

	MVPEntry ::= SEQUENCE {
		mvpAlias 					OCTET STRING,
		mvpAddress  					IpAddress,
		mvpStatus 					INTEGER,
		connReqAttempts					Counter,
		connFailure 					Counter,
		regnReqAttempts 				Counter,
		regnFailure 					Counter,
		deregnReqFailure 				Counter,
		deregFailure 					Counter,
		discoReqAttempts 				Counter,
		discoFailure 					Counter,
		msuFromMvp 					Counter,
		octetsFromMvp 					Counter,
		msuToMvp 					Counter,
		octetsToMvp 					Counter
        }

    	mvpAlias OBJECT-TYPE
        	SYNTAX OCTET STRING (SIZE(0..25))
        	ACCESS read-only
        	STATUS mandatory
        	DESCRIPTION "MVP Alias"
        	::= {mvpEntry 1}

    	mvpAddress OBJECT-TYPE
        	SYNTAX IpAddress
        	ACCESS read-only
        	STATUS mandatory
        	DESCRIPTION "MVP IP Address"
        	::= {mvpEntry 2}

    	mvpStatus OBJECT-TYPE
        	SYNTAX INTEGER
        	ACCESS read-only
        	STATUS mandatory
        	DESCRIPTION "MVP Status"
        	::= {mvpEntry 3}

    	connReqAttempts OBJECT-TYPE
        	SYNTAX Counter
        	ACCESS read-only
        	STATUS mandatory
        	DESCRIPTION "Connection Request Attempts"
        	::= {mvpEntry 4}

    	connFailure OBJECT-TYPE
        	SYNTAX Counter
        	ACCESS read-only
        	STATUS mandatory
        	DESCRIPTION "Connection Failure"
        	::= {mvpEntry 5}

    	regnReqAttempts OBJECT-TYPE
        	SYNTAX Counter
        	ACCESS read-only
        	STATUS mandatory
        	DESCRIPTION "Registration Request Attempts"
        	::= {mvpEntry 6}

    	regnFailure OBJECT-TYPE
        	SYNTAX Counter
        	ACCESS read-only
        	STATUS mandatory
        	DESCRIPTION "Registration Failure"
        	::= {mvpEntry 7}

    	deregnReqFailure OBJECT-TYPE
        	SYNTAX Counter
        	ACCESS read-only
        	STATUS mandatory
        	DESCRIPTION "De-registration Request Failure"
        	::= {mvpEntry 8}

    	deregFailure OBJECT-TYPE
        	SYNTAX Counter
        	ACCESS read-only
        	STATUS mandatory
        	DESCRIPTION "De-registration Failure"
        	::= {mvpEntry 9}

    	discoReqAttempts OBJECT-TYPE
        	SYNTAX Counter
        	ACCESS read-only
        	STATUS mandatory
        	DESCRIPTION "Disconnection Request Attempts"
        	::= {mvpEntry 10}

    	discoFailure OBJECT-TYPE
        	SYNTAX Counter
        	ACCESS read-only
        	STATUS mandatory
        	DESCRIPTION "Disconnection Failure"
        	::= {mvpEntry 11}

    	msuFromMvp OBJECT-TYPE
        	SYNTAX Counter
        	ACCESS read-only
        	STATUS mandatory
        	DESCRIPTION "MSU from MVP"
        	::= {mvpEntry 12}

    	octetsFromMvp OBJECT-TYPE
        	SYNTAX Counter
        	ACCESS read-only
        	STATUS mandatory
        	DESCRIPTION "Octets from MVP"
        	::= {mvpEntry 13}

    	msuToMvp OBJECT-TYPE
        	SYNTAX Counter
        	ACCESS read-only
        	STATUS mandatory
        	DESCRIPTION "MSU to MVP"
        	::= {mvpEntry 14}

    	octetsToMvp OBJECT-TYPE
        	SYNTAX Counter
        	ACCESS read-only
        	STATUS mandatory
        	DESCRIPTION "Octets to MVP"
        	::= {mvpEntry 15}

-- The following table contains Sep statistics
   	sepTable OBJECT-TYPE
                SYNTAX SEQUENCE OF SepEntry 
                ACCESS not-accessible
                STATUS mandatory
                DESCRIPTION "A table consists of Sep statistics"
                ::= {sgfStatistics 3}

        sepEntry OBJECT-TYPE
                SYNTAX SepEntry 
                ACCESS not-accessible
                STATUS mandatory
                DESCRIPTION "Each row of the table contains Sep related statistics"
		INDEX {sepId}
                ::= {sepTable 1}

	SepEntry ::= SEQUENCE {
		sepId	  					OCTET STRING,
		sepDesc  					OCTET STRING,
		sepStatus 					INTEGER,
		routingFailure					Counter,
		inaccessibleCount				Counter,
		inaccessibleDuration 				Counter,
		msuFromSep 					Counter,
		octetsFromSep	 				Counter,
		msuToSep 					Counter,
		octetsToSep	 				Counter,
		msuDiscarded 					Counter
        }

    	sepId OBJECT-TYPE
        	SYNTAX OCTET STRING (SIZE(0..25))
        	ACCESS read-only
        	STATUS mandatory
        	DESCRIPTION "Sep ID"
        	::= {sepEntry 1}

    	sepDesc OBJECT-TYPE
        	SYNTAX OCTET STRING (SIZE(0..128))
        	ACCESS read-only
        	STATUS mandatory
        	DESCRIPTION "Sep Description"
        	::= {sepEntry 2}

    	sepStatus OBJECT-TYPE
        	SYNTAX INTEGER
        	ACCESS read-only
        	STATUS mandatory
        	DESCRIPTION "Sep Status"
        	::= {sepEntry 3}

    	routingFailure OBJECT-TYPE
        	SYNTAX Counter
        	ACCESS read-only
        	STATUS mandatory
        	DESCRIPTION "Routing failure"
        	::= {sepEntry 4}

    	inaccessibleCount OBJECT-TYPE
        	SYNTAX Counter
        	ACCESS read-only
        	STATUS mandatory
        	DESCRIPTION "Inaccessible Count"
        	::= {sepEntry 5}

    	inaccessibleDuration OBJECT-TYPE
        	SYNTAX Counter
        	ACCESS read-only
        	STATUS mandatory
        	DESCRIPTION "Inaccessible Duration"
        	::= {sepEntry 6}

    	msuFromSep OBJECT-TYPE
        	SYNTAX Counter
        	ACCESS read-only
        	STATUS mandatory
        	DESCRIPTION "MSU From Sep"
        	::= {sepEntry 7}

    	octetsFromSep OBJECT-TYPE
        	SYNTAX Counter
        	ACCESS read-only
        	STATUS mandatory
        	DESCRIPTION "Octets From Sep"
        	::= {sepEntry 8}

    	msuToSep OBJECT-TYPE
        	SYNTAX Counter
        	ACCESS read-only
        	STATUS mandatory
        	DESCRIPTION "MSU To Sep"
        	::= {sepEntry 9}

    	octetsToSep OBJECT-TYPE
        	SYNTAX Counter
        	ACCESS read-only
        	STATUS mandatory
        	DESCRIPTION "Octets To Sep"
        	::= {sepEntry 10}

    	msuDiscarded OBJECT-TYPE
        	SYNTAX Counter
        	ACCESS read-only
        	STATUS mandatory
        	DESCRIPTION "MSU Discarded"
        	::= {sepEntry 11}

-- The following table contains link statistics
   	linkSetTable OBJECT-TYPE
                SYNTAX SEQUENCE OF LinkSetEntry 
                ACCESS not-accessible
                STATUS mandatory
                DESCRIPTION "A table consists of link statistics"
                ::= {sgfStatistics 4}

        linkSetEntry OBJECT-TYPE
                SYNTAX LinkSetEntry 
                ACCESS not-accessible
                STATUS mandatory
                DESCRIPTION "Each row of the table contains link related statistics"
		INDEX {linkId}
                ::= {linkSetTable 1}

	LinkSetEntry ::= SEQUENCE {
		linkId	  					OCTET STRING,
		operStatus 					INTEGER,
		insSeconds					Counter,
		msuRx						Counter,
		octetsRx 					Counter,
		msuTx 						Counter,
		octetsTx	 				Counter,
		msuInError 					Counter
        }

    	linkId OBJECT-TYPE
        	SYNTAX OCTET STRING (SIZE(0..25))
        	ACCESS read-only
        	STATUS mandatory
        	DESCRIPTION "Link ID"
        	::= {linkSetEntry 1}

    	operStatus OBJECT-TYPE
        	SYNTAX INTEGER
        	ACCESS read-only
        	STATUS mandatory
        	DESCRIPTION "Operation Status"
        	::= {linkSetEntry 2}

    	insSeconds OBJECT-TYPE
        	SYNTAX Counter
        	ACCESS read-only
        	STATUS mandatory
        	DESCRIPTION "Insert Seconds"
        	::= {linkSetEntry 3}

    	msuRx OBJECT-TYPE
        	SYNTAX Counter
        	ACCESS read-only
        	STATUS mandatory
        	DESCRIPTION "MSU Receive"
        	::= {linkSetEntry 4}

    	octetsRx OBJECT-TYPE
        	SYNTAX Counter
        	ACCESS read-only
        	STATUS mandatory
        	DESCRIPTION "Octets Receive"
        	::= {linkSetEntry 5}

    	msuTx OBJECT-TYPE
        	SYNTAX Counter
        	ACCESS read-only
        	STATUS mandatory
        	DESCRIPTION "MSU Transmit"
        	::= {linkSetEntry 6}

    	octetsTx OBJECT-TYPE
        	SYNTAX Counter
        	ACCESS read-only
        	STATUS mandatory
        	DESCRIPTION "Octets Transmit"
        	::= {linkSetEntry 7}

    	msuInError OBJECT-TYPE
        	SYNTAX Counter
        	ACCESS read-only
        	STATUS mandatory
        	DESCRIPTION "MSU In Error"
        	::= {linkSetEntry 8}

-- The following table contains TS statistics
   	tsTable OBJECT-TYPE
                SYNTAX SEQUENCE OF TSEntry 
                ACCESS not-accessible
                STATUS mandatory
                DESCRIPTION "A table consists of TS statistics"
                ::= {sgfStatistics 5}

        tsEntry OBJECT-TYPE
                SYNTAX TSEntry 
                ACCESS not-accessible
                STATUS mandatory
                DESCRIPTION "Each row of the table contains TS related statistics"
		INDEX {tsAlias}
                ::= {tsTable 1}

	TSEntry ::= SEQUENCE {
		tsAlias	  					OCTET STRING,
		tsAddress	  				IpAddress,
		tsStatus 					INTEGER,
		tsConnReqAttempts				Counter,
		tsConnFailure					Counter,
		tsRegnReqAttempts 				Counter,
		tsRegnFailure 					Counter,
		tsDeregReqAttempt	 			Counter,
		tsDeregFailure 					Counter,
		tsDiscoReqAttempts				Counter,
		tsDiscoFailure 					Counter,
		msuFromTs  					Counter,
		octetsFromTs 					Counter,
		msuToTs 					Counter,
		octetsToTs 					Counter,
		tsUpReq 					Counter,
		tsAcReq 					Counter
        }

    	tsAlias	OBJECT-TYPE
        	SYNTAX OCTET STRING (SIZE(0..25))
        	ACCESS read-only
        	STATUS mandatory
        	DESCRIPTION "TS Alias"
        	::= {tsEntry 1}

    	tsAddress OBJECT-TYPE
        	SYNTAX IpAddress
        	ACCESS read-only
        	STATUS mandatory
        	DESCRIPTION "TS IP Address"
        	::= {tsEntry 2}

    	tsStatus OBJECT-TYPE
        	SYNTAX INTEGER
        	ACCESS read-only
        	STATUS mandatory
        	DESCRIPTION "TS Status"
        	::= {tsEntry 3}

    	tsConnReqAttempts OBJECT-TYPE
        	SYNTAX Counter
        	ACCESS read-only
        	STATUS mandatory
        	DESCRIPTION "TS Connection Request Attempts"
        	::= {tsEntry 4}

    	tsConnFailure OBJECT-TYPE
        	SYNTAX Counter
        	ACCESS read-only
        	STATUS mandatory
        	DESCRIPTION "TS Connection Failure"
        	::= {tsEntry 5}

    	tsRegnReqAttempts OBJECT-TYPE
        	SYNTAX Counter
        	ACCESS read-only
        	STATUS mandatory
        	DESCRIPTION "TS Registration Request Attempts"
        	::= {tsEntry 6}

    	tsRegnFailure OBJECT-TYPE
        	SYNTAX Counter
        	ACCESS read-only
        	STATUS mandatory
        	DESCRIPTION "TS Registration Failure"
        	::= {tsEntry 7}

    	tsDeregReqAttempt OBJECT-TYPE
        	SYNTAX Counter
        	ACCESS read-only
        	STATUS mandatory
        	DESCRIPTION "TS De-registration Request Attempts"
        	::= {tsEntry 8}

    	tsDeregFailure OBJECT-TYPE
        	SYNTAX Counter
        	ACCESS read-only
        	STATUS mandatory
        	DESCRIPTION "TS De-registration Failure"
        	::= {tsEntry 9}

    	tsDiscoReqAttempts OBJECT-TYPE
        	SYNTAX Counter
        	ACCESS read-only
        	STATUS mandatory
        	DESCRIPTION "TS disconnection Request Attempts"
        	::= {tsEntry 10}

    	tsDiscoFailure OBJECT-TYPE
        	SYNTAX Counter
        	ACCESS read-only
        	STATUS mandatory
        	DESCRIPTION "TS disconnection Failure"
        	::= {tsEntry 11}

    	msuFromTs OBJECT-TYPE
        	SYNTAX Counter
        	ACCESS read-only
        	STATUS mandatory
        	DESCRIPTION "MSU From TS"
        	::= {tsEntry 12}

    	octetsFromTs OBJECT-TYPE
        	SYNTAX Counter
        	ACCESS read-only
        	STATUS mandatory
        	DESCRIPTION "Octets From Ts"
        	::= {tsEntry 13}

    	msuToTs OBJECT-TYPE
        	SYNTAX Counter
        	ACCESS read-only
        	STATUS mandatory
        	DESCRIPTION "MSU To Ts"
        	::= {tsEntry 14}

    	octetsToTs OBJECT-TYPE
        	SYNTAX Counter
        	ACCESS read-only
        	STATUS mandatory
        	DESCRIPTION "Octets To Ts"
        	::= {tsEntry 15}

    	tsUpReq OBJECT-TYPE
        	SYNTAX Counter
        	ACCESS read-only
        	STATUS mandatory
        	DESCRIPTION "TS UP Request"
        	::= {tsEntry 16}

    	tsAcReq OBJECT-TYPE
        	SYNTAX Counter
        	ACCESS read-only
        	STATUS mandatory
        	DESCRIPTION "TS Action Request"
        	::= {tsEntry 17}

-- The following table contains CDMS statistics
   	cdmsTable OBJECT-TYPE
                SYNTAX SEQUENCE OF CdmsEntry 
                ACCESS not-accessible
                STATUS mandatory
                DESCRIPTION "A table consists of CDMS statistics"
                ::= {sgfStatistics 6}

        cdmsEntry OBJECT-TYPE
                SYNTAX CdmsEntry 
                ACCESS not-accessible
                STATUS mandatory
                DESCRIPTION "Each row of the table contains CDMS related statistics"
		INDEX {cdmsSystemName}
                ::= {cdmsTable 1}

	CdmsEntry ::= SEQUENCE {
		cdmsSystemName 					OCTET STRING,
		cdmsPointCode  					OCTET STRING,
		cdmsAddress  					IpAddress,
		cdmsStatus 					INTEGER,
		cdmsBindAttempts 				Counter,
		cdmsBindFailure  				Counter,
		cdmsActivations 				Counter,
		cdmsActivationFailure  				Counter,
		cdmsUnbindAttempts 				Counter,
		cdmsUnbindFailure  				Counter,
		cdmsSessionDeactivations 			Counter,
		cdmsDeactivationFailure  			Counter,
		cdmsRouteRegistrations   			Counter,
		cdmsRouteRegistrationFailure   			Counter,
		cdmsRouteDeregistrations   			Counter,
		cdmsRouteDeregistrationFailure 			Counter,
		cdmsMessagesTransmitted   			Counter,
		cdmsOctetsTransmitted   			Counter,
		cdmsMessagesReceived   				Counter,
		cdmsOctetsReceived 	 			Counter
        }

    	cdmsSystemName OBJECT-TYPE
        	SYNTAX OCTET STRING (SIZE(0..25))
        	ACCESS read-only
        	STATUS mandatory
        	DESCRIPTION "CDMS System Name"
        	::= {cdmsEntry 1}

    	cdmsPointCode OBJECT-TYPE
        	SYNTAX OCTET STRING (SIZE(0..25))
        	ACCESS read-only
        	STATUS mandatory
        	DESCRIPTION "CDMS Point Code"
        	::= {cdmsEntry 2}

    	cdmsAddress OBJECT-TYPE
        	SYNTAX IpAddress
        	ACCESS read-only
        	STATUS mandatory
        	DESCRIPTION "CDMS Ip Address"
        	::= {cdmsEntry 3}

    	cdmsStatus OBJECT-TYPE
        	SYNTAX INTEGER
        	ACCESS read-only
        	STATUS mandatory
        	DESCRIPTION "CDMS Status"
        	::= {cdmsEntry 4}

    	cdmsBindAttempts OBJECT-TYPE
        	SYNTAX Counter
        	ACCESS read-only
        	STATUS mandatory
        	DESCRIPTION "CDMS Bind Attempts"
        	::= {cdmsEntry 5}

    	cdmsBindFailure OBJECT-TYPE
        	SYNTAX Counter
        	ACCESS read-only
        	STATUS mandatory
        	DESCRIPTION "CDMS Bind Failure"
        	::= {cdmsEntry 6}

    	cdmsActivations OBJECT-TYPE
        	SYNTAX Counter
        	ACCESS read-only
        	STATUS mandatory
        	DESCRIPTION "CDMS Activations"
        	::= {cdmsEntry 7}

    	cdmsActivationFailure OBJECT-TYPE
        	SYNTAX Counter
        	ACCESS read-only
        	STATUS mandatory
        	DESCRIPTION "CDMS Activation Failure"
        	::= {cdmsEntry 8}

    	cdmsUnbindAttempts OBJECT-TYPE
        	SYNTAX Counter
        	ACCESS read-only
        	STATUS mandatory
        	DESCRIPTION "CDMS Unbind Attempts"
        	::= {cdmsEntry 9}

    	cdmsUnbindFailure OBJECT-TYPE
        	SYNTAX Counter
        	ACCESS read-only
        	STATUS mandatory
        	DESCRIPTION "CDMS Unbind Failure"
        	::= {cdmsEntry 10}

    	cdmsSessionDeactivations OBJECT-TYPE
        	SYNTAX Counter
        	ACCESS read-only
        	STATUS mandatory
        	DESCRIPTION "CDMS Session Deactivations"
        	::= {cdmsEntry 11}

    	cdmsDeactivationFailure OBJECT-TYPE
        	SYNTAX Counter
        	ACCESS read-only
        	STATUS mandatory
        	DESCRIPTION "CDMS Deactivation Failure"
        	::= {cdmsEntry 12}

    	cdmsRouteRegistrations OBJECT-TYPE
        	SYNTAX Counter
        	ACCESS read-only
        	STATUS mandatory
        	DESCRIPTION "CDMS Route Registrations"
        	::= {cdmsEntry 13}

    	cdmsRouteRegistrationFailure OBJECT-TYPE
        	SYNTAX Counter
        	ACCESS read-only
        	STATUS mandatory
        	DESCRIPTION "CDMS Route Registration Failure"
        	::= {cdmsEntry 14}

    	cdmsRouteDeregistrations OBJECT-TYPE
        	SYNTAX Counter
        	ACCESS read-only
        	STATUS mandatory
        	DESCRIPTION "CDMS Route Deregistrations"
        	::= {cdmsEntry 15}

    	cdmsRouteDeregistrationFailure OBJECT-TYPE
        	SYNTAX Counter
        	ACCESS read-only
        	STATUS mandatory
        	DESCRIPTION "CDMS Route Deregistration Failure"
        	::= {cdmsEntry 16}

    	cdmsMessagesTransmitted OBJECT-TYPE
        	SYNTAX Counter
        	ACCESS read-only
        	STATUS mandatory
        	DESCRIPTION "CDMS Messages Transmitted"
        	::= {cdmsEntry 17}

    	cdmsOctetsTransmitted OBJECT-TYPE
        	SYNTAX Counter
        	ACCESS read-only
        	STATUS mandatory
        	DESCRIPTION "CDMS Octets Transmitted"
        	::= {cdmsEntry 18}

    	cdmsMessagesReceived OBJECT-TYPE
        	SYNTAX Counter
        	ACCESS read-only
        	STATUS mandatory
        	DESCRIPTION "CDMS Messages Received"
        	::= {cdmsEntry 19}

    	cdmsOctetsReceived OBJECT-TYPE
        	SYNTAX Counter
        	ACCESS read-only
        	STATUS mandatory
        	DESCRIPTION "CDMS Octets Received"
        	::= {cdmsEntry 20}

-- ----------------------------------------------------------------------------------------------
-- TUI   E N T I T I E S
-- ----------------------------------------------------------------------------------------------

-- The following contain the TUI-related management info

	app	OBJECT IDENTIFIER ::= { tui 1} 

	systemStartTime OBJECT-TYPE
		SYNTAX OCTET STRING (SIZE(0..20))
		ACCESS read-only
		STATUS mandatory
		DESCRIPTION   "The start up time of the Doc Server (TUI) application, expressed in YYYYMMDDHHMMSS"
		::= {app 1}

-- The following table contains call statistics
   	mailboxStatsTable OBJECT-TYPE
                SYNTAX SEQUENCE OF MailboxStatsEntry
                ACCESS not-accessible
                STATUS mandatory
                DESCRIPTION "A table consists of mailbox statistics for COS 1 - 255"
                ::= {tui 2}

-- Each entry on the Mailbox Statistics is of the following type
        mailboxStatsEntry OBJECT-TYPE
                SYNTAX MailboxStatsEntry
                ACCESS not-accessible
                STATUS mandatory
                DESCRIPTION "Each row of the table contains mailbox statistics related for a COS"
                INDEX {mailboxStatsCOS}
                ::= {mailboxStatsTable 1}

	MailboxStatsEntry ::= SEQUENCE {
		mailboxStatsCOS					INTEGER,
		mailboxType0Sessions				INTEGER,
		mailboxType1Sessions				INTEGER,
		mailboxType11Sessions				INTEGER,
		mailboxType12Sessions				INTEGER,
		mailboxType16Sessions				INTEGER,
		mailboxType17essions				INTEGER,
		mailboxType23Sessions				INTEGER,
		mailboxType30Sessions				INTEGER,
		otherMailboxTypeSessions			INTEGER
	}

    	mailboxStatsCOS OBJECT-TYPE
        	SYNTAX INTEGER (0..255)
        	ACCESS read-only
        	STATUS mandatory
        	DESCRIPTION "COS (key) for the Call Statistics"
        	::= {mailboxStatsEntry 1}

    	mailboxType0Sessions OBJECT-TYPE
        	SYNTAX INTEGER
        	ACCESS read-only
        	STATUS mandatory
        	DESCRIPTION "Number of mailbox Type 0 sessions"
        	::= {mailboxStatsEntry 2}

    	mailboxType1Sessions OBJECT-TYPE
        	SYNTAX INTEGER
        	ACCESS read-only
        	STATUS mandatory
        	DESCRIPTION "Number of mailbox Type 1 sessions"
        	::= {mailboxStatsEntry 3}

    	mailboxType11Sessions OBJECT-TYPE
        	SYNTAX INTEGER
        	ACCESS read-only
        	STATUS mandatory
        	DESCRIPTION "Number of mailbox Type 11 sessions"
        	::= {mailboxStatsEntry 4}

    	mailboxType12Sessions OBJECT-TYPE
        	SYNTAX INTEGER
        	ACCESS read-only
        	STATUS mandatory
        	DESCRIPTION "Number of mailbox Type 12 sessions"
        	::= {mailboxStatsEntry 5}

    	mailboxType16Sessions OBJECT-TYPE
        	SYNTAX INTEGER
        	ACCESS read-only
        	STATUS mandatory
        	DESCRIPTION "Number of mailbox Type 16 sessions"
        	::= {mailboxStatsEntry 6}

    	mailboxType17essions OBJECT-TYPE
        	SYNTAX INTEGER
        	ACCESS read-only
        	STATUS mandatory
        	DESCRIPTION "Number of mailbox Type 17 sessions"
        	::= {mailboxStatsEntry 7}

    	mailboxType23Sessions OBJECT-TYPE
        	SYNTAX INTEGER
        	ACCESS read-only
        	STATUS mandatory
        	DESCRIPTION "Number of mailbox Type 23 sessions"
        	::= {mailboxStatsEntry 8}

    	mailboxType30Sessions OBJECT-TYPE
        	SYNTAX INTEGER
        	ACCESS read-only
        	STATUS mandatory
        	DESCRIPTION "Number of mailbox Type 30 sessions"
        	::= {mailboxStatsEntry 9}

    	otherMailboxTypeSessions OBJECT-TYPE
        	SYNTAX INTEGER
        	ACCESS read-only
        	STATUS mandatory
        	DESCRIPTION "Number of other mailbox Type (not 0,1,11,12,16,27,23,30) sessions"
        	::= {mailboxStatsEntry 10}

-- The following table contains subscriber call statistics
   	subscriberStatsTable OBJECT-TYPE
           SYNTAX SEQUENCE OF SubscriberStatsEntry
           ACCESS not-accessible
            STATUS mandatory
            DESCRIPTION "A table consists of subscriber statistics for COS 1 - 255"
            ::= {tui 3}

-- Each entry on the Subscriber Statistics is of the following type
        subscriberStatsEntry OBJECT-TYPE
            SYNTAX SubscriberStatsEntry
            ACCESS not-accessible
            STATUS mandatory
            DESCRIPTION "Each row of the table contains subscriber statistics related for a COS"
            INDEX {subscriberStatsCOS}
            ::= {subscriberStatsTable 1}

	SubscriberStatsEntry ::= SEQUENCE {
		subscriberStatsCOS				INTEGER,
		subscriberInboundCalls				INTEGER,
		subscriberInactivityHangUps			INTEGER,
		subscriberMessagesPlayed			INTEGER,
		subscriberMessagesSent				INTEGER,
		subscriberNumericMessagesPlayed			INTEGER,
		subscriberCallsMaxLength			INTEGER,
		subscriberCallsTotalLength			INTEGER,
		subscriberRecordedMessageMinLength		INTEGER,
		subscriberRecordedMessageMaxLength		INTEGER,
		subscriberRecordedMessageTotalNumber		INTEGER,
		subscriberRecordedMessageTotalLength		INTEGER,
		subscriberNumberOfFaxesOut			INTEGER,
		subscriberMaxNumberOfFaxPagesRetrieved		INTEGER,
		subscriberTotalNumberOfFaxPagesRetrieved	INTEGER,
		subscriberMinLengthRecordedGreeting		INTEGER,
		subscriberMaxLengthRecordedGreeting		INTEGER,
		subscriberTotalLengthRecordedGreetings		INTEGER,
		subscriberTotalNumberOfRecordedGreetings	INTEGER,
		subscriberMaxLengthRecordedSpokenName		INTEGER,
		subscriberTotalLengthRecordedSpokenName		INTEGER,
		subscriberTotalNumberOfRecordedSpokenName	INTEGER
	}

    	subscriberStatsCOS OBJECT-TYPE
        	SYNTAX INTEGER (0..255)
        	ACCESS read-only
        	STATUS mandatory
        	DESCRIPTION "COS (key) for the Call Statistics"
        	::= {subscriberStatsEntry 1}

    	subscriberInboundCalls OBJECT-TYPE
        	SYNTAX INTEGER
        	ACCESS read-only
        	STATUS mandatory
        	DESCRIPTION "No of inbound calls by subscribers"
        	::= {subscriberStatsEntry 2}

    	subscriberInactivityHangUps OBJECT-TYPE
        	SYNTAX INTEGER
        	ACCESS read-only
        	STATUS mandatory
        	DESCRIPTION "No of subscribers' hang-ups due to inactivity"
        	::= {subscriberStatsEntry 3}

    	subscriberMessagesPlayed OBJECT-TYPE
        	SYNTAX INTEGER
        	ACCESS read-only
        	STATUS mandatory
        	DESCRIPTION "Duration of playing messages for subsribers"
        	::= {subscriberStatsEntry 4}

    	subscriberMessagesSent OBJECT-TYPE
        	SYNTAX INTEGER
        	ACCESS read-only
        	STATUS mandatory
        	DESCRIPTION "Duration of sending messages for subscribers"
        	::= {subscriberStatsEntry 5}

    	subscriberNumericMessagesPlayed OBJECT-TYPE
        	SYNTAX INTEGER
        	ACCESS read-only
        	STATUS mandatory
        	DESCRIPTION "Duration of playing numberic messages for subscribers"
        	::= {subscriberStatsEntry 6}

    	subscriberCallsMaxLength OBJECT-TYPE
        	SYNTAX INTEGER
        	ACCESS read-only
        	STATUS mandatory
        	DESCRIPTION "Max call duration for subscribers"
        	::= {subscriberStatsEntry 7}

    	subscriberCallsTotalLength OBJECT-TYPE
        	SYNTAX INTEGER
        	ACCESS read-only
        	STATUS mandatory
        	DESCRIPTION "Total duration for subscriber calls"
        	::= {subscriberStatsEntry 8}

    	subscriberRecordedMessageMinLength OBJECT-TYPE
        	SYNTAX INTEGER
        	ACCESS read-only
        	STATUS mandatory
        	DESCRIPTION "Min length of recorded message by subscribers"
        	::= {subscriberStatsEntry 9}

    	subscriberRecordedMessageMaxLength OBJECT-TYPE
        	SYNTAX INTEGER
        	ACCESS read-only
        	STATUS mandatory
        	DESCRIPTION "Max length of recorded message by subscribers"
        	::= {subscriberStatsEntry 10}

    	subscriberRecordedMessageTotalNumber OBJECT-TYPE
        	SYNTAX INTEGER
        	ACCESS read-only
        	STATUS mandatory
        	DESCRIPTION "Total number of recorded messages by subscribers"
        	::= {subscriberStatsEntry 11}

    	subscriberRecordedMessageTotalLength OBJECT-TYPE
        	SYNTAX INTEGER
        	ACCESS read-only
        	STATUS mandatory
        	DESCRIPTION "Total length of recorded messages by subscribers"
        	::= {subscriberStatsEntry 12}

    	subscriberNumberOfFaxesOut OBJECT-TYPE
        	SYNTAX INTEGER
        	ACCESS read-only
        	STATUS mandatory
        	DESCRIPTION "Number of out-going faxes by subscribers"
        	::= {subscriberStatsEntry 13}


    	subscriberMaxNumberOfFaxPagesRetrieved OBJECT-TYPE
        	SYNTAX INTEGER
        	ACCESS read-only
        	STATUS mandatory
        	DESCRIPTION "Max number of fax pages retrieved by subscribers"
        	::= {subscriberStatsEntry 14}

    	subscriberTotalNumberOfFaxPagesRetrieved OBJECT-TYPE
        	SYNTAX INTEGER
        	ACCESS read-only
        	STATUS mandatory
        	DESCRIPTION "Total number of fax pages retrieved by subscribers"
        	::= {subscriberStatsEntry 15}

    	subscriberMinLengthRecordedGreeting OBJECT-TYPE
        	SYNTAX INTEGER
        	ACCESS read-only
        	STATUS mandatory
        	DESCRIPTION "Min length of greeting recorded by subscribers"
        	::= {subscriberStatsEntry 16}

    	subscriberMaxLengthRecordedGreeting OBJECT-TYPE
        	SYNTAX INTEGER
        	ACCESS read-only
        	STATUS mandatory
        	DESCRIPTION "Max length of greeting recorded by subscribers"
        	::= {subscriberStatsEntry 17}

    	subscriberTotalLengthRecordedGreetings OBJECT-TYPE
        	SYNTAX INTEGER
        	ACCESS read-only
        	STATUS mandatory
        	DESCRIPTION "Total length of greeting recorded by subscribers"
        	::= {subscriberStatsEntry 18}

    	subscriberTotalNumberOfRecordedGreetings OBJECT-TYPE
        	SYNTAX INTEGER
        	ACCESS read-only
        	STATUS mandatory
        	DESCRIPTION "Total number of greetings recorded by subscribers"
        	::= {subscriberStatsEntry 19}

    	subscriberMaxLengthRecordedSpokenName OBJECT-TYPE
        	SYNTAX INTEGER
        	ACCESS read-only
        	STATUS mandatory
        	DESCRIPTION "Max length of recorded spoken name by subscribers"
        	::= {subscriberStatsEntry 20}

    	subscriberTotalLengthRecordedSpokenName OBJECT-TYPE
        	SYNTAX INTEGER
        	ACCESS read-only
        	STATUS mandatory
        	DESCRIPTION "Total length of recorded spoken names by subscribers"
        	::= {subscriberStatsEntry 21}

    	subscriberTotalNumberOfRecordedSpokenName OBJECT-TYPE
        	SYNTAX INTEGER
        	ACCESS read-only
        	STATUS mandatory
        	DESCRIPTION "Total number of recorded spoken names by subscribers"
        	::= {subscriberStatsEntry 22}

-- The following table contains caller statistics
   	callerStatsTable OBJECT-TYPE
            SYNTAX SEQUENCE OF CallerStatsEntry
            ACCESS not-accessible
            STATUS mandatory
            DESCRIPTION "A table consists of caller statistics for COS 1 - 255"
            ::= {tui 4}

-- Each entry on the Caller Statistics is of the following type
        callerStatsEntry OBJECT-TYPE
            SYNTAX CallerStatsEntry
            ACCESS not-accessible
            STATUS mandatory
            DESCRIPTION "Each row of the table contains caller statistics related for a COS"
            INDEX {callerStatsCOS}
            ::= {callerStatsTable 1}

	CallerStatsEntry ::= SEQUENCE {
		callerStatsCOS					INTEGER,
		callerInboundCalls				INTEGER,
		callerInactivityHangUps				INTEGER,
		callerTotalTimeCall				INTEGER,
		callerNumericMessagesDeposited			INTEGER,
		callerMaxRecordTimeReached			INTEGER,
		callerMinRecordTimeNotReached			INTEGER,
		callerTotalMessagesDeposited			INTEGER,
		callerTotalLengthOfDepositedMessages		INTEGER,
		callerFaxesDeposited				INTEGER,
		callerMaxFaxPagesDeposited			INTEGER,
		callerTotalFaxPagesDeposited			INTEGER,
		callerMailboxFullRejection			INTEGER,
		callerMailboxSuspendedRejection			INTEGER
	}

    	callerStatsCOS OBJECT-TYPE
        	SYNTAX INTEGER (0..255)
        	ACCESS read-only
        	STATUS mandatory
        	DESCRIPTION "COS (key) for the Caller Statistics"
        	::= {callerStatsEntry 1}

    	callerInboundCalls OBJECT-TYPE
        	SYNTAX INTEGER
        	ACCESS read-only
        	STATUS mandatory
        	DESCRIPTION "No of inbound calls by callers"
        	::= {callerStatsEntry 2}

    	callerInactivityHangUps OBJECT-TYPE
        	SYNTAX INTEGER
        	ACCESS read-only
        	STATUS mandatory
        	DESCRIPTION "No of callers' hang-ups due to inactivity"
        	::= {callerStatsEntry 3}

    	callerTotalTimeCall OBJECT-TYPE
        	SYNTAX INTEGER
        	ACCESS read-only
        	STATUS mandatory
        	DESCRIPTION "Total call duration for callers"
        	::= {callerStatsEntry 4}

    	callerNumericMessagesDeposited OBJECT-TYPE
        	SYNTAX INTEGER
        	ACCESS read-only
        	STATUS mandatory
        	DESCRIPTION "No of numeric messages deposited by callers"
        	::= {callerStatsEntry 5}

    	callerMaxRecordTimeReached OBJECT-TYPE
        	SYNTAX INTEGER
        	ACCESS read-only
        	STATUS mandatory
        	DESCRIPTION "No of times when max recording duration was reached for callers"
        	::= {callerStatsEntry 6}

    	callerMinRecordTimeNotReached OBJECT-TYPE
        	SYNTAX INTEGER
        	ACCESS read-only
        	STATUS mandatory
        	DESCRIPTION "No of times when min recording duration was not reached for callers"
        	::= {callerStatsEntry 7}

    	callerTotalMessagesDeposited OBJECT-TYPE
        	SYNTAX INTEGER
        	ACCESS read-only
        	STATUS mandatory
        	DESCRIPTION "Total no of messages deposited by callers"
        	::= {callerStatsEntry 8}

    	callerTotalLengthOfDepositedMessages OBJECT-TYPE
        	SYNTAX INTEGER
        	ACCESS read-only
        	STATUS mandatory
        	DESCRIPTION "Total length of messages deposited by callers"
        	::= {callerStatsEntry 9}

    	callerFaxesDeposited OBJECT-TYPE
        	SYNTAX INTEGER
        	ACCESS read-only
        	STATUS mandatory
        	DESCRIPTION "No of faxes deposited by callers"
        	::= {callerStatsEntry 10}

    	callerMaxFaxPagesDeposited OBJECT-TYPE
        	SYNTAX INTEGER
        	ACCESS read-only
        	STATUS mandatory
        	DESCRIPTION "Max no of fax pages deposited by callers"
        	::= {callerStatsEntry 11}

    	callerTotalFaxPagesDeposited OBJECT-TYPE
        	SYNTAX INTEGER
        	ACCESS read-only
        	STATUS mandatory
        	DESCRIPTION "Total no of fax pages deposited by callers"
        	::= {callerStatsEntry 12}

    	callerMailboxFullRejection OBJECT-TYPE
        	SYNTAX INTEGER
        	ACCESS read-only
        	STATUS mandatory
        	DESCRIPTION "No of callers rejected due to mailbox full"
        	::= {callerStatsEntry 13}

    	callerMailboxSuspendedRejection OBJECT-TYPE
        	SYNTAX INTEGER
        	ACCESS read-only
        	STATUS mandatory
        	DESCRIPTION "No of callers rejected ue to mailbox suspected"
        	::= {callerStatsEntry 14}

-- The following table contains otherCall statistics
   	otherCallStatsTable OBJECT-TYPE
            	SYNTAX SEQUENCE OF OtherCallStatsEntry
            	ACCESS not-accessible
            	STATUS mandatory
            	DESCRIPTION "A table consists of otherCall statistics for COS 1 - 255"
            	::= {tui 5}

-- Each entry on the OtherCall Statistics is of the following type
        otherCallStatsEntry OBJECT-TYPE
            	SYNTAX OtherCallStatsEntry
            	ACCESS not-accessible
            	STATUS mandatory
            	DESCRIPTION "Each row of the table contains otherCall statistics related for a COS"
            	INDEX {otherCallStatsCOS}
            	::= {otherCallStatsTable 1}

	OtherCallStatsEntry ::= SEQUENCE {
		otherCallStatsCOS					INTEGER,
		numberOfSessions					INTEGER,
		numberOfSessionTimeouts					INTEGER,
		loginAttemptsSuccesful					INTEGER,
		loginAttemptsUnsuccessful				INTEGER,
		disconnectsFromUnsuccessfulLogin			INTEGER,
		totalInboundCalls					INTEGER,
		totalTimeInboundCalls					INTEGER,
		totalTimeOfOutdials					INTEGER,
		maxTimeOfOutdial					INTEGER,
		outdialsSuccessful					INTEGER,
		outdialsUnsuccessful					INTEGER,
		outdialNumberMenuAfterCmdTimeout			INTEGER,
		outdialNumberMenuInvalidCommand				INTEGER
	}

    	otherCallStatsCOS OBJECT-TYPE
        	SYNTAX INTEGER (0..255)
        	ACCESS read-only
        	STATUS mandatory
        	DESCRIPTION "COS (key) for the Other Call Statistics"
        	::= {otherCallStatsEntry 1}

    	numberOfSessions OBJECT-TYPE
        	SYNTAX INTEGER
        	ACCESS read-only
        	STATUS mandatory
        	DESCRIPTION "Number of sessions"
        	::= {otherCallStatsEntry 2}

    	numberOfSessionTimeouts OBJECT-TYPE
        	SYNTAX INTEGER
        	ACCESS read-only
        	STATUS mandatory
        	DESCRIPTION "No of sessions that have been timed-out"
        	::= {otherCallStatsEntry 3}

    	loginAttemptsSuccesful OBJECT-TYPE
        	SYNTAX INTEGER
        	ACCESS read-only
        	STATUS mandatory
        	DESCRIPTION "No of successful login attempts"
        	::= {otherCallStatsEntry 4}

    	loginAttemptsUnsuccessful OBJECT-TYPE
        	SYNTAX INTEGER
        	ACCESS read-only
        	STATUS mandatory
        	DESCRIPTION "No of unsuccessful login attempts"
        	::= {otherCallStatsEntry 5}

    	disconnectsFromUnsuccessfulLogin OBJECT-TYPE
        	SYNTAX INTEGER
        	ACCESS read-only
        	STATUS mandatory
        	DESCRIPTION "No of disconnects due to unsuccessful login attempts"
        	::= {otherCallStatsEntry 6}

    	totalInboundCalls OBJECT-TYPE
        	SYNTAX INTEGER
        	ACCESS read-only
        	STATUS mandatory
        	DESCRIPTION "Total no of inbound calls"
        	::= {otherCallStatsEntry 7}

    	totalTimeInboundCalls OBJECT-TYPE
        	SYNTAX INTEGER
        	ACCESS read-only
        	STATUS mandatory
        	DESCRIPTION "Total duration of inbound calls"
        	::= {otherCallStatsEntry 8}

    	totalTimeOfOutdials OBJECT-TYPE
        	SYNTAX INTEGER
        	ACCESS read-only
        	STATUS mandatory
        	DESCRIPTION "Total duration of outdials"
        	::= {otherCallStatsEntry 9}

    	maxTimeOfOutdial OBJECT-TYPE
        	SYNTAX INTEGER
        	ACCESS read-only
        	STATUS mandatory
        	DESCRIPTION "Max duration for outdials"
        	::= {otherCallStatsEntry 10}

    	outdialsSuccessful OBJECT-TYPE
        	SYNTAX INTEGER
        	ACCESS read-only
        	STATUS mandatory
        	DESCRIPTION "No of successfull outdials"
        	::= {otherCallStatsEntry 11}

    	outdialsUnsuccessful OBJECT-TYPE
        	SYNTAX INTEGER
        	ACCESS read-only
        	STATUS mandatory
        	DESCRIPTION "No of unsuccessfull outdials"
        	::= {otherCallStatsEntry 12}

    	outdialNumberMenuAfterCmdTimeout OBJECT-TYPE
        	SYNTAX INTEGER
        	ACCESS read-only
        	STATUS mandatory
        	DESCRIPTION "No of outdial number menu after command timeout"
        	::= {otherCallStatsEntry 13}

    	outdialNumberMenuInvalidCommand OBJECT-TYPE
        	SYNTAX INTEGER
        	ACCESS read-only
        	STATUS mandatory
        	DESCRIPTION "No of outdial number menu invalid command"
        	::= {otherCallStatsEntry 14}

-- The following table contains greetings statistics
        greetingsStatsTable OBJECT-TYPE
                SYNTAX SEQUENCE OF GreetingsStatsEntry
                ACCESS not-accessible
                STATUS mandatory
                DESCRIPTION "a table consists of greetings statistics for COS 1 - 255"
                ::= {tui 6}

-- Each entry on the greetings Statistics is of the following type
        greetingsStatsEntry OBJECT-TYPE
                SYNTAX GreetingsStatsEntry
                ACCESS not-accessible
                STATUS mandatory
                DESCRIPTION "Each row of the table contains greetings statistics related for a COS"
                INDEX {greetingsStatsCOS}
                ::= {greetingsStatsTable 1}

	GreetingsStatsEntry ::= SEQUENCE {
		greetingsStatsCOS						INTEGER,
		calledNumberGreetingsToggleCalledNumberGreetings		INTEGER,
		calledNumberGreetingsInvalidCommand				INTEGER,
		calledNumberGreetingsPlayMailboxNumbers				INTEGER,
		calledNumberGreetingsCmdTimeout					INTEGER,
		greetingsMenuPlayActiveGreeting					INTEGER,
		greetingsMenuRecordActiveGreeting				INTEGER,
		greetingsMenuSelectActiveGreeting				INTEGER,
		greetingsMenuModifyAGreeting					INTEGER,
		greetingsMenuExtendedAbsenceGreeting				INTEGER,
		greetingsMenuDeleteActiveGreeting				INTEGER,
		greetingsMenuCalledNumberGreetingsMenu				INTEGER,
		greetingsMenuInvalidCommand					INTEGER,
		greetingsMenuCmdTimeout						INTEGER,
		modifyGreetingsPlayGreeting					INTEGER,
		modifyGreetingsRecordGreeting					INTEGER,
		modifyGreetingsDeleteGreeting					INTEGER,
		modifyGreetingsInvalidCommand					INTEGER,
		modifyGreetingsCmdTimeout					INTEGER
	}

    	greetingsStatsCOS OBJECT-TYPE
        	SYNTAX INTEGER (0..255)
        	ACCESS read-only
        	STATUS mandatory
        	DESCRIPTION "COS (key) for the Greetings Statistics"
        	::= {greetingsStatsEntry 1}

    	calledNumberGreetingsToggleCalledNumberGreetings OBJECT-TYPE
        	SYNTAX INTEGER
        	ACCESS read-only
        	STATUS mandatory
        	DESCRIPTION ""
        	::= {greetingsStatsEntry 2}

    	calledNumberGreetingsInvalidCommand OBJECT-TYPE
        	SYNTAX INTEGER
        	ACCESS read-only
        	STATUS mandatory
        	DESCRIPTION ""
        	::= {greetingsStatsEntry 3}

    	calledNumberGreetingsPlayMailboxNumbers OBJECT-TYPE
        	SYNTAX INTEGER
        	ACCESS read-only
        	STATUS mandatory
        	DESCRIPTION ""
        	::= {greetingsStatsEntry 4}

    	calledNumberGreetingsCmdTimeout OBJECT-TYPE
        	SYNTAX INTEGER
        	ACCESS read-only
        	STATUS mandatory
        	DESCRIPTION ""
        	::= {greetingsStatsEntry 5}

    	greetingsMenuPlayActiveGreeting OBJECT-TYPE
        	SYNTAX INTEGER
        	ACCESS read-only
        	STATUS mandatory
        	DESCRIPTION "No of "
        	::= {greetingsStatsEntry 6}

    	greetingsMenuRecordActiveGreeting OBJECT-TYPE
        	SYNTAX INTEGER
        	ACCESS read-only
        	STATUS mandatory
        	DESCRIPTION ""
        	::= {greetingsStatsEntry 7}

    	greetingsMenuSelectActiveGreeting OBJECT-TYPE
        	SYNTAX INTEGER
        	ACCESS read-only
        	STATUS mandatory
        	DESCRIPTION ""
        	::= {greetingsStatsEntry 8}

    	greetingsMenuModifyAGreeting OBJECT-TYPE
        	SYNTAX INTEGER
        	ACCESS read-only
        	STATUS mandatory
        	DESCRIPTION ""
        	::= {greetingsStatsEntry 9}

    	greetingsMenuExtendedAbsenceGreeting OBJECT-TYPE
        	SYNTAX INTEGER
        	ACCESS read-only
        	STATUS mandatory
        	DESCRIPTION ""
        	::= {greetingsStatsEntry 10}

    	greetingsMenuDeleteActiveGreeting OBJECT-TYPE
        	SYNTAX INTEGER
        	ACCESS read-only
        	STATUS mandatory
        	DESCRIPTION ""
        	::= {greetingsStatsEntry 11}

    	greetingsMenuCalledNumberGreetingsMenu OBJECT-TYPE
        	SYNTAX INTEGER
        	ACCESS read-only
        	STATUS mandatory
        	DESCRIPTION ""
        	::= {greetingsStatsEntry 12}

    	greetingsMenuInvalidCommand OBJECT-TYPE
        	SYNTAX INTEGER
        	ACCESS read-only
        	STATUS mandatory
        	DESCRIPTION ""
        	::= {greetingsStatsEntry 13}

    	greetingsMenuCmdTimeout OBJECT-TYPE
        	SYNTAX INTEGER
        	ACCESS read-only
        	STATUS mandatory
        	DESCRIPTION ""
        	::= {greetingsStatsEntry 14}

    	modifyGreetingsPlayGreeting OBJECT-TYPE
        	SYNTAX INTEGER
        	ACCESS read-only
        	STATUS mandatory
        	DESCRIPTION ""
        	::= {greetingsStatsEntry 15}

    	modifyGreetingsRecordGreeting OBJECT-TYPE
        	SYNTAX INTEGER
        	ACCESS read-only
        	STATUS mandatory
        	DESCRIPTION ""
        	::= {greetingsStatsEntry 16}

    	modifyGreetingsDeleteGreeting OBJECT-TYPE
        	SYNTAX INTEGER
        	ACCESS read-only
        	STATUS mandatory
        	DESCRIPTION ""
        	::= {greetingsStatsEntry 17}

    	modifyGreetingsInvalidCommand OBJECT-TYPE
        	SYNTAX INTEGER
        	ACCESS read-only
        	STATUS mandatory
        	DESCRIPTION ""
        	::= {greetingsStatsEntry 18}

    	modifyGreetingsCmdTimeout OBJECT-TYPE
        	SYNTAX INTEGER
        	ACCESS read-only
        	STATUS mandatory
        	DESCRIPTION ""
        	::= {greetingsStatsEntry 19}

-- The following table contains globalCmds statistics
        globalCmdsStatsTable OBJECT-TYPE
                SYNTAX SEQUENCE OF GlobalCmdsStatsEntry
                ACCESS not-accessible
                STATUS mandatory
                DESCRIPTION "a table consists of globalCmds statistics for COS 1 - 255"
                ::= {tui 7}

-- Each entry on the globalCmds Statistics is of the following type
        globalCmdsStatsEntry OBJECT-TYPE
                SYNTAX GlobalCmdsStatsEntry
                ACCESS not-accessible
                STATUS mandatory
                DESCRIPTION "Each row of the table contains globalCmds statistics related for a COS"
                INDEX {globalCmdsStatsCOS}
                ::= {globalCmdsStatsTable 1}

	GlobalCmdsStatsEntry ::= SEQUENCE {
		globalCmdsStatsCOS						INTEGER,
		globalCommandsPreviousMenu					INTEGER,
		globalCommandsReturnToMainMenu					INTEGER,
		globalCommandsRe-ID						INTEGER,
		globalCommandsAdditionalHelp					INTEGER,
		globalCommandsOperatorTransfer					INTEGER
	}

    	globalCmdsStatsCOS OBJECT-TYPE
        	SYNTAX INTEGER (0..255)
        	ACCESS read-only
        	STATUS mandatory
        	DESCRIPTION "COS (key) for the globalCmds Statistics"
        	::= {globalCmdsStatsEntry 1}

    	globalCommandsPreviousMenu OBJECT-TYPE
        	SYNTAX INTEGER
        	ACCESS read-only
        	STATUS mandatory
        	DESCRIPTION ""
        	::= {globalCmdsStatsEntry 2}

    	globalCommandsReturnToMainMenu OBJECT-TYPE
        	SYNTAX INTEGER
        	ACCESS read-only
        	STATUS mandatory
        	DESCRIPTION ""
        	::= {globalCmdsStatsEntry 3}

    	globalCommandsRe-ID OBJECT-TYPE
        	SYNTAX INTEGER
        	ACCESS read-only
        	STATUS mandatory
        	DESCRIPTION ""
        	::= {globalCmdsStatsEntry 4}


    	globalCommandsAdditionalHelp OBJECT-TYPE
        	SYNTAX INTEGER
        	ACCESS read-only
        	STATUS mandatory
        	DESCRIPTION ""
        	::= {globalCmdsStatsEntry 5}

    	globalCommandsOperatorTransfer OBJECT-TYPE
        	SYNTAX INTEGER
        	ACCESS read-only
        	STATUS mandatory
        	DESCRIPTION ""
        	::= {globalCmdsStatsEntry 6}

-- The following table contains mainMenu statistics
        mainMenuStatsTable OBJECT-TYPE
                SYNTAX SEQUENCE OF MainMenuStatsEntry
                ACCESS not-accessible
                STATUS mandatory
                DESCRIPTION "a table consists of mainMenu statistics for COS 1 - 255"
                ::= {tui 8}

-- Each entry on the mainMenu Statistics is of the following type
        mainMenuStatsEntry OBJECT-TYPE
                SYNTAX MainMenuStatsEntry
                ACCESS not-accessible
                STATUS mandatory
                DESCRIPTION "Each row of the table contains mainMenu statistics related for a COS"
                INDEX {mainMenuStatsCOS}
                ::= {mainMenuStatsTable 1}

	MainMenuStatsEntry ::= SEQUENCE {
		mainMenuStatsCOS						INTEGER,
		mainMenuPlayMessages						INTEGER,
		mainMenuRecordMessage						INTEGER,
		mainMenuGreetingsMenu						INTEGER,
		mainMenuPersonalOptionsMenu					INTEGER,
		mainMenuConstantTouchMenu					INTEGER,
		mainMenuMakeACall						INTEGER,
		mainMenuVSSAccess						INTEGER,
		mainMenuEndCall							INTEGER,
		mainMenuUndeleteMessages					INTEGER,
		mainMenuInvalidCommand						INTEGER,
		mainMenuCmdTimeout						INTEGER
	}

    	mainMenuStatsCOS OBJECT-TYPE
        	SYNTAX INTEGER (0..255)
        	ACCESS read-only
        	STATUS mandatory
        	DESCRIPTION "COS (key) for the mainMenu Statistics"
        	::= {mainMenuStatsEntry 1}

    	mainMenuPlayMessages OBJECT-TYPE
        	SYNTAX INTEGER
        	ACCESS read-only
        	STATUS mandatory
        	DESCRIPTION ""
        	::= {mainMenuStatsEntry 2}

    	mainMenuRecordMessage OBJECT-TYPE
        	SYNTAX INTEGER
        	ACCESS read-only
        	STATUS mandatory
        	DESCRIPTION ""
        	::= {mainMenuStatsEntry 3}

    	mainMenuGreetingsMenu OBJECT-TYPE
        	SYNTAX INTEGER
        	ACCESS read-only
        	STATUS mandatory
        	DESCRIPTION ""
        	::= {mainMenuStatsEntry 4}

    	mainMenuPersonalOptionsMenu OBJECT-TYPE
        	SYNTAX INTEGER
        	ACCESS read-only
        	STATUS mandatory
        	DESCRIPTION ""
        	::= {mainMenuStatsEntry 5}

    	mainMenuConstantTouchMenu OBJECT-TYPE
        	SYNTAX INTEGER
        	ACCESS read-only
        	STATUS mandatory
        	DESCRIPTION ""
        	::= {mainMenuStatsEntry 6}

    	mainMenuMakeACall OBJECT-TYPE
        	SYNTAX INTEGER
        	ACCESS read-only
        	STATUS mandatory
        	DESCRIPTION ""
        	::= {mainMenuStatsEntry 7}

    	mainMenuVSSAccess OBJECT-TYPE
        	SYNTAX INTEGER
        	ACCESS read-only
        	STATUS mandatory
        	DESCRIPTION ""
        	::= {mainMenuStatsEntry 8}

    	mainMenuEndCall OBJECT-TYPE
        	SYNTAX INTEGER
        	ACCESS read-only
        	STATUS mandatory
        	DESCRIPTION ""
        	::= {mainMenuStatsEntry 9}

    	mainMenuUndeleteMessages OBJECT-TYPE
        	SYNTAX INTEGER
        	ACCESS read-only
        	STATUS mandatory
        	DESCRIPTION ""
        	::= {mainMenuStatsEntry 10}

    	mainMenuInvalidCommand OBJECT-TYPE
        	SYNTAX INTEGER
        	ACCESS read-only
        	STATUS mandatory
        	DESCRIPTION ""
        	::= {mainMenuStatsEntry 11}

    	mainMenuCmdTimeout OBJECT-TYPE
        	SYNTAX INTEGER
        	ACCESS read-only
        	STATUS mandatory
        	DESCRIPTION ""
        	::= {mainMenuStatsEntry 12}

-- The following table contains callerMenu statistics
        callerMenuStatsTable OBJECT-TYPE
                SYNTAX SEQUENCE OF CallerMenuStatsEntry
                ACCESS not-accessible
                STATUS mandatory
                DESCRIPTION "a table consists of callerMenu statistics for COS 1 - 255"
                ::= {tui 9}

-- Each entry on the callerMenu Statistics is of the following type
        callerMenuStatsEntry OBJECT-TYPE
                SYNTAX CallerMenuStatsEntry
                ACCESS not-accessible
                STATUS mandatory
                DESCRIPTION "Each row of the table contains callerMenu statistics related for a COS"
                INDEX {callerMenuStatsCOS}
                ::= {callerMenuStatsTable 1}

	CallerMenuStatsEntry ::= SEQUENCE {
		callerMenuStatsCOS						INTEGER,
		callerDeliveryOptionsUrgent					INTEGER,
		callerDeliveryOptionsPrivate					INTEGER,
		callerDeliveryOptionsFutureDelivery				INTEGER,
		callerDeliveryOptionsSendMessage				INTEGER,
		callerDeliveryOptionsPreviousMenu				INTEGER,
		callerDeliveryOptionsInvalidCommand				INTEGER,
		callerDeliveryOptionsCmdTimeout					INTEGER,
		callerMenuOperatorTransfer					INTEGER,
		callerMenuCallbackNumber					INTEGER,
		callerMenuNDCTransfer						INTEGER,
		callerMenuConstantTouch						INTEGER,
		callerMenuRecordMessage						INTEGER,
		callerMenuFaxDeposit						INTEGER,
		callerMenuAdditionalHelp					INTEGER,
		callerMenuImmediateRecord					INTEGER,
		callerMenuLogin							INTEGER,
		callerMenuInvalidCommand					INTEGER,
		callerMenuCmdTimeout						INTEGER
	}

    	callerMenuStatsCOS OBJECT-TYPE
        	SYNTAX INTEGER (0..255)
        	ACCESS read-only
        	STATUS mandatory
        	DESCRIPTION "COS (key) for the callerMenu Statistics"
        	::= {callerMenuStatsEntry 1}

    	callerDeliveryOptionsUrgent OBJECT-TYPE
        	SYNTAX INTEGER
        	ACCESS read-only
        	STATUS mandatory
        	DESCRIPTION ""
        	::= {callerMenuStatsEntry 2}

    	callerDeliveryOptionsPrivate OBJECT-TYPE
        	SYNTAX INTEGER
        	ACCESS read-only
        	STATUS mandatory
        	DESCRIPTION ""
        	::= {callerMenuStatsEntry 3}

    	callerDeliveryOptionsFutureDelivery OBJECT-TYPE
        	SYNTAX INTEGER
        	ACCESS read-only
        	STATUS mandatory
        	DESCRIPTION ""
        	::= {callerMenuStatsEntry 4}

    	callerDeliveryOptionsSendMessage OBJECT-TYPE
        	SYNTAX INTEGER
        	ACCESS read-only
        	STATUS mandatory
        	DESCRIPTION ""
        	::= {callerMenuStatsEntry 5}

    	callerDeliveryOptionsPreviousMenu OBJECT-TYPE
        	SYNTAX INTEGER
        	ACCESS read-only
        	STATUS mandatory
        	DESCRIPTION ""
        	::= {callerMenuStatsEntry 6}

    	callerDeliveryOptionsInvalidCommand OBJECT-TYPE
        	SYNTAX INTEGER
        	ACCESS read-only
        	STATUS mandatory
        	DESCRIPTION ""
        	::= {callerMenuStatsEntry 7}

    	callerDeliveryOptionsCmdTimeout OBJECT-TYPE
        	SYNTAX INTEGER
        	ACCESS read-only
        	STATUS mandatory
        	DESCRIPTION ""
        	::= {callerMenuStatsEntry 8}

    	callerMenuOperatorTransfer OBJECT-TYPE
        	SYNTAX INTEGER
        	ACCESS read-only
        	STATUS mandatory
        	DESCRIPTION ""
        	::= {callerMenuStatsEntry 9}

    	callerMenuCallbackNumber OBJECT-TYPE
        	SYNTAX INTEGER
        	ACCESS read-only
        	STATUS mandatory
        	DESCRIPTION ""
        	::= {callerMenuStatsEntry 10}

    	callerMenuNDCTransfer OBJECT-TYPE
        	SYNTAX INTEGER
        	ACCESS read-only
        	STATUS mandatory
        	DESCRIPTION ""
        	::= {callerMenuStatsEntry 11}

    	callerMenuConstantTouch OBJECT-TYPE
        	SYNTAX INTEGER
        	ACCESS read-only
        	STATUS mandatory
        	DESCRIPTION ""
        	::= {callerMenuStatsEntry 12}

    	callerMenuRecordMessage OBJECT-TYPE
        	SYNTAX INTEGER
        	ACCESS read-only
        	STATUS mandatory
        	DESCRIPTION ""
        	::= {callerMenuStatsEntry 13}

    	callerMenuFaxDeposit OBJECT-TYPE
        	SYNTAX INTEGER
        	ACCESS read-only
        	STATUS mandatory
        	DESCRIPTION ""
        	::= {callerMenuStatsEntry 14}

    	callerMenuAdditionalHelp OBJECT-TYPE
        	SYNTAX INTEGER
        	ACCESS read-only
        	STATUS mandatory
        	DESCRIPTION ""
        	::= {callerMenuStatsEntry 15}

    	callerMenuImmediateRecord OBJECT-TYPE
        	SYNTAX INTEGER
        	ACCESS read-only
        	STATUS mandatory
        	DESCRIPTION ""
        	::= {callerMenuStatsEntry 16}

    	callerMenuLogin OBJECT-TYPE
        	SYNTAX INTEGER
        	ACCESS read-only
        	STATUS mandatory
        	DESCRIPTION ""
        	::= {callerMenuStatsEntry 17}

    	callerMenuInvalidCommand OBJECT-TYPE
        	SYNTAX INTEGER
        	ACCESS read-only
        	STATUS mandatory
        	DESCRIPTION ""
        	::= {callerMenuStatsEntry 18}

    	callerMenuCmdTimeout OBJECT-TYPE
        	SYNTAX INTEGER
        	ACCESS read-only
        	STATUS mandatory
        	DESCRIPTION ""
        	::= {callerMenuStatsEntry 19}

-- The following table contains deposit statistics
        depositStatsTable OBJECT-TYPE
                SYNTAX SEQUENCE OF DepositStatsEntry
                ACCESS not-accessible
                STATUS mandatory
                DESCRIPTION "a table consists of deposit statistics for COS 1 - 255"
                ::= {tui 10}

-- Each entry on the deposit Statistics is of the following type
        depositStatsEntry OBJECT-TYPE
                SYNTAX DepositStatsEntry
                ACCESS not-accessible
                STATUS mandatory
                DESCRIPTION "Each row of the table contains deposit statistics related for a COS"
                INDEX {depositStatsCOS}
                ::= {depositStatsTable 1}

	DepositStatsEntry ::= SEQUENCE {
		depositStatsCOS							INTEGER,
		depositMenuOperatorTransfer					INTEGER,
		depositMenuContinueRecording					INTEGER,
		depositMenuReplaymessage					INTEGER,
		depositMenuCallerDeliveryOptionsMenu				INTEGER,
		depositMenuAdditionalHelp					INTEGER,
		depositMenuSendMessage						INTEGER,
		depositMenuTerminateMessageRecord				INTEGER,
		depositMenuDeleteMessage					INTEGER,
		depositMenuInvalidCommand					INTEGER,
		depositMenuCmdTimeout						INTEGER
	}

    	depositStatsCOS OBJECT-TYPE
        	SYNTAX INTEGER (0..255)
        	ACCESS read-only
        	STATUS mandatory
        	DESCRIPTION "COS (key) for the deposit Statistics"
        	::= {depositStatsEntry 1}


    	depositMenuOperatorTransfer OBJECT-TYPE
        	SYNTAX INTEGER
        	ACCESS read-only
        	STATUS mandatory
        	DESCRIPTION ""
        	::= {depositStatsEntry 2}

    	depositMenuContinueRecording OBJECT-TYPE
        	SYNTAX INTEGER
        	ACCESS read-only
        	STATUS mandatory
        	DESCRIPTION ""
        	::= {depositStatsEntry 3}

    	depositMenuReplaymessage OBJECT-TYPE
        	SYNTAX INTEGER
        	ACCESS read-only
        	STATUS mandatory
        	DESCRIPTION ""
        	::= {depositStatsEntry 4}

    	depositMenuCallerDeliveryOptionsMenu OBJECT-TYPE
        	SYNTAX INTEGER
        	ACCESS read-only
        	STATUS mandatory
        	DESCRIPTION ""
        	::= {depositStatsEntry 5}

    	depositMenuAdditionalHelp OBJECT-TYPE
        	SYNTAX INTEGER
        	ACCESS read-only
        	STATUS mandatory
        	DESCRIPTION ""
        	::= {depositStatsEntry 6}

    	depositMenuSendMessage OBJECT-TYPE
        	SYNTAX INTEGER
        	ACCESS read-only
        	STATUS mandatory
        	DESCRIPTION ""
        	::= {depositStatsEntry 7}

    	depositMenuTerminateMessageRecord OBJECT-TYPE
        	SYNTAX INTEGER
        	ACCESS read-only
        	STATUS mandatory
        	DESCRIPTION ""
        	::= {depositStatsEntry 8}

    	depositMenuDeleteMessage OBJECT-TYPE
        	SYNTAX INTEGER
        	ACCESS read-only
        	STATUS mandatory
        	DESCRIPTION ""
        	::= {depositStatsEntry 9}

    	depositMenuInvalidCommand OBJECT-TYPE
        	SYNTAX INTEGER
        	ACCESS read-only
        	STATUS mandatory
        	DESCRIPTION ""
        	::= {depositStatsEntry 10}

    	depositMenuCmdTimeout OBJECT-TYPE
        	SYNTAX INTEGER
        	ACCESS read-only
        	STATUS mandatory
        	DESCRIPTION ""
        	::= {depositStatsEntry 11}

-- The following table contains fax statistics
        faxStatsTable OBJECT-TYPE
                SYNTAX SEQUENCE OF FaxStatsEntry
                ACCESS not-accessible
                STATUS mandatory
                DESCRIPTION "a table consists of fax statistics for COS 1 - 255"
                ::= {tui 11}

-- Each entry on the fax Statistics is of the following type
        faxStatsEntry OBJECT-TYPE
                SYNTAX FaxStatsEntry
                ACCESS not-accessible
                STATUS mandatory
                DESCRIPTION "Each row of the table contains fax statistics related for a COS"
                INDEX {faxStatsCOS}
                ::= {faxStatsTable 1}

	FaxStatsEntry ::= SEQUENCE {
		faxStatsCOS							INTEGER,
		faxAdministrationChangePrimaryFaxNumber				INTEGER,
		faxAdministrationChangeSecondaryFaxNumber			INTEGER,
		faxAdministrationAuto-FaxDeliveryOptions			INTEGER,
		faxAdministrationInvalidCommand					INTEGER,
		faxAdministrationCmdTimeout					INTEGER,
		printFaxMenuPrimaryFaxDelivery					INTEGER,
		printFaxMenuSecondaryFaxDelivery				INTEGER,
		printFaxMenuTemporaryFaxDelivery				INTEGER,
		printFaxMenuCurrentLineFaxDelivery				INTEGER,
		printFaxMenuInvalidCommand					INTEGER,
		printFaxMenuCmdTimeout						INTEGER
	}

    	faxStatsCOS OBJECT-TYPE
        	SYNTAX INTEGER (0..255)
        	ACCESS read-only
        	STATUS mandatory
        	DESCRIPTION "COS (key) for the fax Statistics"
        	::= {faxStatsEntry 1}

    	faxAdministrationChangePrimaryFaxNumber OBJECT-TYPE
        	SYNTAX INTEGER
        	ACCESS read-only
        	STATUS mandatory
        	DESCRIPTION ""
        	::= {faxStatsEntry 2}

    	faxAdministrationChangeSecondaryFaxNumber OBJECT-TYPE
        	SYNTAX INTEGER
        	ACCESS read-only
        	STATUS mandatory
        	DESCRIPTION ""
        	::= {faxStatsEntry 3}

    	faxAdministrationAuto-FaxDeliveryOptions OBJECT-TYPE
        	SYNTAX INTEGER
        	ACCESS read-only
        	STATUS mandatory
        	DESCRIPTION ""
        	::= {faxStatsEntry 4}

    	faxAdministrationInvalidCommand OBJECT-TYPE
        	SYNTAX INTEGER
        	ACCESS read-only
        	STATUS mandatory
        	DESCRIPTION ""
        	::= {faxStatsEntry 5}

    	faxAdministrationCmdTimeout OBJECT-TYPE
        	SYNTAX INTEGER
        	ACCESS read-only
        	STATUS mandatory
        	DESCRIPTION ""
        	::= {faxStatsEntry 6}

    	printFaxMenuPrimaryFaxDelivery OBJECT-TYPE
        	SYNTAX INTEGER
        	ACCESS read-only
        	STATUS mandatory
        	DESCRIPTION ""
        	::= {faxStatsEntry 7}

    	printFaxMenuSecondaryFaxDelivery OBJECT-TYPE
        	SYNTAX INTEGER
        	ACCESS read-only
        	STATUS mandatory
        	DESCRIPTION ""
        	::= {faxStatsEntry 8}

    	printFaxMenuTemporaryFaxDelivery OBJECT-TYPE
        	SYNTAX INTEGER
        	ACCESS read-only
        	STATUS mandatory
        	DESCRIPTION ""
        	::= {faxStatsEntry 9}

    	printFaxMenuCurrentLineFaxDelivery OBJECT-TYPE
        	SYNTAX INTEGER
        	ACCESS read-only
        	STATUS mandatory
        	DESCRIPTION ""
        	::= {faxStatsEntry 10}

    	printFaxMenuInvalidCommand OBJECT-TYPE
        	SYNTAX INTEGER
        	ACCESS read-only
        	STATUS mandatory
        	DESCRIPTION ""
        	::= {faxStatsEntry 11}

    	printFaxMenuCmdTimeout OBJECT-TYPE
        	SYNTAX INTEGER
        	ACCESS read-only
        	STATUS mandatory
        	DESCRIPTION ""
        	::= {faxStatsEntry 12}

-- The following table contains message statistics
        messageStatsTable OBJECT-TYPE
                SYNTAX SEQUENCE OF MessageStatsEntry
                ACCESS not-accessible
                STATUS mandatory
                DESCRIPTION "a table consists of message statistics for COS 1 - 255"
                ::= {tui 12}

-- Each entry on the message Statistics is of the following type
        messageStatsEntry OBJECT-TYPE
                SYNTAX MessageStatsEntry
                ACCESS not-accessible
                STATUS mandatory
                DESCRIPTION "Each row of the table contains message statistics related for a COS"
                INDEX {messageStatsCOS}
                ::= {messageStatsTable 1}

	MessageStatsEntry ::= SEQUENCE {
		messageStatsCOS							INTEGER,
		messageNotificationOptionsPlayMWINumber				INTEGER,
		messageNotificationOptionsModifyMWINumber			INTEGER,
		messageNotificationOptionsEnableDisableMWI			INTEGER,
		messageNotificationOptionsEnableDisableMWIonUrgentOnly		INTEGER,
		messageNotificationOptionsInvalidCommand			INTEGER,
		messageNotificationOptionsCmdTimeout				INTEGER
	}

    	messageStatsCOS OBJECT-TYPE
        	SYNTAX INTEGER (0..255)
        	ACCESS read-only
        	STATUS mandatory
        	DESCRIPTION "COS (key) for the fax Statistics"
        	::= {messageStatsEntry 1}

   	messageNotificationOptionsPlayMWINumber OBJECT-TYPE
        	SYNTAX INTEGER
        	ACCESS read-only
        	STATUS mandatory
        	DESCRIPTION ""
        	::= {messageStatsEntry 2}

    	messageNotificationOptionsModifyMWINumber OBJECT-TYPE
        	SYNTAX INTEGER
        	ACCESS read-only
        	STATUS mandatory
        	DESCRIPTION ""
        	::= {messageStatsEntry 3}

    	messageNotificationOptionsEnableDisableMWI OBJECT-TYPE
        	SYNTAX INTEGER
        	ACCESS read-only
        	STATUS mandatory
        	DESCRIPTION ""
        	::= {messageStatsEntry 4}

    	messageNotificationOptionsEnableDisableMWIonUrgentOnly OBJECT-TYPE
        	SYNTAX INTEGER
        	ACCESS read-only
        	STATUS mandatory
        	DESCRIPTION ""
        	::= {messageStatsEntry 5}

    	messageNotificationOptionsInvalidCommand OBJECT-TYPE
        	SYNTAX INTEGER
        	ACCESS read-only
        	STATUS mandatory
        	DESCRIPTION ""
        	::= {messageStatsEntry 6}

    	messageNotificationOptionsCmdTimeout OBJECT-TYPE
        	SYNTAX INTEGER
        	ACCESS read-only
        	STATUS mandatory
        	DESCRIPTION ""
        	::= {messageStatsEntry 7}

-- The following table contains name statistics
        nameStatsTable OBJECT-TYPE
                SYNTAX SEQUENCE OF NameStatsEntry
                ACCESS not-accessible
                STATUS mandatory
                DESCRIPTION "a table consists of name statistics for COS 1 - 255"
                ::= {tui 13}

-- Each entry on the name Statistics is of the following type
        nameStatsEntry OBJECT-TYPE
                SYNTAX NameStatsEntry
                ACCESS not-accessible
                STATUS mandatory
                DESCRIPTION "Each row of the table contains name statistics related for a COS"
                INDEX {nameStatsCOS}
                ::= {nameStatsTable 1}

	NameStatsEntry ::= SEQUENCE {
		nameStatsCOS							INTEGER,
		nameOptionsPlayName						INTEGER,
		nameOptionsRecordName						INTEGER,
		nameOptionsDeleteName						INTEGER,
		nameOptionsInvalidCommand					INTEGER,
		nameOptionsCmdTimeout		  				INTEGER
	}

    	nameStatsCOS OBJECT-TYPE
        	SYNTAX INTEGER (0..255)
        	ACCESS read-only
        	STATUS mandatory
        	DESCRIPTION "COS (key) for the name Statistics"
        	::= {nameStatsEntry 1}

   	nameOptionsPlayName OBJECT-TYPE
        	SYNTAX INTEGER
        	ACCESS read-only
        	STATUS mandatory
        	DESCRIPTION ""
        	::= {nameStatsEntry 2}

    	nameOptionsRecordName OBJECT-TYPE
        	SYNTAX INTEGER
        	ACCESS read-only
        	STATUS mandatory
        	DESCRIPTION ""
        	::= {nameStatsEntry 3}

    	nameOptionsDeleteName OBJECT-TYPE
        	SYNTAX INTEGER
        	ACCESS read-only
        	STATUS mandatory
        	DESCRIPTION ""
        	::= {nameStatsEntry 4}

    	nameOptionsInvalidCommand OBJECT-TYPE
        	SYNTAX INTEGER
        	ACCESS read-only
        	STATUS mandatory
        	DESCRIPTION ""
        	::= {nameStatsEntry 5}

    	nameOptionsCmdTimeout OBJECT-TYPE
        	SYNTAX INTEGER
        	ACCESS read-only
        	STATUS mandatory
        	DESCRIPTION ""
        	::= {nameStatsEntry 6}

-- The following table contains personal statistics
        personalStatsTable OBJECT-TYPE
                SYNTAX SEQUENCE OF PersonalStatsEntry
                ACCESS not-accessible
                STATUS mandatory
                DESCRIPTION "a table consists of personal statistics for COS 1 - 255"
                ::= {tui 14}

-- Each entry on the personal Statistics is of the following type
        personalStatsEntry OBJECT-TYPE
                SYNTAX PersonalStatsEntry
                ACCESS not-accessible
                STATUS mandatory
                DESCRIPTION "Each row of the table contains personal statistics related for a COS"
                INDEX {personalStatsCOS}
                ::= {personalStatsTable 1}

	PersonalStatsEntry ::= SEQUENCE {
		personalStatsCOS						INTEGER,
		personalOperatorOptionsPlayOperatorNumber			INTEGER,
		personalOperatorOptionsModifyOperatorNumber			INTEGER,
		personalOperatorOptionsInvalidCommand				INTEGER,
		personalOperatorOptionsCmdTimeout				INTEGER,
		personalOptionsFaxAdministration				INTEGER,
		personalOptionsMessageNotificationOptions			INTEGER,
		personalOptionsPersonalPreferences				INTEGER,
		personalOptionsCallerIDRestrictionToggle			INTEGER,
		personalOptionsBypassPasswordToggle				INTEGER,
		personalOptionsInvalidCommand					INTEGER,
		personalOptionsCmdTimeout					INTEGER,
		personalPreferencesLoginPassword				INTEGER,
		personalPreferencesPlaybackPreferences				INTEGER,
		personalPreferencesNameOptions					INTEGER,
		personalPreferencesPersonalOperatorOptions			INTEGER,
		personalPreferencesInvalidCommand				INTEGER,
		personalPreferencesCmdTimeout					INTEGER
	}

    	personalStatsCOS OBJECT-TYPE
        	SYNTAX INTEGER (0..255)
        	ACCESS read-only
        	STATUS mandatory
        	DESCRIPTION "COS (key) for the personal Statistics"
        	::= {personalStatsEntry 1}

    	personalOperatorOptionsPlayOperatorNumber OBJECT-TYPE
        	SYNTAX INTEGER
        	ACCESS read-only
        	STATUS mandatory
        	DESCRIPTION ""
        	::= {personalStatsEntry 2}

    	personalOperatorOptionsModifyOperatorNumber OBJECT-TYPE
        	SYNTAX INTEGER
        	ACCESS read-only
        	STATUS mandatory
        	DESCRIPTION ""
        	::= {personalStatsEntry 3}

    	personalOperatorOptionsInvalidCommand OBJECT-TYPE
        	SYNTAX INTEGER
        	ACCESS read-only
        	STATUS mandatory
        	DESCRIPTION ""
        	::= {personalStatsEntry 4}

    	personalOperatorOptionsCmdTimeout OBJECT-TYPE
        	SYNTAX INTEGER
        	ACCESS read-only
        	STATUS mandatory
        	DESCRIPTION ""
        	::= {personalStatsEntry 5}

    	personalOptionsFaxAdministration OBJECT-TYPE
        	SYNTAX INTEGER
        	ACCESS read-only
        	STATUS mandatory
        	DESCRIPTION ""
        	::= {personalStatsEntry 6}

    	personalOptionsMessageNotificationOptions OBJECT-TYPE
        	SYNTAX INTEGER
        	ACCESS read-only
        	STATUS mandatory
        	DESCRIPTION ""
        	::= {personalStatsEntry 7}

    	personalOptionsPersonalPreferences OBJECT-TYPE
        	SYNTAX INTEGER
        	ACCESS read-only
        	STATUS mandatory
        	DESCRIPTION ""
        	::= {personalStatsEntry 8}

    	personalOptionsCallerIDRestrictionToggle OBJECT-TYPE
        	SYNTAX INTEGER
        	ACCESS read-only
        	STATUS mandatory
        	DESCRIPTION ""
        	::= {personalStatsEntry 9}

    	personalOptionsBypassPasswordToggle OBJECT-TYPE
        	SYNTAX INTEGER
        	ACCESS read-only
        	STATUS mandatory
        	DESCRIPTION ""
        	::= {personalStatsEntry 10}

    	personalOptionsInvalidCommand OBJECT-TYPE
        	SYNTAX INTEGER
        	ACCESS read-only
        	STATUS mandatory
        	DESCRIPTION ""
        	::= {personalStatsEntry 11}

    	personalOptionsCmdTimeout OBJECT-TYPE
        	SYNTAX INTEGER
        	ACCESS read-only
        	STATUS mandatory
        	DESCRIPTION ""
        	::= {personalStatsEntry 12}

    	personalPreferencesLoginPassword OBJECT-TYPE
        	SYNTAX INTEGER
        	ACCESS read-only
        	STATUS mandatory
        	DESCRIPTION ""
        	::= {personalStatsEntry 13}

    	personalPreferencesPlaybackPreferences OBJECT-TYPE
        	SYNTAX INTEGER
        	ACCESS read-only
        	STATUS mandatory
        	DESCRIPTION ""
        	::= {personalStatsEntry 14}

    	personalPreferencesNameOptions OBJECT-TYPE
        	SYNTAX INTEGER
        	ACCESS read-only
        	STATUS mandatory
        	DESCRIPTION ""
        	::= {personalStatsEntry 15}

    	personalPreferencesPersonalOperatorOptions OBJECT-TYPE
        	SYNTAX INTEGER
        	ACCESS read-only
        	STATUS mandatory
        	DESCRIPTION ""
        	::= {personalStatsEntry 16}

    	personalPreferencesInvalidCommand OBJECT-TYPE
        	SYNTAX INTEGER
        	ACCESS read-only
        	STATUS mandatory
        	DESCRIPTION ""
        	::= {personalStatsEntry 17}

    	personalPreferencesCmdTimeout OBJECT-TYPE
        	SYNTAX INTEGER
        	ACCESS read-only
        	STATUS mandatory
        	DESCRIPTION ""
        	::= {personalStatsEntry 18}

-- The following table contains play statistics
        playStatsTable OBJECT-TYPE
                SYNTAX SEQUENCE OF PlayStatsEntry
                ACCESS not-accessible
                STATUS mandatory
                DESCRIPTION "a table consists of play statistics for COS 1 - 255"
                ::= {tui 15}

-- Each entry on the play Statistics is of the following type
        playStatsEntry OBJECT-TYPE
                SYNTAX PlayStatsEntry
                ACCESS not-accessible
                STATUS mandatory
                DESCRIPTION "Each row of the table contains play statistics related for a COS"
                INDEX {playStatsCOS}
                ::= {playStatsTable 1}

	PlayStatsEntry ::= SEQUENCE {
		playStatsCOS						INTEGER,
		playMenuBack-upMessage					INTEGER,
		playMenuFastForward					INTEGER,
		playMenuPrintFax					INTEGER,
		playMenuPlayOptionsMenu					INTEGER,
		playMenuCopyMessageToAnotherMailbox			INTEGER,
		playMenuDeleteMessage					INTEGER,
		playMenuAutomaticCallback				INTEGER,
		playMenuSaveMessage					INTEGER,
		playMenuReplayMessage					INTEGER,
		playMenuSkipToEndOfMessage				INTEGER,
		playMenuReply						INTEGER,
		playMenuNextMessage					INTEGER,
		playMenuInvalidCommand					INTEGER,
		playMenuAfterReplayMessage				INTEGER,
		playMenuAfterPrintFax					INTEGER,
		playMenuAfterPlayOptionsMenu				INTEGER,
		playMenuAfterCopyMessageToAnotherMailbox		INTEGER,
		playMenuAfterDeleteMessage				INTEGER,
		playMenuAfterAutomaticCallback				INTEGER,
		playMenuAfterReply					INTEGER,
		playMenuAfterNextMessage				INTEGER,
		playMenuAfterInvalidCommand				INTEGER,
		playMenuAfterCmdTimeout					INTEGER,
		playOptionsPreviousMessage				INTEGER,
		playOptionsTogglePlaybackMode				INTEGER,
		playOptionsPlayWithTimeDate				INTEGER,
		playOptionsInvalidCommand				INTEGER,
		playOptionsCmdTimeout					INTEGER,
		playbackPreferencesLIFOFIFOPlaybackOrder		INTEGER,
		playbackPreferencesNormalAuto-Playback			INTEGER,
		playbackPreferencesTimeDateStampToggle			INTEGER,
		playbackPreferencesInvalidCommand			INTEGER,
		playbackPreferencesCmdTimeout				INTEGER
	}

    	playStatsCOS OBJECT-TYPE
        	SYNTAX INTEGER (0..255)
        	ACCESS read-only
        	STATUS mandatory
        	DESCRIPTION "COS (key) for the play Statistics"
        	::= {playStatsEntry 1}

    	playMenuBack-upMessage OBJECT-TYPE
        	SYNTAX INTEGER
        	ACCESS read-only
        	STATUS mandatory
        	DESCRIPTION ""
        	::= {playStatsEntry 2}

    	playMenuFastForward OBJECT-TYPE
        	SYNTAX INTEGER
        	ACCESS read-only
        	STATUS mandatory
        	DESCRIPTION ""
        	::= {playStatsEntry 3}

    	playMenuPrintFax OBJECT-TYPE
        	SYNTAX INTEGER
        	ACCESS read-only
        	STATUS mandatory
        	DESCRIPTION ""
        	::= {playStatsEntry 4}

    	playMenuPlayOptionsMenu OBJECT-TYPE
        	SYNTAX INTEGER
        	ACCESS read-only
        	STATUS mandatory
        	DESCRIPTION ""
        	::= {playStatsEntry 5}

    	playMenuCopyMessageToAnotherMailbox OBJECT-TYPE
        	SYNTAX INTEGER
        	ACCESS read-only
        	STATUS mandatory
        	DESCRIPTION ""
        	::= {playStatsEntry 6}

    	playMenuDeleteMessage OBJECT-TYPE
        	SYNTAX INTEGER
        	ACCESS read-only
        	STATUS mandatory
        	DESCRIPTION ""
        	::= {playStatsEntry 7}

    	playMenuAutomaticCallback OBJECT-TYPE
        	SYNTAX INTEGER
        	ACCESS read-only
        	STATUS mandatory
        	DESCRIPTION ""
        	::= {playStatsEntry 8}

    	playMenuSaveMessage OBJECT-TYPE
        	SYNTAX INTEGER
        	ACCESS read-only
        	STATUS mandatory
        	DESCRIPTION ""
        	::= {playStatsEntry 9}

    	playMenuReplayMessage OBJECT-TYPE
        	SYNTAX INTEGER
        	ACCESS read-only
        	STATUS mandatory
        	DESCRIPTION ""
        	::= {playStatsEntry 10}

    	playMenuSkipToEndOfMessage OBJECT-TYPE
        	SYNTAX INTEGER
        	ACCESS read-only
        	STATUS mandatory
        	DESCRIPTION ""
        	::= {playStatsEntry 11}

    	playMenuReply OBJECT-TYPE
        	SYNTAX INTEGER
        	ACCESS read-only
        	STATUS mandatory
        	DESCRIPTION ""
        	::= {playStatsEntry 12}

    	playMenuNextMessage OBJECT-TYPE
        	SYNTAX INTEGER
        	ACCESS read-only
        	STATUS mandatory
        	DESCRIPTION ""
        	::= {playStatsEntry 13}

    	playMenuInvalidCommand OBJECT-TYPE
        	SYNTAX INTEGER
        	ACCESS read-only
        	STATUS mandatory
        	DESCRIPTION ""
        	::= {playStatsEntry 14}

    	playMenuAfterReplayMessage OBJECT-TYPE
        	SYNTAX INTEGER
        	ACCESS read-only
        	STATUS mandatory
        	DESCRIPTION ""
        	::= {playStatsEntry 15}

    	playMenuAfterPrintFax OBJECT-TYPE
        	SYNTAX INTEGER
        	ACCESS read-only
        	STATUS mandatory
        	DESCRIPTION ""
        	::= {playStatsEntry 16}

    	playMenuAfterPlayOptionsMenu OBJECT-TYPE
        	SYNTAX INTEGER
        	ACCESS read-only
        	STATUS mandatory
        	DESCRIPTION ""
        	::= {playStatsEntry 17}

    	playMenuAfterCopyMessageToAnotherMailbox OBJECT-TYPE
        	SYNTAX INTEGER
        	ACCESS read-only
        	STATUS mandatory
        	DESCRIPTION ""
        	::= {playStatsEntry 18}

    	playMenuAfterDeleteMessage OBJECT-TYPE
        	SYNTAX INTEGER
        	ACCESS read-only
        	STATUS mandatory
        	DESCRIPTION ""
        	::= {playStatsEntry 19}

    	playMenuAfterAutomaticCallback OBJECT-TYPE
        	SYNTAX INTEGER
        	ACCESS read-only
        	STATUS mandatory
        	DESCRIPTION ""
        	::= {playStatsEntry 20}

    	playMenuAfterReply OBJECT-TYPE
        	SYNTAX INTEGER
        	ACCESS read-only
        	STATUS mandatory
        	DESCRIPTION ""
        	::= {playStatsEntry 21}

    	playMenuAfterNextMessage OBJECT-TYPE
        	SYNTAX INTEGER
        	ACCESS read-only
        	STATUS mandatory
        	DESCRIPTION ""
        	::= {playStatsEntry 22}

    	playMenuAfterInvalidCommand OBJECT-TYPE
        	SYNTAX INTEGER
        	ACCESS read-only
        	STATUS mandatory
        	DESCRIPTION ""
        	::= {playStatsEntry 23}

    	playMenuAfterCmdTimeout OBJECT-TYPE
        	SYNTAX INTEGER
        	ACCESS read-only
        	STATUS mandatory
        	DESCRIPTION ""
        	::= {playStatsEntry 24}

    	playOptionsPreviousMessage OBJECT-TYPE
        	SYNTAX INTEGER
        	ACCESS read-only
        	STATUS mandatory
        	DESCRIPTION ""
        	::= {playStatsEntry 25}

    	playOptionsTogglePlaybackMode OBJECT-TYPE
        	SYNTAX INTEGER
        	ACCESS read-only
        	STATUS mandatory
        	DESCRIPTION ""
        	::= {playStatsEntry 26}

    	playOptionsPlayWithTimeDate OBJECT-TYPE
        	SYNTAX INTEGER
        	ACCESS read-only
        	STATUS mandatory
        	DESCRIPTION ""
        	::= {playStatsEntry 27}

    	playOptionsInvalidCommand OBJECT-TYPE
        	SYNTAX INTEGER
        	ACCESS read-only
        	STATUS mandatory
        	DESCRIPTION ""
        	::= {playStatsEntry 28}

    	playOptionsCmdTimeout OBJECT-TYPE
        	SYNTAX INTEGER
        	ACCESS read-only
        	STATUS mandatory
        	DESCRIPTION ""
        	::= {playStatsEntry 29}

    	playbackPreferencesLIFOFIFOPlaybackOrder OBJECT-TYPE
        	SYNTAX INTEGER
        	ACCESS read-only
        	STATUS mandatory
        	DESCRIPTION ""
        	::= {playStatsEntry 30}

    	playbackPreferencesNormalAuto-Playback OBJECT-TYPE
        	SYNTAX INTEGER
        	ACCESS read-only
        	STATUS mandatory
        	DESCRIPTION ""
        	::= {playStatsEntry 31}

    	playbackPreferencesTimeDateStampToggle OBJECT-TYPE
        	SYNTAX INTEGER
        	ACCESS read-only
        	STATUS mandatory
        	DESCRIPTION ""
        	::= {playStatsEntry 32}

    	playbackPreferencesInvalidCommand OBJECT-TYPE
        	SYNTAX INTEGER
        	ACCESS read-only
        	STATUS mandatory
        	DESCRIPTION ""
        	::= {playStatsEntry 33}

    	playbackPreferencesCmdTimeout OBJECT-TYPE
        	SYNTAX INTEGER
        	ACCESS read-only
        	STATUS mandatory
        	DESCRIPTION ""
        	::= {playStatsEntry 34}

-- The following table contains record statistics
        recordStatsTable OBJECT-TYPE
                SYNTAX SEQUENCE OF RecordStatsEntry
                ACCESS not-accessible
                STATUS mandatory
                DESCRIPTION "a table consists of record statistics for COS 1 - 255"
                ::= {tui 16}

-- Each entry on the record Statistics is of the following type
        recordStatsEntry OBJECT-TYPE
                SYNTAX RecordStatsEntry
                ACCESS not-accessible
                STATUS mandatory
                DESCRIPTION "Each row of the table contains record statistics related for a COS"
                INDEX {recordStatsCOS}
                ::= {recordStatsTable 1}

	RecordStatsEntry ::= SEQUENCE {
		recordStatsCOS						INTEGER,
		recordMenuReplayMessage					INTEGER,
		recordMenuMessageDeliveryOptionsMenu			INTEGER,
		recordMenuDeleteRecordedMessage				INTEGER,
		recordMenuSendMessage					INTEGER,
		recordMenuTerminateMessageRecord			INTEGER,
		recordMenuInvalidCommand				INTEGER,
		recordMenuContinueRecording				INTEGER,
		recordMenuRecordMessage					INTEGER,
		recordMenuCmdTimeout					INTEGER
	}

    	recordStatsCOS OBJECT-TYPE
        	SYNTAX INTEGER (0..255)
        	ACCESS read-only
        	STATUS mandatory
        	DESCRIPTION "COS (key) for the record Statistics"
        	::= {recordStatsEntry 1}


    	recordMenuReplayMessage OBJECT-TYPE
        	SYNTAX INTEGER
        	ACCESS read-only
        	STATUS mandatory
        	DESCRIPTION "No of in record menu"
        	::= {recordStatsEntry 2}

    	recordMenuMessageDeliveryOptionsMenu OBJECT-TYPE
        	SYNTAX INTEGER
        	ACCESS read-only
        	STATUS mandatory
        	DESCRIPTION ""
        	::= {recordStatsEntry 3}

    	recordMenuDeleteRecordedMessage OBJECT-TYPE
        	SYNTAX INTEGER
        	ACCESS read-only
        	STATUS mandatory
        	DESCRIPTION ""
        	::= {recordStatsEntry 4}

    	recordMenuSendMessage OBJECT-TYPE
        	SYNTAX INTEGER
        	ACCESS read-only
        	STATUS mandatory
        	DESCRIPTION ""
        	::= {recordStatsEntry 5}

    	recordMenuTerminateMessageRecord OBJECT-TYPE
        	SYNTAX INTEGER
        	ACCESS read-only
        	STATUS mandatory
        	DESCRIPTION ""
        	::= {recordStatsEntry 6}

    	recordMenuInvalidCommand OBJECT-TYPE
        	SYNTAX INTEGER
        	ACCESS read-only
        	STATUS mandatory
        	DESCRIPTION ""
        	::= {recordStatsEntry 7}

    	recordMenuContinueRecording OBJECT-TYPE
        	SYNTAX INTEGER
        	ACCESS read-only
        	STATUS mandatory
        	DESCRIPTION ""
        	::= {recordStatsEntry 8}

    	recordMenuRecordMessage OBJECT-TYPE
        	SYNTAX INTEGER
        	ACCESS read-only
        	STATUS mandatory
        	DESCRIPTION ""
        	::= {recordStatsEntry 9}

    	recordMenuCmdTimeout OBJECT-TYPE
        	SYNTAX INTEGER
        	ACCESS read-only
        	STATUS mandatory
        	DESCRIPTION ""
        	::= {recordStatsEntry 10}

-- The following table contains redirect statistics
        redirectStatsTable OBJECT-TYPE
                SYNTAX SEQUENCE OF RedirectStatsEntry
                ACCESS not-accessible
                STATUS mandatory
                DESCRIPTION "a table consists of redirect statistics for COS 1 - 255"
                ::= {tui 17}

-- Each entry on the redirect Statistics is of the following type
        redirectStatsEntry OBJECT-TYPE
                SYNTAX RedirectStatsEntry
                ACCESS not-accessible
                STATUS mandatory
                DESCRIPTION "Each row of the table contains redirect statistics related for a COS"
                INDEX {redirectStatsCOS}
                ::= {redirectStatsTable 1}

	RedirectStatsEntry ::= SEQUENCE {
		redirectStatsCOS						INTEGER,
		redirectMenuReplayRecordedComment				INTEGER,
		redirectMenuContinueRecordingComment				INTEGER,
		redirectMenuRecordComment					INTEGER,
		redirectMenuMessageDeliveryOptionsMenu				INTEGER,
		redirectMenuDeleteRecordedComment				INTEGER,
		redirectMenuSendMessage						INTEGER,
		redirectMenuCmdTimeout						INTEGER,
		redirectMenuTerminateCommentRecord				INTEGER,
		redirectMenuInvalidCommand					INTEGER
	}

    	redirectStatsCOS OBJECT-TYPE
        	SYNTAX INTEGER (0..255)
        	ACCESS read-only
        	STATUS mandatory
        	DESCRIPTION "COS (key) for the redirect Statistics"
        	::= {redirectStatsEntry 1}

    	redirectMenuReplayRecordedComment OBJECT-TYPE
        	SYNTAX INTEGER
        	ACCESS read-only
        	STATUS mandatory
        	DESCRIPTION "No of recorded comments replayed after recording in redirect menu"
        	::= {redirectStatsEntry 2}

    	redirectMenuContinueRecordingComment OBJECT-TYPE
        	SYNTAX INTEGER
        	ACCESS read-only
        	STATUS mandatory
        	DESCRIPTION "No of recorded comments continued after recording in redirect menu"
        	::= {redirectStatsEntry 3}

    	redirectMenuRecordComment OBJECT-TYPE
        	SYNTAX INTEGER
        	ACCESS read-only
        	STATUS mandatory
        	DESCRIPTION "No of comments recorded after recording in redirect menu"
        	::= {redirectStatsEntry 4}

    	redirectMenuMessageDeliveryOptionsMenu OBJECT-TYPE
        	SYNTAX INTEGER
        	ACCESS read-only
        	STATUS mandatory
        	DESCRIPTION "No of special delivery options menu selected after recording message in redirect menu"
        	::= {redirectStatsEntry 5}

    	redirectMenuDeleteRecordedComment OBJECT-TYPE
        	SYNTAX INTEGER
        	ACCESS read-only
        	STATUS mandatory
        	DESCRIPTION "No of recorded comments deleted after recording in redirect menu"
        	::= {redirectStatsEntry 6}

    	redirectMenuSendMessage OBJECT-TYPE
        	SYNTAX INTEGER
        	ACCESS read-only
        	STATUS mandatory
        	DESCRIPTION "No of messages sent after recording in redirect menu"
        	::= {redirectStatsEntry 7}

    	redirectMenuCmdTimeout OBJECT-TYPE
        	SYNTAX INTEGER
        	ACCESS read-only
        	STATUS mandatory
        	DESCRIPTION "No of timeouts waiting for user input after recording in redirect menu"
        	::= {redirectStatsEntry 8}

    	redirectMenuTerminateCommentRecord OBJECT-TYPE
        	SYNTAX INTEGER
        	ACCESS read-only
        	STATUS mandatory
        	DESCRIPTION "No of comment record terminated in redirect menu"
        	::= {redirectStatsEntry 9}

    	redirectMenuInvalidCommand OBJECT-TYPE
        	SYNTAX INTEGER
        	ACCESS read-only
        	STATUS mandatory
        	DESCRIPTION "No of invalid commands in redirect menu"
        	::= {redirectStatsEntry 10}

-- The following table contains reply statistics
        replyStatsTable OBJECT-TYPE
                SYNTAX SEQUENCE OF ReplyStatsEntry
                ACCESS not-accessible
                STATUS mandatory
                DESCRIPTION "a table consists of reply statistics for COS 1 - 255"
                ::= {tui 18}

-- Each entry on the reply Statistics is of the following type
        replyStatsEntry OBJECT-TYPE
                SYNTAX ReplyStatsEntry
                ACCESS not-accessible
                STATUS mandatory
                DESCRIPTION "Each row of the table contains reply statistics related for a COS"
                INDEX {replyStatsCOS}
                ::= {replyStatsTable 1}

	ReplyStatsEntry ::= SEQUENCE {
		replyStatsCOS						INTEGER,
		replyMenuReplayReply					INTEGER,
		replyMenuMessageDeliveryOptionsMenu			INTEGER,
		replyMenuDeleteReply					INTEGER,
		replyMenuSendReply					INTEGER,
		replyMenuTerminateReplyRecord				INTEGER,
		replyMenuInvalidCommand					INTEGER,
		replyMenuContinueRecordingReply				INTEGER,
		replyMenuRecordReply					INTEGER,
		replyMenuCmdTimeout					INTEGER
	}

    	replyStatsCOS OBJECT-TYPE
        	SYNTAX INTEGER (0..255)
        	ACCESS read-only
        	STATUS mandatory
        	DESCRIPTION "COS (key) for the reply Statistics"
        	::= {replyStatsEntry 1}


    	replyMenuReplayReply OBJECT-TYPE
        	SYNTAX INTEGER
        	ACCESS read-only
        	STATUS mandatory
        	DESCRIPTION "No of replies replayed in reply menu"
        	::= {replyStatsEntry 2}

    	replyMenuMessageDeliveryOptionsMenu OBJECT-TYPE
        	SYNTAX INTEGER
        	ACCESS read-only
        	STATUS mandatory
        	DESCRIPTION "No of special delivery options selected in reply menu"
        	::= {replyStatsEntry 3}

    	replyMenuDeleteReply OBJECT-TYPE
        	SYNTAX INTEGER
        	ACCESS read-only
        	STATUS mandatory
        	DESCRIPTION "No of replies deleted in reply menu"
        	::= {replyStatsEntry 4}

    	replyMenuSendReply OBJECT-TYPE
        	SYNTAX INTEGER
        	ACCESS read-only
        	STATUS mandatory
        	DESCRIPTION "No of replies sent in reply menu"
        	::= {replyStatsEntry 5}

    	replyMenuTerminateReplyRecord OBJECT-TYPE
        	SYNTAX INTEGER
        	ACCESS read-only
        	STATUS mandatory
        	DESCRIPTION "No of reply recordings terminated in reply menu"
        	::= {replyStatsEntry 6}

    	replyMenuInvalidCommand OBJECT-TYPE
        	SYNTAX INTEGER
        	ACCESS read-only
        	STATUS mandatory
        	DESCRIPTION "No of invalid commands in reply menu"
        	::= {replyStatsEntry 7}

    	replyMenuContinueRecordingReply OBJECT-TYPE
        	SYNTAX INTEGER
        	ACCESS read-only
        	STATUS mandatory
        	DESCRIPTION "No of times to continue recording after recording in reply menu"
        	::= {replyStatsEntry 8}

    	replyMenuRecordReply OBJECT-TYPE
        	SYNTAX INTEGER
        	ACCESS read-only
        	STATUS mandatory
        	DESCRIPTION "No of times to record reply after recording in reply menu"
        	::= {replyStatsEntry 9}

    	replyMenuCmdTimeout OBJECT-TYPE
        	SYNTAX INTEGER
        	ACCESS read-only
        	STATUS mandatory
        	DESCRIPTION "No of timeouts for user input after recording in reply menu"
        	::= {replyStatsEntry 10}

-- The following table contains special Delivery statistics
        specialDeliveryStatsTable OBJECT-TYPE
                SYNTAX SEQUENCE OF SpecialDeliveryStatsEntry
                ACCESS not-accessible
                STATUS mandatory
                DESCRIPTION "a table consists of special Delivery statistics for COS 1 - 255"
                ::= {tui 19}

-- Each entry on the special Delivery Statistics is of the following type
        specialDeliveryStatsEntry OBJECT-TYPE
                SYNTAX SpecialDeliveryStatsEntry
                ACCESS not-accessible
                STATUS mandatory
                DESCRIPTION "Each row of the table contains special Delivery statistics related for a COS"
                INDEX {specialDeliveryStatsCOS}
                ::= {specialDeliveryStatsTable 1}

	SpecialDeliveryStatsEntry ::= SEQUENCE {
		specialDeliveryStatsCOS						INTEGER,
		specialDeliveryOptionsMenuUrgentMessage				INTEGER,
		specialDeliveryOptionsMenuPrivateMessage			INTEGER,
		specialDeliveryOptionsMenuFutureDelivery			INTEGER,
		specialDeliveryOptionsMenuSendMessage				INTEGER,
		specialDeliveryOptionsMenuCancelDeliveryOptions			INTEGER,
		specialDeliveryOptionsMenuInvalidCommand			INTEGER,
		specialDeliveryOptionsMenuCmdTimeout				INTEGER
	}

    	specialDeliveryStatsCOS OBJECT-TYPE
        	SYNTAX INTEGER (0..255)
        	ACCESS read-only
        	STATUS mandatory
        	DESCRIPTION "COS (key) for the special Delivery Statistics"
        	::= {specialDeliveryStatsEntry 1}

    	specialDeliveryOptionsMenuUrgentMessage OBJECT-TYPE
        	SYNTAX INTEGER
        	ACCESS read-only
        	STATUS mandatory
        	DESCRIPTION "No of messages set to urgent in special delivery options menu"
        	::= {specialDeliveryStatsEntry 2}

    	specialDeliveryOptionsMenuPrivateMessage OBJECT-TYPE
        	SYNTAX INTEGER
        	ACCESS read-only
        	STATUS mandatory
        	DESCRIPTION "No of messages selected as private in special delivery options menu"
        	::= {specialDeliveryStatsEntry 3}

    	specialDeliveryOptionsMenuFutureDelivery OBJECT-TYPE
        	SYNTAX INTEGER
        	ACCESS read-only
        	STATUS mandatory
        	DESCRIPTION "No of messages selected as future delivery in special delivery options menu"
        	::= {specialDeliveryStatsEntry 4}

    	specialDeliveryOptionsMenuSendMessage OBJECT-TYPE
        	SYNTAX INTEGER
        	ACCESS read-only
        	STATUS mandatory
        	DESCRIPTION "No of messages sent in special delivery options menu"
        	::= {specialDeliveryStatsEntry 5}

    	specialDeliveryOptionsMenuCancelDeliveryOptions OBJECT-TYPE
        	SYNTAX INTEGER
        	ACCESS read-only
        	STATUS mandatory
        	DESCRIPTION "No of Delivery Options cancelled in special delivery options menu"
        	::= {specialDeliveryStatsEntry 6}

    	specialDeliveryOptionsMenuInvalidCommand OBJECT-TYPE
        	SYNTAX INTEGER
        	ACCESS read-only
        	STATUS mandatory
        	DESCRIPTION "No of invalid commands in special delivery options menu"
        	::= {specialDeliveryStatsEntry 7}

    	specialDeliveryOptionsMenuCmdTimeout OBJECT-TYPE
        	SYNTAX INTEGER
        	ACCESS read-only
        	STATUS mandatory
        	DESCRIPTION "No of timeouts for user input in special delivery options menu"
        	::= {specialDeliveryStatsEntry 8}



-- ----------------------------------------------------------------------------------------------

END

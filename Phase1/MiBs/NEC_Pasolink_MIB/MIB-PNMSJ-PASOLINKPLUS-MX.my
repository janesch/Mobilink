-------------------------------------------------------------------------------
-- Release Date : 2007/07/30
--    Version   : Ver.1.19
-------------------------------------------------------------------------------


MIB-PNMSJ-PASOLINKPLUS-MX DEFINITIONS ::= BEGIN

-----------------------------------------------
-- INPORTS Definitions
-----------------------------------------------

	IMPORTS
		IpAddress,Counter,TimeTicks,enterprises
			FROM RFC1155-SMI
		OBJECT-TYPE
			FROM RFC-1212
		DisplayString
			FROM RFC1213-MIB
		pnms
			FROM NEC-SMI;

-----------------------------------------------
-- Begin User MIB Object Definitions
-----------------------------------------------

	SeverityValue	::= TEXTUAL-CONVENTION
		STATUS		current
		DESCRIPTION	"Severity (CCITT Rec. X.733)
					  invalid(0),
					  clear(1),
					  minor(2),
					  major(3),
					  critical(4)"
		SYNTAX		INTEGER (0..4)

	AlarmTypeValue	::= TEXTUAL-CONVENTION
		STATUS		current
		DESCRIPTION	"Alarm Type (CCITT Rec. X.733)
					  invalid(0),
					  communicationAlarm(1),
					  qualityOfServiceAlarm(2),
					  processingErrorAlarm(3),
					  equipmentAlarm(4),
					  environmentalAlarm(5),
					  integrityViolationAlarm(6),
					  operationalViolationAlarm(7),
					  physicalViolationAlarm(8),
					  securityViolationAlarm(9),
					  timeDomainViolationAlarm(10)"
		SYNTAX		INTEGER (0..10)

	ProbableCauseValue	::= TEXTUAL-CONVENTION
		STATUS		current
		DESCRIPTION	"Probable Cause (CCITT Rec. X.733)
					  invalid(0),
					  aIS(1),
					  callSetUpFailure(2),
					  degradedSignal(3),
					  farEndReceiverFailure(4),
					  framingError(5),
					  lossOfFrame(6),
					  lossOfPointer(7),
					  lossOfSignal(8),
					  payloadTypeMismatch(9),
					  transmissionError(10),
					  remoteAlarmInterface(11),
					  excessiveBER(12),
					  pathTraceMismatch(13),
					  backplaneFailure(51),
					  dataSetProblem(52),
					  equipmentIdentifierDuplication(53),
					  externalIFDeviceProblem(54),
					  lineCardProblem(55),
					  multiplexerProblem(56),
					  nEIdentifierDuplication(57),
					  powerProblem(58),
					  processorProblem(59),
					  protectionPathFailure(60),
					  receiverFailure(61),
					  replaceableUnitMissing(62),
					  replaceableUnitTypeMismatch(63),
					  synchronizationSourceMismatch(64),
					  terminalProblem(65),
					  timingProblem(66),
					  transmitterFailure(67),
					  trunkCardProblem(68),
					  replaceableUnitProblem(69),
					  airCompressorFailure(101),
					  airConditioningFailure(102),
					  airDryerFailure(103),
					  batteryDischarging(104),
					  batteryFailure(105),
					  commercialPowerFailure(106),
					  coolingFanFailure(107),
					  engineFailure(108),
					  fireDetectorFailure(109),
					  fuseFailure(110),
					  generatorFailure(111),
					  lowBatteryThreshold(112),
					  pumpFailure(113),
					  rectifierFailure(114),
					  rectifierHighVoltage(115),
					  rectifierLowFVoltage(116),
					  ventilationsSystemFailure(117),
					  enclosureDoorOpen(118),
					  explosiveGas(119),
					  fire(120),
					  flood(121),
					  highHumidity(122),
					  highTemperature(123),
					  highWind(124),
					  iceBuildUp(125),
					  intrusionDetection(126),
					  lowFuel(127),
					  lowHumidity(128),
					  lowCablePressure(129),
					  lowTemperature(130),
					  lowWater(131),
					  smoke(132),
					  toxicGas(133),
					  storageCapacityProblem(151),
					  memoryMismatch(152),
					  corruptData(153),
					  outOfCPUCycles(154),
					  sfwrEnvironmentProblem(155),
					  sfwrDownloadFailure(156),
					  communicationsProtocolError(157),
					  congestion(158),
					  heatingOrVentilationOrCoolingSystemProblem(159),
					  lANError(160),
					  performanceDegraded(161),
					  temperatureUnacceptable(162),
					  thresholdCrossed(163),
					  underlyingResourceUnavailable(164),
					  equipmentMalfunction(165),
					  configurationOrCustomizationError(166),
					  duplicateInformation(501),
					  informationMissing(502),
					  informationModificationDetected(503),
					  informationOutOfSequence(504),
					  unexpectedInformation(505),
					  denialOfService(506),
					  outOfService(507),
					  proceduralError(508),
					  cableTamper(509),
					  securityIntrusionDetection(510),
					  authenticationFailure(511),
					  breachOfConfidentiality(512),
					  unauthorisedAccessAttempt(513),
					  delayedInformation(514),
					  keyExpired(515),
					  outOfHoursActivity(516),
					  otherReasons(517),
					  bossHardwareFailure(518),
					  bossSystemSoftwareFailure(519),
					  bossApplicationSoftwareFailure(520),
					  bossDatabaseFailure(521),
					  bossNetworkFailure(522)"
		SYNTAX		INTEGER (0..522)

	OffOn01Value	::= TEXTUAL-CONVENTION
		STATUS		current
		DESCRIPTION	"Alarm Off/On Type
					  invalid(0),
					  off(1),
					  on(2)"
		SYNTAX		INTEGER (0..2)

	NormalAlarm01Value	::= TEXTUAL-CONVENTION
		STATUS		current
		DESCRIPTION	"Normal/Alarm Type
					  invalid(0),
					  normal(1),
					  alarm(2)"
		SYNTAX		INTEGER (0..2)

	NormalRcvd01Value	::= TEXTUAL-CONVENTION
		STATUS		current
		DESCRIPTION	"Normal/Rcvd Type
					  invalid(0),
					  normal(1),
					  received(2)"
		SYNTAX		INTEGER (0..2)

	NormalGen01Value	::= TEXTUAL-CONVENTION
		STATUS		current
		DESCRIPTION	"Normal/Generated Type
					  invalid(0),
					  normal(1),
					  generated(2)"
		SYNTAX		INTEGER (0..2)

	DeactiveActive01Value	::= TEXTUAL-CONVENTION
		STATUS		current
		DESCRIPTION	"EVENT OFF/EVENT ON Type
					  invalid(0),
					  EVENT OFF-OPEN LOOP(1),
					  EVENT ON-CLOSE LOOP(2)"
		SYNTAX		INTEGER (0..2)

	SwitchCtrlValue	::= TEXTUAL-CONVENTION
		STATUS		current
		DESCRIPTION	"SwitchCtrl Type
					  invalid(0),
					  auto(1),
					  no_1(2),
					  no_2(3)"
		SYNTAX		INTEGER (0..3)

	SwitchModeValue	::= TEXTUAL-CONVENTION
		STATUS		current
		DESCRIPTION	"SwitchModeType
					  invalid(0),
					  auto(1),
					  manual(2)"
		SYNTAX		INTEGER (0..2)

	SwitchStatusValue	::= TEXTUAL-CONVENTION
		STATUS		current
		DESCRIPTION	"SwitchStatus Type
					  invalid(0),
					  no_1(1),
					  no_2(2)"
		SYNTAX		INTEGER (0..2)

-----------------------------------------------
-- enterprises Group Definitions
-----------------------------------------------
	
	pasolinkPlusMx OBJECT IDENTIFIER
		::= { pnms 111 }

        pasolinkPlusMxSystem OBJECT IDENTIFIER
		::= { pasolinkPlusMx 1 }

	    pasolinkPlusMxInformation OBJECT IDENTIFIER
		::= { pasolinkPlusMx 2 }


-----------------------------------------------
-- system2 Group Definitions
-----------------------------------------------

	ppMxSystem OBJECT IDENTIFIER
		::= { pasolinkPlusMxSystem 1 }

	ppMxConfiguration OBJECT IDENTIFIER
		::= { pasolinkPlusMxSystem 2 }

	ppMxSys2Trap OBJECT IDENTIFIER
		::= { pasolinkPlusMxSystem 3 }
          
          
-----------------------------------------------
-- pasolinkPlusMx Group Definitions
-----------------------------------------------

	ppMxSummaryInfo OBJECT IDENTIFIER
		::= { pasolinkPlusMxInformation 1 }

	ppMxTrapInfo OBJECT IDENTIFIER
		::= { pasolinkPlusMxInformation 2 }

	ppMxAlarmStatusInfo OBJECT IDENTIFIER
		::= { pasolinkPlusMxInformation 3 }

	ppMxEquipmentConfigInfo OBJECT IDENTIFIER
		::= { pasolinkPlusMxInformation 4 }

	ppMxProvisioningInfo OBJECT IDENTIFIER
		::= { pasolinkPlusMxInformation 5 }

	ppMxInventoryInfo OBJECT IDENTIFIER
		::= { pasolinkPlusMxInformation 6 }

	ppMxMeteringInfo OBJECT IDENTIFIER
		::= { pasolinkPlusMxInformation 7 }

	ppMxPmonInfo OBJECT IDENTIFIER
		::= { pasolinkPlusMxInformation 8 }

	ppMxAuxIOInfo OBJECT IDENTIFIER
		::= { pasolinkPlusMxInformation 9 }

    ppMxGetMeasurementData OBJECT IDENTIFIER
		::= { pasolinkPlusMxInformation 10 }
		
-----------------------------------------------
-- ppSystem Group Definitions
-----------------------------------------------

	ppMxSysSystemInfo OBJECT IDENTIFIER
		::= { ppMxSystem 1 }

	ppMxSystemEquipmentConfigTable OBJECT-TYPE
		SYNTAX		SEQUENCE OF PpMxSystemEquipmentConfigEntry
		ACCESS		not-accessible
		STATUS		mandatory
		DESCRIPTION	"Equipment Config"
		::= { ppMxSysSystemInfo 1 }

	ppMxSystemEquipmentConfigEntry OBJECT-TYPE
		SYNTAX		PpMxSystemEquipmentConfigEntry
		ACCESS		not-accessible
		STATUS		mandatory
		DESCRIPTION	"Equipment Config Entry"
		INDEX		{
					ppMxSysPasoIndex
					}
		::= { ppMxSystemEquipmentConfigTable 1 }

	PpMxSystemEquipmentConfigEntry ::= SEQUENCE {
		ppMxSysPasoIndex		IpAddress,
		ppMxSysEquipmentConfig        INTEGER
	}

	ppMxSysPasoIndex OBJECT-TYPE
		SYNTAX		IpAddress 
		ACCESS		read-only
		STATUS		mandatory
		DESCRIPTION	"Pasolink IP Address index"
		::= { ppMxSystemEquipmentConfigEntry 1 }

	ppMxSysEquipmentConfig OBJECT-TYPE
		SYNTAX		INTEGER (0..8)
		ACCESS		read-only
		STATUS		mandatory
		DESCRIPTION	"Equipment Config
					0:INVALID
					1:1+0
					2:1+1
					3:1+1 HS
					4:1+1 TP
					5:1+0(expandable)
					7:1+0(4*2M)
					8:1+0(20*2M)"
		::= { ppMxSystemEquipmentConfigEntry 2 }     
		

-----------------------------------------------
-- ppConfiguration Group Definitions
-----------------------------------------------

-----------------------------------------------
-- Mx AUX Config Input Table
-----------------------------------------------

	ppMxCfgAux OBJECT IDENTIFIER
		::= { ppMxConfiguration 1 }

	ppMxCfgAuxInTable OBJECT-TYPE
		SYNTAX		SEQUENCE OF PpMxCfgAuxInEntry
		ACCESS		not-accessible
		STATUS		mandatory
		DESCRIPTION	"Optical coupler setting table"
		::= { ppMxCfgAux 1 }

	ppMxCfgAuxInEntry OBJECT-TYPE
		SYNTAX		PpMxCfgAuxInEntry
		ACCESS		not-accessible
		STATUS		mandatory
		DESCRIPTION	"Optical coupler setting table entry"
		INDEX		{
						ppMxCfgAuxInPasoIndex,
						ppMxCfgAuxInIndex
					}
		::= { ppMxCfgAuxInTable 1 }

	PpMxCfgAuxInEntry ::= SEQUENCE {
					  ppMxCfgAuxInPasoIndex      IpAddress,
					  ppMxCfgAuxInIndex          INTEGER,
					  ppMxCfgAuxInItemName       DisplayString,
					  ppMxCfgAuxInItemType       INTEGER,
					  ppMxCfgAuxInOpenState      DisplayString,
					  ppMxCfgAuxInCloseState     DisplayString,
					  ppMxCfgAuxInSeverity       SeverityValue,
					  ppMxCfgAuxInAlarmType      AlarmTypeValue,
					  ppMxCfgAuxInProbableCause  ProbableCauseValue
					}
					
	ppMxCfgAuxInPasoIndex OBJECT-TYPE
		SYNTAX		IpAddress 
		ACCESS		read-only
		STATUS		mandatory
		DESCRIPTION	"Pasolink IP Address index"
		::= { ppMxCfgAuxInEntry 1 }

	ppMxCfgAuxInIndex OBJECT-TYPE
		SYNTAX		INTEGER
		ACCESS		read-only
		STATUS		mandatory
		DESCRIPTION "Aux Input Index
				  No.1-6"
		::= { ppMxCfgAuxInEntry 2 }

	ppMxCfgAuxInItemName OBJECT-TYPE
		SYNTAX		DisplayString
		ACCESS		read-only
		STATUS		mandatory
		DESCRIPTION	"Aux Input Item Name
		                 TRAP=configTrapPpSys2AuxInItemName"
		::= { ppMxCfgAuxInEntry 3 }

	ppMxCfgAuxInItemType OBJECT-TYPE
		SYNTAX		INTEGER (0..3)
		ACCESS		read-only
		STATUS		mandatory
		DESCRIPTION	"Aux Input Item Type
			         INVALID(0),
			         ALARM WHEN EVENT OFF-OPEN LOOP(1),
			         ALARM WHEN EVENT ON-CLOSE LOOP(2),
			         STATUS(3)
			         TRAP=configTrapPpSys2AuxInItemType"
		::= { ppMxCfgAuxInEntry 4 }

	ppMxCfgAuxInOpenState OBJECT-TYPE
		SYNTAX		DisplayString
		ACCESS		read-only
		STATUS		mandatory
		DESCRIPTION	"Aux Input OpenState
		                 TRAP=configTrapPpSys2AuxInOpenState"
		::= { ppMxCfgAuxInEntry 5 }

	ppMxCfgAuxInCloseState OBJECT-TYPE
		SYNTAX		DisplayString
		ACCESS		read-only
		STATUS		mandatory
		DESCRIPTION	"Aux Input CloseState
			         TRAP=configTrapPpSys2AuxInCloseState"
		::= { ppMxCfgAuxInEntry 6 }

	ppMxCfgAuxInSeverity OBJECT-TYPE
		SYNTAX		SeverityValue
		ACCESS		read-only
		STATUS		mandatory
		DESCRIPTION	"Aux Input Severity Type
				 INVALID(0), CLEAR(1), MINOR(2), MAJOR(3), CRITICAL(4)
			         TRAP=configTrapPpSys2AuxInSeverity"
		::= { ppMxCfgAuxInEntry 7 }

	ppMxCfgAuxInAlarmType OBJECT-TYPE
		SYNTAX		AlarmTypeValue
		ACCESS		read-only
		STATUS		mandatory
		DESCRIPTION	"Aux Input AlarmType
				Refer to AlarmTypeValue of TEXTUAL-CONVENTION
				TRAP=configTrapPpSys2AuxInAlarmType"
		::= { ppMxCfgAuxInEntry 8 }

	ppMxCfgAuxInProbableCause OBJECT-TYPE
		SYNTAX		ProbableCauseValue
		ACCESS		read-only
		STATUS		mandatory
		DESCRIPTION	"Aux Input ProbableCause
				Refer to ProbableCauseValue of TEXTUAL-CONVENTION
				TRAP=configTrapPpSys2AuxInProbableCause"
		::= { ppMxCfgAuxInEntry 9 }


-----------------------------------------------
-- Mx AUX Config Output Table
-----------------------------------------------

	ppMxCfgAuxOutTable OBJECT-TYPE
		SYNTAX		SEQUENCE OF PpMxCfgAuxOutEntry
		ACCESS		not-accessible
		STATUS		mandatory
		DESCRIPTION	"Out setting table"
		::= { ppMxCfgAux 2 }

	ppMxCfgAuxOutEntry OBJECT-TYPE
		SYNTAX		PpMxCfgAuxOutEntry
		ACCESS		not-accessible
		STATUS		mandatory
		DESCRIPTION	"Out setting table entry"
		INDEX		{
						ppMxCfgAuxOutPasoIndex,
						ppMxCfgAuxOutIndex
					}
		::= { ppMxCfgAuxOutTable 1 }

	PpMxCfgAuxOutEntry ::= SEQUENCE {
					  ppMxCfgAuxOutPasoIndex   IpAddress,
					  ppMxCfgAuxOutIndex       INTEGER,
					  ppMxCfgAuxOutItemName    DisplayString,
					  ppMxCfgAuxOutOpenState   DisplayString,
					  ppMxCfgAuxOutCloseState  DisplayString
					}

	ppMxCfgAuxOutPasoIndex OBJECT-TYPE
		SYNTAX		IpAddress 
		ACCESS		read-only
		STATUS		mandatory
		DESCRIPTION	"Pasolink IP Address index"
		::= { ppMxCfgAuxOutEntry 1 }

	ppMxCfgAuxOutIndex OBJECT-TYPE
		SYNTAX		INTEGER
		ACCESS		read-only
		STATUS		mandatory
		DESCRIPTION	"Aux Output index
				No.1-4"
		::= { ppMxCfgAuxOutEntry 2 }

	ppMxCfgAuxOutItemName OBJECT-TYPE
		SYNTAX		DisplayString
		ACCESS		read-only
		STATUS		mandatory
		DESCRIPTION	"Aux Output Item name
		                 TRAP=configTrapPpSys2AuxOutItemName"
		::= { ppMxCfgAuxOutEntry 3 }

	ppMxCfgAuxOutOpenState OBJECT-TYPE
		SYNTAX		DisplayString
		ACCESS		read-only
		STATUS		mandatory
		DESCRIPTION	"Aux Output OpenState
				TRAP=configTrapPpSys2AuxOutOpenState"
		::= { ppMxCfgAuxOutEntry 4 }

	ppMxCfgAuxOutCloseState OBJECT-TYPE
		SYNTAX		DisplayString
		ACCESS		read-only
		STATUS		mandatory
		DESCRIPTION	"Aux Output CloseState
		                TRAP=configTrapPpSys2AuxOutCloseState"
		::= { ppMxCfgAuxOutEntry 5 }

-----------------------------------------------
-- ppSys2Trap Group Definitions
-----------------------------------------------

	ppSys2TrapCommon OBJECT IDENTIFIER
		::= { ppMxSys2Trap 1 }

	ppSys2TrapGenericVars OBJECT IDENTIFIER
		::= { ppSys2TrapCommon 1 }

	sys2TrapSequenceNumber OBJECT-TYPE
		SYNTAX		Counter
		ACCESS		read-only
		STATUS		mandatory
		DESCRIPTION	"Trap Sequence Number(0..4294967295)"
		::= { ppSys2TrapGenericVars 1 }

	sys2TrapDate OBJECT-TYPE
		SYNTAX		DisplayString
		ACCESS		read-only
		STATUS		mandatory
		DESCRIPTION	"TrapDate (YYYY/MM/DD)"
		::= { ppSys2TrapGenericVars 2 }

	sys2TrapTime OBJECT-TYPE
		SYNTAX		DisplayString
		ACCESS		read-only
		STATUS		mandatory
		DESCRIPTION	"TrapTime (HH:MM:SS)"
		::= { ppSys2TrapGenericVars 3 }

	sys2TrapSource OBJECT-TYPE
		SYNTAX		OBJECT IDENTIFIER
		ACCESS		read-only
		STATUS		mandatory
		DESCRIPTION	"TrapSource"
		::= { ppSys2TrapGenericVars 4 }

	ppSys2TrapItemVar OBJECT IDENTIFIER
		::= { ppMxSys2Trap 2 }

	ppSys2ConfigTrapItemVar OBJECT IDENTIFIER
		::= { ppSys2TrapItemVar 1 }

	configItemPpSys2AuxInItemName OBJECT-TYPE
		SYNTAX		DisplayString
		ACCESS		read-only
		STATUS		mandatory
		DESCRIPTION	"Aux Input Item Name"
		::= { ppSys2ConfigTrapItemVar 1 }

	configItemPpSys2AuxInItemType OBJECT-TYPE
		SYNTAX		INTEGER(0..3)
		ACCESS		read-only
		STATUS		mandatory
		DESCRIPTION	"Aux Input Type
				  INVALID(0),
				  ALARM WHEN EVENT OFF-OPEN LOOP(1),
				  ALARM WHEN EVENT ON-CLOSE LOOP(2),
				  STATUS(3)"
		::= { ppSys2ConfigTrapItemVar 2 }

	configItemPpSys2AuxInOpenState OBJECT-TYPE
		SYNTAX		DisplayString
		ACCESS		read-only
		STATUS		mandatory
		DESCRIPTION	"Aux Input OpenState"
		::= { ppSys2ConfigTrapItemVar 3 }

	configItemPpSys2AuxInCloseState OBJECT-TYPE
		SYNTAX		DisplayString
		ACCESS		read-only
		STATUS		mandatory
		DESCRIPTION	"Aux Input CloseState"
		::= { ppSys2ConfigTrapItemVar 4 }

	configItemPpSys2AuxInSeverity OBJECT-TYPE
		SYNTAX		SeverityValue
		ACCESS		read-only
		STATUS		mandatory
		DESCRIPTION	"Aux Input Severity
				INVALID(0), CLEAR(1), MINOR(2), MAJOR(3), CRITICAL(4)"
		::= { ppSys2ConfigTrapItemVar 5 }

	configItemPpSys2AuxInAlarmType OBJECT-TYPE
		SYNTAX		AlarmTypeValue
		ACCESS		read-only
		STATUS		mandatory
		DESCRIPTION	"Aux Input AlarmType
				Refer to AlarmTypeValue of TEXTUAL-CONVENTION"
		::= { ppSys2ConfigTrapItemVar 6 }

	configItemPpSys2AuxInProbableCause OBJECT-TYPE
		SYNTAX		ProbableCauseValue
		ACCESS		read-only
		STATUS		mandatory
		DESCRIPTION	"Aux Input ProbableCause
				Refer to ProbableCauseValue of TEXTUAL-CONVENTION"
		::= { ppSys2ConfigTrapItemVar 7 }

	configItemPpSys2AuxOutItemName OBJECT-TYPE
		SYNTAX		DisplayString
		ACCESS		read-only
		STATUS		mandatory
		DESCRIPTION	"Aux Out Item Name"
		::= { ppSys2ConfigTrapItemVar 8 }

	configItemPpSys2AuxOutOpenState OBJECT-TYPE
		SYNTAX		DisplayString
		ACCESS		read-only
		STATUS		mandatory
		DESCRIPTION	"Aux Output OpenState"
		::= { ppSys2ConfigTrapItemVar 9 }

	configItemPpSys2AuxOutCloseState OBJECT-TYPE
		SYNTAX		DisplayString
		ACCESS		read-only
		STATUS		mandatory
		DESCRIPTION	"Aux Outout CloseState"
		::= { ppSys2ConfigTrapItemVar 10 }

-----------------------------------------------
-- Mx Config Trap definitions
-----------------------------------------------

	configTrapPpSys2AuxInItemName	TRAP-TYPE
		ENTERPRISE	pasolinkPlusMx
		VARIABLES	{
					  sys2TrapSequenceNumber,
					  sys2TrapDate,
					  sys2TrapTime,
					  sys2TrapSource,
					  configItemPpSys2AuxInItemName
					}
		::= 404

	configTrapPpSys2AuxInItemType	TRAP-TYPE
		ENTERPRISE	pasolinkPlusMx
		VARIABLES	{
					  sys2TrapSequenceNumber,
					  sys2TrapDate,
					  sys2TrapTime,
					  sys2TrapSource,
					  configItemPpSys2AuxInItemType
					}
		::= 405

	configTrapPpSys2AuxInOpenState	TRAP-TYPE
		ENTERPRISE	pasolinkPlusMx
		VARIABLES	{
					  sys2TrapSequenceNumber,
					  sys2TrapDate,
					  sys2TrapTime,
					  sys2TrapSource,
					  configItemPpSys2AuxInOpenState
					}
		::= 406

	configTrapPpSys2AuxInCloseState	TRAP-TYPE
		ENTERPRISE	pasolinkPlusMx
		VARIABLES	{
					  sys2TrapSequenceNumber,
					  sys2TrapDate,
					  sys2TrapTime,
					  sys2TrapSource,
					  configItemPpSys2AuxInCloseState
					}
		::= 407

	configTrapPpSys2AuxInSeverity	TRAP-TYPE
		ENTERPRISE	pasolinkPlusMx
		VARIABLES	{
					  sys2TrapSequenceNumber,
					  sys2TrapDate,
					  sys2TrapTime,
					  sys2TrapSource,
					  configItemPpSys2AuxInSeverity
					}
		::= 408

	configTrapPpSys2AuxInAlarmType	TRAP-TYPE
		ENTERPRISE	pasolinkPlusMx
		VARIABLES	{
					  sys2TrapSequenceNumber,
					  sys2TrapDate,
					  sys2TrapTime,
					  sys2TrapSource,
					  configItemPpSys2AuxInAlarmType
					}
		::= 409

	configTrapPpSys2AuxInProbableCause	TRAP-TYPE
		ENTERPRISE	pasolinkPlusMx
		VARIABLES	{
					  sys2TrapSequenceNumber,
					  sys2TrapDate,
					  sys2TrapTime,
					  sys2TrapSource,
					  configItemPpSys2AuxInProbableCause
					}
		::= 410

	configTrapPpSys2AuxOutItemName	TRAP-TYPE
		ENTERPRISE	pasolinkPlusMx
		VARIABLES	{
					  sys2TrapSequenceNumber,
					  sys2TrapDate,
					  sys2TrapTime,
					  sys2TrapSource,
					  configItemPpSys2AuxOutItemName
					}
		::= 411

	configTrapPpSys2AuxOutOpenState	TRAP-TYPE
		ENTERPRISE	pasolinkPlusMx
		VARIABLES	{
					  sys2TrapSequenceNumber,
					  sys2TrapDate,
					  sys2TrapTime,
					  sys2TrapSource,
					  configItemPpSys2AuxOutOpenState
					}
		::= 412

	configTrapPpSys2AuxOutCloseState	TRAP-TYPE
		ENTERPRISE	pasolinkPlusMx
		VARIABLES	{
					  sys2TrapSequenceNumber,
					  sys2TrapDate,
					  sys2TrapTime,
					  sys2TrapSource,
					  configItemPpSys2AuxOutCloseState
					}
		::= 413

-----------------------------------------------
-- ppMxSummaryInfo Group Definitions
-----------------------------------------------

-----------------------------------------------
-- Mx Summary Status Table
-----------------------------------------------

	ppMxSummaryItem OBJECT IDENTIFIER
		::= { ppMxSummaryInfo 1 }
		
	ppMxSummaryItemTable OBJECT-TYPE
		SYNTAX		SEQUENCE OF PpMxSummaryItemEntry
		ACCESS		not-accessible
		STATUS		optional
		DESCRIPTION	"Summary Item Table"
		::= { ppMxSummaryItem 1 }

	ppMxSummaryItemEntry OBJECT-TYPE
		SYNTAX		PpMxSummaryItemEntry
		ACCESS		not-accessible
		STATUS		optional
		DESCRIPTION	"Summary Item Table Entry"
		INDEX		{
					ppMxSummaryItemPasoIndex	
					}
		::= { ppMxSummaryItemTable 1 }

	PpMxSummaryItemEntry ::= SEQUENCE {
					  ppMxSummaryItemPasoIndex 	 IpAddress,
					  ppMxPmcSummary               SeverityValue,
					  ppMxAuxSummary               SeverityValue,
					  ppMxLpmSummary               SeverityValue
					 }					  
					         
	ppMxSummaryItemPasoIndex OBJECT-TYPE
		SYNTAX		IpAddress 
		ACCESS		read-only
		STATUS		mandatory
		DESCRIPTION	"Pasolink IP Address Index"
		::= { ppMxSummaryItemEntry 1 }

	ppMxPmcSummary OBJECT-TYPE
		SYNTAX		SeverityValue
		ACCESS		read-only
		STATUS		mandatory
		DESCRIPTION	"PMC Summary
				INVALID(0), CLEAR(1), MINOR(2), MAJOR(3), CRITICAL(4)
				TRAP=ppMxPartialSummaryTrapPmc"
		::= { ppMxSummaryItemEntry 2 }

	ppMxAuxSummary OBJECT-TYPE
		SYNTAX		SeverityValue
		ACCESS		read-only
		STATUS		mandatory
		DESCRIPTION	"AUX. Summary
				INVALID(0), CLEAR(1), MINOR(2), MAJOR(3), CRITICAL(4)
				TRAP=ppMxPartialSummaryTrapAux"
		::= { ppMxSummaryItemEntry 3 }

	ppMxLpmSummary OBJECT-TYPE
		SYNTAX		SeverityValue
		ACCESS		read-only
		STATUS		mandatory
		DESCRIPTION	"LPM Summary
				INVALID(0), CLEAR(1), MINOR(2), MAJOR(3), CRITICAL(4)
				TRAP=ppMxPartialSummaryTrapLpm"
		::= { ppMxSummaryItemEntry 4 }

	ppMxSummaryTable OBJECT-TYPE
		SYNTAX		SEQUENCE OF PpMxSummaryEntry
		ACCESS		not-accessible
		STATUS		mandatory
		DESCRIPTION	"Mx Summary Table"
		::= { ppMxSummaryInfo 2 }

	ppMxSummaryEntry OBJECT-TYPE
		SYNTAX		PpMxSummaryEntry
		ACCESS		not-accessible
		STATUS		mandatory
		DESCRIPTION	"Mx Summary Table Entry"
		INDEX		{
						ppMxSummaryPasoIndex,
						ppMxSummaryIndex
					}
		::= { ppMxSummaryTable 1 }

	PpMxSummaryEntry ::= SEQUENCE {
					  ppMxSummaryPasoIndex  IpAddress, 
					  ppMxSummaryIndex      INTEGER,
					  ppMxOduSummary        SeverityValue,
					  ppMxIduSummary        SeverityValue
					}

	ppMxSummaryPasoIndex OBJECT-TYPE
		SYNTAX		IpAddress 
		ACCESS		read-only
		STATUS		mandatory
		DESCRIPTION	"Pasolink IP Address Index"
		::= { ppMxSummaryEntry 1 }

	ppMxSummaryIndex OBJECT-TYPE
		SYNTAX		INTEGER
		ACCESS		read-only
		STATUS		mandatory
		DESCRIPTION	"Mx Summary Index
				No.1(1), No.2(2)"
		::= { ppMxSummaryEntry 2 }

	ppMxOduSummary OBJECT-TYPE
		SYNTAX		SeverityValue
		ACCESS		read-only
		STATUS		mandatory
		DESCRIPTION	"ODU Summary
				INVALID(0), CLEAR(1), MINOR(2), MAJOR(3), CRITICAL(4)
				TRAP=ppMxPartialSummaryTrapOdu"
		::= { ppMxSummaryEntry 3 }

	ppMxIduSummary OBJECT-TYPE
		SYNTAX		SeverityValue
		ACCESS		read-only
		STATUS		mandatory
		DESCRIPTION	"IDU Summary
				INVALID(0), CLEAR(1), MINOR(2), MAJOR(3), CRITICAL(4)
				TRAP=ppMxPartialSummaryTrapIdu"
		::= { ppMxSummaryEntry 4 }

-----------------------------------------------
-- ppMxTrapInfo Group Definitions
-----------------------------------------------

-----------------------------------------------
-- ppMxTrap Common Group Definitions
-----------------------------------------------
	ppMxTrapCommon OBJECT IDENTIFIER
		::= { ppMxTrapInfo 1 }

	ppMxTrapGenericVars OBJECT IDENTIFIER
		::= { ppMxTrapCommon 1 }

	trapSequenceNumber OBJECT-TYPE
		SYNTAX		Counter
		ACCESS		read-only
		STATUS		mandatory
		DESCRIPTION	"Trap Sequence Number(0..4294967295)"
		::= { ppMxTrapGenericVars 1 }

	trapDate OBJECT-TYPE
		SYNTAX		DisplayString
		ACCESS		read-only
		STATUS		mandatory
		DESCRIPTION	"Trap Date (YYYY/MM/DD)"
		::= { ppMxTrapGenericVars 2 }

	trapTime OBJECT-TYPE
		SYNTAX		DisplayString
		ACCESS		read-only
		STATUS		mandatory
		DESCRIPTION	"Trap Time (HH:MM:SS)"
		::= { ppMxTrapGenericVars 3 }

	trapSource OBJECT-TYPE
		SYNTAX		OBJECT IDENTIFIER
		ACCESS		read-only
		STATUS		mandatory
		DESCRIPTION	"Trap Source"
		::= { ppMxTrapGenericVars 4 }

	ppMxTrapX733Vars OBJECT IDENTIFIER
		::= { ppMxTrapCommon 2 }

	severity OBJECT-TYPE
		SYNTAX		SeverityValue
		ACCESS		read-only
		STATUS		mandatory
		DESCRIPTION	"Severity (CCITT Rec. X.733)
				INVALID(0), CLEAR(1), MINOR(2), MAJOR(3), CRITICAL(4)"
		::= { ppMxTrapX733Vars 1 }

	alarmType OBJECT-TYPE
		SYNTAX		AlarmTypeValue
		ACCESS		read-only
		STATUS		mandatory
		DESCRIPTION	"Alarm Type (CCITT Rec. X.733)
				Refer to AlarmTypeValue of TEXTUAL-CONVENTION"
		::= { ppMxTrapX733Vars 2 }

	probableCause OBJECT-TYPE
		SYNTAX		ProbableCauseValue
		ACCESS		read-only
		STATUS		mandatory
		DESCRIPTION	"Probable Cause (CCITT Rec. X.733)
				Refer to ProbableCauseValue of TEXTUAL-CONVENTION"
		::= { ppMxTrapX733Vars 3 }

	ppMxTrapItemType OBJECT IDENTIFIER
		::= { ppMxTrapInfo 2 }

	ppMxStatusTrapItemType OBJECT IDENTIFIER
		::= { ppMxTrapItemType 1 }
		
	statusTypeAux OBJECT-TYPE
		SYNTAX		INTEGER (0..3)
		ACCESS		read-only
		STATUS		mandatory
		DESCRIPTION	"Status type of AUX.
				INVALID(0),
				ALARM WHEN EVENT OFF-OPEN LOOP(1),
				ALARM WHEN EVENT ON-CLOSE LOOP(2),
				STATUS(3)"
		::= { ppMxStatusTrapItemType 1 }

	statusTypeAis OBJECT-TYPE
		SYNTAX		INTEGER (0..2)
		ACCESS		read-only
		STATUS		mandatory
		DESCRIPTION	"Status type of AIS.
					 0: Invalid
					 1: AlarmType
					 2: StatusType
					"
		::= { ppMxStatusTrapItemType 2 }

-----------------------------------------------
-- Mx Partial Summary Trap Item Var Group Definitions
-----------------------------------------------
	ppMxTrapItemVar OBJECT IDENTIFIER
		::= { ppMxTrapInfo 3 }

	ppMxPartialSummaryTrapItemVar OBJECT IDENTIFIER
		::= { ppMxTrapItemVar 1 }

	ppMxPartialSummaryItemOdu OBJECT-TYPE
		SYNTAX		SeverityValue
		ACCESS		read-only
		STATUS		mandatory
		DESCRIPTION	"Mx Odu Summary
				INVALID(0), CLEAR(1), MINOR(2), MAJOR(3), CRITICAL(4)"
		::= { ppMxPartialSummaryTrapItemVar 1 }

	ppMxPartialSummaryItemIdu OBJECT-TYPE
		SYNTAX		SeverityValue
		ACCESS		read-only
		STATUS		mandatory
		DESCRIPTION	"Mx Idu Summary
				INVALID(0), CLEAR(1), MINOR(2), MAJOR(3), CRITICAL(4)"
		::= { ppMxPartialSummaryTrapItemVar 2 }

	ppMxPartialSummaryItemPmc OBJECT-TYPE
		SYNTAX		SeverityValue
		ACCESS		read-only
		STATUS		mandatory
		DESCRIPTION	"Mx Pmc Summary
				INVALID(0), CLEAR(1), MINOR(2), MAJOR(3), CRITICAL(4)"
		::= { ppMxPartialSummaryTrapItemVar 3 }

	ppMxPartialSummaryItemAux OBJECT-TYPE
		SYNTAX		SeverityValue
		ACCESS		read-only
		STATUS		mandatory
		DESCRIPTION	"Mx Aux Summary
				INVALID(0), CLEAR(1), MINOR(2), MAJOR(3), CRITICAL(4)"
		::= { ppMxPartialSummaryTrapItemVar 4 }

	ppMxPartialSummaryItemLpm OBJECT-TYPE
		SYNTAX		SeverityValue
		ACCESS		read-only
		STATUS		mandatory
		DESCRIPTION	"Mx Lpm Summary
				INVALID(0), CLEAR(1), MINOR(2), MAJOR(3), CRITICAL(4)"
		::= { ppMxPartialSummaryTrapItemVar 5 }

-----------------------------------------------
-- Mx Alarm Trap Item Var Group Definitions
-----------------------------------------------

	ppMxAlarmTrapItemVar OBJECT IDENTIFIER
		::= { ppMxTrapItemVar 2 }

	alarmItemPpMxOduTxInput OBJECT-TYPE
		SYNTAX		NormalAlarm01Value
		ACCESS		read-only
		STATUS		mandatory
		DESCRIPTION	"alarmItemPpMxOduTxInput
					INVALID(0),NORMAL(1),ALARM(2)
					FLAG=SUMMARY_ODU
					severity=major
					alarmType=equipmentAlarm
					probableCause=transmitterFailure"
		::= { ppMxAlarmTrapItemVar 1 }

	alarmItemPpMxOduTxPower OBJECT-TYPE
		SYNTAX		NormalAlarm01Value
		ACCESS		read-only
		STATUS		mandatory
		DESCRIPTION	"alarmItemPpMxOduTxPower
					INVALID(0),NORMAL(1),ALARM(2)
					FLAG=SUMMARY_ODU
					severity=major
					alarmType=equipmentAlarm
					probableCause=transmitterFailure"
		::= { ppMxAlarmTrapItemVar 2 }

	alarmItemPpMxOduRxLevel OBJECT-TYPE
		SYNTAX		NormalAlarm01Value
		ACCESS		read-only
		STATUS		mandatory
		DESCRIPTION	"alarmItemPpMxOduRxLevel
					INVALID(0),NORMAL(1),ALARM(2)
					FLAG=SUMMARY_ODU
					severity=major
					alarmType=communicationAlarm
					probableCause=receiverFailure"
		::= { ppMxAlarmTrapItemVar 3 }

	alarmItemPpMxOduApc OBJECT-TYPE
		SYNTAX		NormalAlarm01Value
		ACCESS		read-only
		STATUS		mandatory
		DESCRIPTION	"alarmItemPpMxOduApc
					INVALID(0),NORMAL(1),ALARM(2)
					FLAG=SUMMARY_ODU
					severity=major
					alarmType=equipmentAlarm
					probableCause=equipmentMalfunction"
		::= { ppMxAlarmTrapItemVar 4 }

	alarmItemPpMxOduCpuAlm OBJECT-TYPE
		SYNTAX		NormalAlarm01Value
		ACCESS		read-only
		STATUS		mandatory
		DESCRIPTION	"alarmItemPpMxOduCpuAlm
					INVALID(0),NORMAL(1),ALARM(2)
					FLAG=SUMMARY_ODU
					severity=major
					alarmType=equipmentAlarm
					probableCause=equipmentMalfunction"
		::= { ppMxAlarmTrapItemVar 5 }

	alarmItemPpMxIduMainBoardAlm OBJECT-TYPE
		SYNTAX		NormalAlarm01Value
		ACCESS		read-only
		STATUS		mandatory
		DESCRIPTION	"alarmItemPpMxIduMainBoardAlm
					INVALID(0),NORMAL(1),ALARM(2)
					FLAG=SUMMARY_IDU
					severity=major
					alarmType=equipmentAlarm
					probableCause=equipmentMalfunction"
		::= { ppMxAlarmTrapItemVar 6 }

	alarmItemPpMxIduInputLoss OBJECT-TYPE
		SYNTAX		NormalAlarm01Value
		ACCESS		read-only
		STATUS		mandatory
		DESCRIPTION	"alarmItemPpMxIduInputLoss
					INVALID(0),NORMAL(1),ALARM(2)
					FLAG=SUMMARY_IDU
					severity=major
					alarmType=communicationAlarm
					probableCause=lossOfSignal"
		::= { ppMxAlarmTrapItemVar 7 }

	alarmItemPpMxIduOutputLoss OBJECT-TYPE
		SYNTAX		NormalAlarm01Value
		ACCESS		read-only
		STATUS		mandatory
		DESCRIPTION	"alarmItemPpMxIduOutputLoss
					INVALID(0),NORMAL(1),ALARM(2)
					FLAG=SUMMARY_IDU
					severity=major
					alarmType=communicationAlarm
					probableCause=lineCardProblem"
		::= { ppMxAlarmTrapItemVar 8 }

	alarmItemPpMxIduModAlm OBJECT-TYPE
		SYNTAX		NormalAlarm01Value
		ACCESS		read-only
		STATUS		mandatory
		DESCRIPTION	"alarmItemPpMxIduModAlm
					INVALID(0),NORMAL(1),ALARM(2)
					FLAG=SUMMARY_IDU
					severity=major
					alarmType=equipmentAlarm
					probableCause=transmitterFailure"
		::= { ppMxAlarmTrapItemVar 9 }

	alarmItemPpMxIduDemAlm OBJECT-TYPE
		SYNTAX		NormalAlarm01Value
		ACCESS		read-only
		STATUS		mandatory
		DESCRIPTION	"alarmItemPpMxIduDemAlm
					INVALID(0),NORMAL(1),ALARM(2)
					FLAG=SUMMARY_IDU
					severity=major
					alarmType=equipmentAlarm
					probableCause=receiverFailure"
		::= { ppMxAlarmTrapItemVar 10 }

	alarmItemPpMxIduIfCableShort OBJECT-TYPE
		SYNTAX		NormalAlarm01Value
		ACCESS		read-only
		STATUS		mandatory
		DESCRIPTION	"alarmItemPpMxIduIfCableShort
					INVALID(0),NORMAL(1),ALARM(2)
					FLAG=SUMMARY_IDU
					severity=major
					alarmType=equipmentAlarm
					probableCause=equipmentMalfunction"
		::= { ppMxAlarmTrapItemVar 11 }

	alarmItemPpMxIduCpuSubAlm OBJECT-TYPE
		SYNTAX		NormalAlarm01Value
		ACCESS		read-only
		STATUS		mandatory
		DESCRIPTION	"alarmItemPpMxIduMdCpuAlm
					INVALID(0),NORMAL(1),ALARM(2)
					FLAG=SUMMARY_PMC
					severity=major
					alarmType=equipmentAlarm
					probableCause=equipmentMalfunction"
		::= { ppMxAlarmTrapItemVar 12 }

	alarmItemPpMxIduLanIntfcMAlm OBJECT-TYPE
		SYNTAX		NormalAlarm01Value
		ACCESS		read-only
		STATUS		mandatory
		DESCRIPTION	"alarmItemPpMxIduLanIntfcMAlm
					INVALID(0),NORMAL(1),ALARM(2)
					FLAG=SUMMARY_IDU
					severity=major
					alarmType=equipmentAlarm
					probableCause=equipmentMalfunction"
		::= { ppMxAlarmTrapItemVar 13 }

	alarmItemPpMxIduLanIntfcSAlm OBJECT-TYPE
		SYNTAX		NormalAlarm01Value
		ACCESS		read-only
		STATUS		mandatory
		DESCRIPTION	"alarmItemPpMxIduLanIntfcSAlm
					INVALID(0),NORMAL(1),ALARM(2)
					FLAG=SUMMARY_IDU
					severity=major
					alarmType=equipmentAlarm
					probableCause=equipmentMalfunction"
		::= { ppMxAlarmTrapItemVar 14 }

	alarmItemPpMxIduModemAlm OBJECT-TYPE
		SYNTAX		NormalAlarm01Value
		ACCESS		read-only
		STATUS		mandatory
		DESCRIPTION	"alarmItemPpMxIduModemAlm
					INVALID(0),NORMAL(1),ALARM(2)
					FLAG=SUMMARY_IDU
					severity=major
					alarmType=equipmentAlarm
					probableCause=equipmentMalfunction"
		::= { ppMxAlarmTrapItemVar 15 }

	alarmItemPpMxIduPsAlm OBJECT-TYPE
		SYNTAX		NormalAlarm01Value
		ACCESS		read-only
		STATUS		mandatory
		DESCRIPTION	"alarmItemPpMxIduPsAlm
					INVALID(0),NORMAL(1),ALARM(2)
					FLAG=SUMMARY_IDU
					severity=major
					alarmType=equipmentAlarm
					probableCause=powerProblem"
		::= { ppMxAlarmTrapItemVar 16 }

	alarmItemPpMxIduLowBerAlm OBJECT-TYPE
		SYNTAX		NormalAlarm01Value
		ACCESS		read-only
		STATUS		mandatory
		DESCRIPTION	"alarmItemPpMxIduLowBerAlm
					INVALID(0),NORMAL(1),ALARM(2)
					FLAG=SUMMARY_IDU
					severity=minor
					alarmType=qualityOfServiceAlarm
					probableCause=degradedSignal"
		::= { ppMxAlarmTrapItemVar 17 }

	alarmItemPpMxIduHighBerAlm OBJECT-TYPE
		SYNTAX		NormalAlarm01Value
		ACCESS		read-only
		STATUS		mandatory
		DESCRIPTION	"alarmItemPpMxIduHighBerAlm
					INVALID(0),NORMAL(1),ALARM(2)
					FLAG=SUMMARY_IDU
					severity=major
					alarmType=qualityOfServiceAlarm
					probableCause=excessiveBER"
		::= { ppMxAlarmTrapItemVar 18 }

	alarmItemPpMxIduLof OBJECT-TYPE
		SYNTAX		NormalAlarm01Value
		ACCESS		read-only
		STATUS		mandatory
		DESCRIPTION	"alarmItemPpMxIduLof
					INVALID(0),NORMAL(1),ALARM(2)
					FLAG=SUMMARY_IDU
					severity=major
					alarmType=qualityOfServiceAlarm
					probableCause=lossOfFrame"
		::= { ppMxAlarmTrapItemVar 19 }

	alarmItemPpMxIduUsageError OBJECT-TYPE
		SYNTAX		NormalAlarm01Value
		ACCESS		read-only
		STATUS		mandatory
		DESCRIPTION	"alarmItemPpMxIduUsageError
					INVALID(0),NORMAL(1),ALARM(2)
					FLAG=SUMMARY_IDU
					severity=minor
					alarmType=operationalViolationAlarm
					probableCause=callSetUpFailure"
		::= { ppMxAlarmTrapItemVar 20 }

	alarmItemPpMxCalendar OBJECT-TYPE
		SYNTAX		NormalAlarm01Value
		ACCESS		read-only
		STATUS		mandatory
		DESCRIPTION	"alarmItemPpMxCalendar
					INVALID(0),NORMAL(1),ALARM(2)
					FLAG=SUMMARY_PMC
					severity=major
					alarmType=equipmentAlarm
					probableCause=equipmentMalfunction"
		::= { ppMxAlarmTrapItemVar 21 }

	alarmItemPpMxIdu4pLanLink OBJECT-TYPE
		SYNTAX		NormalAlarm01Value
		ACCESS		read-only
		STATUS		mandatory
		DESCRIPTION	"alarmItemPpMxIdu4pLanLink
					INVALID(0),NORMAL(1),ALARM(2)
					FLAG=SUMMARY_IDU
					severity=major
					alarmType=communicationAlarm
					probableCause=lossOfSignal"
		::= { ppMxAlarmTrapItemVar 22 }

	alarmItemPpMxIdu2pLanLink OBJECT-TYPE
		SYNTAX		NormalAlarm01Value
		ACCESS		read-only
		STATUS		mandatory
		DESCRIPTION	"alarmItemPpMxIdu2pLanLink
					INVALID(0),NORMAL(1),ALARM(2)
					FLAG=SUMMARY_IDU
					severity=major
					alarmType=communicationAlarm
					probableCause=lossOfSignal"
		::= { ppMxAlarmTrapItemVar 23 }

	alarmItemPpMxTcnDaily OBJECT-TYPE
		SYNTAX		NormalAlarm01Value
		ACCESS		read-only
		STATUS		mandatory
		DESCRIPTION	"alarmItemPpMxTcnDaily
					INVALID(0),NORMAL(1),ALARM(2)
					FLAG=SUMMARY_LPM
					severity=minor
					alarmType=qualityOfServiceAlarm
					probableCause=thresholdCrossed"
		::= { ppMxAlarmTrapItemVar 24 }

	alarmItemPpMxTcnWeekly OBJECT-TYPE
		SYNTAX		NormalAlarm01Value
		ACCESS		read-only
		STATUS		mandatory
		DESCRIPTION	"alarmItemPpMxTcnWeekly
					INVALID(0),NORMAL(1),ALARM(2)
					FLAG=SUMMARY_LPM
					severity=minor
					alarmType=qualityOfServiceAlarm
					probableCause=thresholdCrossed"
		::= { ppMxAlarmTrapItemVar 25 }

	alarmItemPpMxIduTnsCard OBJECT-TYPE
		SYNTAX		NormalAlarm01Value
		ACCESS		read-only
		STATUS		mandatory
		DESCRIPTION	"alarmItemPpMxIduTnsCard
					INVALID(0),NORMAL(1),ALARM(2)
					FLAG=SUMMARY_IDU
					severity=major
					alarmType=equipmentAlarm
					probableCause=equipmentMalfunction"
		::= { ppMxAlarmTrapItemVar 26 }


-----------------------------------------------
-- Mx Event Trap Item Var Group Definitions
-----------------------------------------------

	ppMxEventTrapItemVar OBJECT IDENTIFIER
		::= { ppMxTrapItemVar 3 }

	eventItemPpMxRxSwitchMode OBJECT-TYPE
		SYNTAX		SwitchModeValue
		ACCESS		read-only
		STATUS		mandatory
		DESCRIPTION	"RX Switch Mode 
				0:INVALID, 1:AUTO, 2:MANUAL"
		::= { ppMxEventTrapItemVar 1 }

	eventItemPpMxSelectedRx OBJECT-TYPE
		SYNTAX		SwitchStatusValue
		ACCESS		read-only
		STATUS		mandatory
		DESCRIPTION	"RX Switch Status
				0:INVALID, 1:No.1, 2:No.2"
		::= { ppMxEventTrapItemVar 2 }

	eventItemPpMxTxSwitchMode OBJECT-TYPE
		SYNTAX		SwitchModeValue
		ACCESS		read-only
		STATUS		mandatory
		DESCRIPTION	"TX Switch Mode 
				0:INVALID, 1:AUTO, 2:MANUAL"
		::= { ppMxEventTrapItemVar 3 }

	eventItemPpMxSelectedTx OBJECT-TYPE
		SYNTAX		SwitchStatusValue
		ACCESS		read-only
		STATUS		mandatory
		DESCRIPTION	"TX Switch Status
				0:INVALID, 1:No.1, 2:No.2"
		::= { ppMxEventTrapItemVar 4 }

	eventItemPpMxMainChLB1AllOff OBJECT-TYPE
		SYNTAX		INTEGER(0..1)
		ACCESS		read-only
		STATUS		mandatory
		DESCRIPTION	"CH Loopback-1 all-off Control
				INVALID(0),EXECUTE(1)	"
		::= { ppMxEventTrapItemVar 5 }

	eventItemPpMxMainChLB2AllOff OBJECT-TYPE
		SYNTAX		INTEGER(0..1)
		ACCESS		read-only
		STATUS		mandatory
		DESCRIPTION	"CH Loopback-2 all-off Control
				INVALID(0),EXECUTE(1)"
		::= { ppMxEventTrapItemVar 6 }

	eventItemPpMxMainChLB1 OBJECT-TYPE
		SYNTAX		OffOn01Value
		ACCESS		read-only
		STATUS		mandatory
		DESCRIPTION	"2M CHxx  LOOPBACK-1 Control
					0:INVALID,  1:OFF,  2:ON"
		::= { ppMxEventTrapItemVar 7 }

	eventItemPpMxMainChLB2 OBJECT-TYPE
		SYNTAX		OffOn01Value
		ACCESS		read-only
		STATUS		mandatory
		DESCRIPTION	"2M CHxx  LOOPBACK-2 Control
					0:INVALID,  1:OFF,  2:ON"
		::= { ppMxEventTrapItemVar 8 }

	eventItemPpMxAtpcManual OBJECT-TYPE
		SYNTAX		INTEGER (0..2)
		ACCESS		read-only
		STATUS		mandatory
		DESCRIPTION	"ATPC MANUAL CONTROL 
					0:INVALID, 2:MANUAL, 1:AUTO"
		::= { ppMxEventTrapItemVar 9 }

	eventItemPpMxTxPower OBJECT-TYPE
		SYNTAX		INTEGER
		ACCESS		read-only
		STATUS		mandatory
		DESCRIPTION	"ATPC Manual value"
		::= { ppMxEventTrapItemVar 10 }

	eventItemPpMxTxMute OBJECT-TYPE
		SYNTAX		OffOn01Value
		ACCESS		read-only
		STATUS		mandatory
		DESCRIPTION	"TX MUTE CONTROL  
					0:INVALID, 1:OFF, 2:ON"
		::= { ppMxEventTrapItemVar 11 }

	eventItemPpMxCw OBJECT-TYPE
		SYNTAX		OffOn01Value
		ACCESS		read-only
		STATUS		mandatory
		DESCRIPTION	"Carrier Wave CONTROL 
					0:INVALID, 1:OFF, 2:ON"
		::= { ppMxEventTrapItemVar 12 }

	eventItemPpMxIfLB OBJECT-TYPE
		SYNTAX		OffOn01Value
		ACCESS		read-only
		STATUS		mandatory
		DESCRIPTION	"IF LOOPBACK CONTROL  
					0:INVALID, 1:OFF, 2:ON"
		::= { ppMxEventTrapItemVar 13 }

	eventItemPpMxIdu4PortLanPortReset OBJECT-TYPE
		SYNTAX		INTEGER(0..1)
		ACCESS		read-only
		STATUS		mandatory
		DESCRIPTION	" LAN Interface-Main (4port LAN) Port Reset
				INVALID(0),EXECUTE(1)"
		::= { ppMxEventTrapItemVar 14 }

	eventItemPpMxIdu2PortLanPortReset OBJECT-TYPE
		SYNTAX		INTEGER(0..1)
		ACCESS		read-only
		STATUS		mandatory
		DESCRIPTION	" LAN Interface-Main (2port LAN) Port Reset
				INVALID(0),EXECUTE(1)"
		::= { ppMxEventTrapItemVar 15 }

	eventItemPpMxEquipmentMaint OBJECT-TYPE
		SYNTAX		OffOn01Value
		ACCESS		read-only
		STATUS		mandatory
		DESCRIPTION	"MAINT CONTROL
					0:INVALID, 1:OFF, 2:ON"
		::= { ppMxEventTrapItemVar 16 }

	eventItemPpMxConfigDataInvalid OBJECT-TYPE
		SYNTAX		INTEGER(0..1)
		ACCESS		read-only
		STATUS		mandatory
		DESCRIPTION	"eventItemPpMxConfigDataInvalid
				INVALID(0),VALID(1)"
		::= { ppMxEventTrapItemVar 17 }

	eventItemPpMxConfigDataUp OBJECT-TYPE
		SYNTAX		INTEGER(0..1)
		ACCESS		read-only
		STATUS		mandatory
		DESCRIPTION	"eventItemPpMxConfigDataUp
				INVALID(0),UPDATE(1)"
		::= { ppMxEventTrapItemVar 18 }

	eventItemPpMxIduAisGenerated OBJECT-TYPE
		SYNTAX		INTEGER(0..2)
		ACCESS		read-only
		STATUS		mandatory
		DESCRIPTION	" AIS Genarated status
				INVALID(0),NORMAL(1),GENERATED(2)"
		::= { ppMxEventTrapItemVar 19 }

	eventItemPpMxIdu4pLanCollision OBJECT-TYPE
		SYNTAX		INTEGER(0..2)
		ACCESS		read-only
		STATUS		mandatory
		DESCRIPTION	"4PORT LAN Collision Status
				INVALID(0),NORMAL(1),COLLISION(2)"
		::= { ppMxEventTrapItemVar 20 }

	eventItemPpMxIdu4pLanPortSpeedDuplex OBJECT-TYPE
		SYNTAX		INTEGER(0..8)
		ACCESS		read-only
		STATUS		mandatory
		DESCRIPTION	"4PORT LAN SpeedDuplex
				INVALID(0),10M-HALF(MDI)(1),10M-FULL(MDI)(2),100M-HALF(MDI)(3),100M-FULL(MDI)(4),10M-HALF(MDIX)(5),10M-FULL(MDIX)(6),100M-HALF(MDIX)(7),100M-FULL(MDIX)(8)"
		::= { ppMxEventTrapItemVar 21 }

	eventItemPpMxIdu4pLanLinkLosForwarding OBJECT-TYPE
		SYNTAX		INTEGER(0..2)
		ACCESS		read-only
		STATUS		mandatory
		DESCRIPTION	"4PORT LAN LinkLosForwarding
				INVALID(0),NORMAL(1),UNDER EXECUTION(2)"
		::= { ppMxEventTrapItemVar 22 }

	eventItemPpMxIdu2pLanCollision OBJECT-TYPE
		SYNTAX		INTEGER(0..2)
		ACCESS		read-only
		STATUS		mandatory
		DESCRIPTION	"2PORT LAN Collision Status
				INVALID(0),NORMAL(1),COLLISION(2)"
		::= { ppMxEventTrapItemVar 23 }

	eventItemPpMxIdu2pLanPortSpeedDuplex OBJECT-TYPE
		SYNTAX		INTEGER(0..8)
		ACCESS		read-only
		STATUS		mandatory
		DESCRIPTION	"2PORT LAN SpeedDuplex
				INVALID(0),10M-HALF(MDI)(1),10M-FULL(MDI)(2),100M-HALF(MDI)(3),100M-FULL(MDI)(4),10M-HALF(MDIX)(5),10M-FULL(MDIX)(6),100M-HALF(MDIX)(7),100M-FULL(MDIX)(8)"
		::= { ppMxEventTrapItemVar 24 }

	eventItemPpMxIdu2pLanLinkLosForwarding OBJECT-TYPE
		SYNTAX		INTEGER(0..2)
		ACCESS		read-only
		STATUS		mandatory
		DESCRIPTION	"2PORT LAN LinkLosForwarding
				INVALID(0),NORMAL(1),UNDER EXECUTION(2)"
		::= { ppMxEventTrapItemVar 25 }

	eventItemPpMxTcnDailyOccur OBJECT-TYPE
		SYNTAX		INTEGER
		ACCESS		read-only
		STATUS		mandatory
		DESCRIPTION	"Performance Monitor Threshold  value (15-min., Alarm Occur )"
		::= { ppMxEventTrapItemVar 26 }

	eventItemPpMxTcnDailyRecover OBJECT-TYPE
		SYNTAX		INTEGER
		ACCESS		read-only
		STATUS		mandatory
		DESCRIPTION	"Performance Monitor Threshold  value (15-min., Alarm Recover)"
		::= { ppMxEventTrapItemVar 27 }

	eventItemPpMxTcnWeeklyOccur OBJECT-TYPE
		SYNTAX		INTEGER
		ACCESS		read-only
		STATUS		mandatory
		DESCRIPTION	"Performance Monitor Threshold  value (1-day, Alarm Occur)"
		::= { ppMxEventTrapItemVar 28 }

	eventItemPpMxTcnWeeklyRecover OBJECT-TYPE
		SYNTAX		INTEGER
		ACCESS		read-only
		STATUS		mandatory
		DESCRIPTION	"Performance Monitor Threshold  value (1-day, Alarm Recover)"
		::= { ppMxEventTrapItemVar 29 }

	eventItemPpMxBerThreshold OBJECT-TYPE
		SYNTAX		INTEGER
		ACCESS		read-only
		STATUS		mandatory
		DESCRIPTION	"Ber Threshold"
		::= { ppMxEventTrapItemVar 30 }

	eventItemPpMxAdditionalAtt OBJECT-TYPE
		SYNTAX		INTEGER
		ACCESS		read-only
		STATUS		mandatory
		DESCRIPTION	"additional Attenuation value [dB]"
		::= { ppMxEventTrapItemVar 31 }

	eventItemPpMxAtpcMax OBJECT-TYPE
		SYNTAX		INTEGER
		ACCESS		read-only
		STATUS		mandatory
		DESCRIPTION	"ATPC Maximum value [dB]"
		::= { ppMxEventTrapItemVar 32 }

	eventItemPpMxAtpcMin OBJECT-TYPE
		SYNTAX		INTEGER
		ACCESS		read-only
		STATUS		mandatory
		DESCRIPTION	"ATPC Minimum value [dB]"
		::= { ppMxEventTrapItemVar 33 }

	eventItemPpMxAtpcRxThresholdLevel OBJECT-TYPE
		SYNTAX		INTEGER
		ACCESS		read-only
		STATUS		mandatory
		DESCRIPTION	"ATPC RX Threshold Level Value [dBm]"
		::= { ppMxEventTrapItemVar 34 }

	eventItemPpMxOduAlarmMode OBJECT-TYPE
		SYNTAX		INTEGER(0..4)
		ACCESS		read-only
		STATUS		mandatory
		DESCRIPTION	"ODU alarm mode
				INVALID(0),MUTE(1),MAX(2), MIN(3), HOLD(4)"
		::= { ppMxEventTrapItemVar 36 }

	eventItemPpMxMtpcTxPower OBJECT-TYPE
		SYNTAX		INTEGER
		ACCESS		read-only
		STATUS		mandatory
		DESCRIPTION	"MTPC TX Power value [dB]"
		::= { ppMxEventTrapItemVar 37 }

	eventItemPpMxTxSwPriority OBJECT-TYPE
		SYNTAX		INTEGER(0..2)
		ACCESS		read-only
		STATUS		mandatory
		DESCRIPTION	"TX SW Priority
				INVALID(0),PRIORITY No.1(1),NON-PRIORITY(2)"
		::= { ppMxEventTrapItemVar 38 }

	eventItemPpMxRxSwPriority OBJECT-TYPE
		SYNTAX		INTEGER(0..2)
		ACCESS		read-only
		STATUS		mandatory
		DESCRIPTION	"RX SW Priority
				INVALID(0),PRIORITY No.1(1),NON-PRIORITY(2)"
		::= { ppMxEventTrapItemVar 39 }

	eventItemPpMxAisActivationCondition OBJECT-TYPE
		SYNTAX		INTEGER(0..2)
		ACCESS		read-only
		STATUS		mandatory
		DESCRIPTION	"AIS Activation Condition 
				INVALID(0), LOF+HIGH BER(1), LOF(2)"
		::= { ppMxEventTrapItemVar 41 }

	eventItemPpMxMainChAisReceivedReport OBJECT-TYPE
		SYNTAX		INTEGER(0..2)
		ACCESS		read-only
		STATUS		mandatory
		DESCRIPTION	"AIS Received Report
				INVALID(0),REPORTED(1),NOT REPORTED(2)"
		::= { ppMxEventTrapItemVar 42 }

	eventItemPpMxMainChAisReceivedConditionSetting OBJECT-TYPE
		SYNTAX		INTEGER(0..2)
		ACCESS		read-only
		STATUS		mandatory
		DESCRIPTION	"AIS RECEIVED CONDITION SETTING
				INVALID(0),ALARM(1),STATUS(2)
					FLAG=SUMMARY_IDU"
		::= { ppMxEventTrapItemVar 43 }

	eventItemPpMxMainChAisGeneratedReport OBJECT-TYPE
		SYNTAX		INTEGER(0..2)
		ACCESS		read-only
		STATUS		mandatory
		DESCRIPTION	"AIS GENERATED REPORT
				INVALID(0),REPORTED(1),NOT REPORTED(2)"
		::= { ppMxEventTrapItemVar 44 }

	eventItemPpMxMainChUsage OBJECT-TYPE
		SYNTAX		INTEGER(0..3)
		ACCESS		read-only
		STATUS		mandatory
		DESCRIPTION	"CHANNEL USAGE
				INVALID(0),USED(1),NOT USED(2),LAN RESERVED(3)"
		::= { ppMxEventTrapItemVar 45 }

	eventItemPpMxMainChErrorReport OBJECT-TYPE
		SYNTAX		INTEGER(0..2)
		ACCESS		read-only
		STATUS		mandatory
		DESCRIPTION	"CHANNEL USAGE ERROR REPORT
				INVALID(0),REPORTED(1),NOT REPORTED(2)"
		::= { ppMxEventTrapItemVar 46 }

	eventItemPpMx4pLanPortUsage OBJECT-TYPE
		SYNTAX		INTEGER(0..2)
		ACCESS		read-only
		STATUS		mandatory
		DESCRIPTION	"4PORT LAN Port Usage
				INVALID(0),USED(1),NOT USED(2)"
		::= { ppMxEventTrapItemVar 47 }

	eventItemPpMx4pLanPortSpeedDuplex OBJECT-TYPE
		SYNTAX		INTEGER(0..9)
		ACCESS		read-only
		STATUS		mandatory
		DESCRIPTION	"4PORT LAN SpeedDuplex
				 1:AUTONEG(AUTO-MDI/MDIX)
				 2:10M-HALF(MDI)
				 3:10M-FULL(MDI)
				 4:100M-HALF(MDI)
				 5:100M-FULL(MDI)
				 6:10M-HALF(MDIX)
				 7:10M-FULL(MDIX)
				 8:100M-HALF(MDIX)
				 9:100M-FULL(MDIX)
				 0:INVALID"
		::= { ppMxEventTrapItemVar 48 }

	eventItemPpMx4pLanFlowControl OBJECT-TYPE
		SYNTAX		INTEGER(0..2)
		ACCESS		read-only
		STATUS		mandatory
		DESCRIPTION	"4PORT LAN FlowControl
				INVALID(0),ON(1),OFF(2)"
		::= { ppMxEventTrapItemVar 49 }

	eventItemPpMx4pLanCollisionReport OBJECT-TYPE
		SYNTAX		INTEGER(0..2)
		ACCESS		read-only
		STATUS		mandatory
		DESCRIPTION	"4PORT LAN Collision Report
				INVALID(0),REPORTED(1),NOT REPORTED(2)"
		::= { ppMxEventTrapItemVar 50 }

	eventItemPpMx4pLanLinkLossForwarding OBJECT-TYPE
		SYNTAX		INTEGER(0..2)
		ACCESS		read-only
		STATUS		mandatory
		DESCRIPTION	"4PORT LAN LinkLossForwarding
				INVALID(0),ENAVLED(1),DISAVLED(2)"
		::= { ppMxEventTrapItemVar 51 }

	eventItemPpMx4pLanPortSwitching OBJECT-TYPE
		SYNTAX		INTEGER(0..6)
		ACCESS		read-only
		STATUS		mandatory
		DESCRIPTION	"4PORT LAN Port Switching
				0:INVALID
				1:P1-2=ENABLED,P3-4=ENABLED
				2:P1-2=ENABLED,P3-4=DISABLED
				3:P1-2=DISABLED,P3-4=ENABLED
				4:P1-2=DISABLED,P3-4=DISABLED
				5:P1-4=ENABLED
				6:P1-4=DISABLED"
		::= { ppMxEventTrapItemVar 52 }

	eventItemPpMx2pLanPortUsage OBJECT-TYPE
		SYNTAX		INTEGER(0..2)
		ACCESS		read-only
		STATUS		mandatory
		DESCRIPTION	"2PORT LAN Port Usage
				INVALID(0),USED(1),NOT USED(2)"
		::= { ppMxEventTrapItemVar 53 }

	eventItemPpMx2pLanPortSpeedDuplex OBJECT-TYPE
		SYNTAX		INTEGER(0..9)
		ACCESS		read-only
		STATUS		mandatory
		DESCRIPTION	"2PORT LAN SpeedDuplex
				 1:AUTONEG(AUTO-MDI/MDIX)
				 2:10M-HALF(MDI)
				 3:10M-FULL(MDI)
				 4:100M-HALF(MDI)
				 5:100M-FULL(MDI)
				 6:10M-HALF(MDIX)
				 7:10M-FULL(MDIX)
				 8:100M-HALF(MDIX)
				 9:100M-FULL(MDIX)
				 0:INVALID"
		::= { ppMxEventTrapItemVar 54 }

	eventItemPpMx2pLanFlowControl OBJECT-TYPE
		SYNTAX		INTEGER(0..2)
		ACCESS		read-only
		STATUS		mandatory
		DESCRIPTION	"2PORT LAN FlowControl
				INVALID(0),ON(1),OFF(2)"
		::= { ppMxEventTrapItemVar 55 }

	eventItemPpMx2pLanCollisionReport OBJECT-TYPE
		SYNTAX		INTEGER(0..2)
		ACCESS		read-only
		STATUS		mandatory
		DESCRIPTION	"2PORT LAN Collision Report
				INVALID(0),REPORTED(1),NOT REPORTED(2)"
		::= { ppMxEventTrapItemVar 56 }

	eventItemPpMx2pLanLinkLossForwarding OBJECT-TYPE
		SYNTAX		INTEGER(0..2)
		ACCESS		read-only
		STATUS		mandatory
		DESCRIPTION	"2PORT LAN LinkLossForwarding
				INVALID(0),ENAVLED(1),DISAVLED(2)"
		::= { ppMxEventTrapItemVar 57 }

	eventItemPpMx2pLanPort1or12Lan2MFraming OBJECT-TYPE
		SYNTAX		INTEGER(0..5)
		ACCESS		read-only
		STATUS		mandatory
		DESCRIPTION	"2PORT LAN Port1 2M Framing
				0:INVALID
				1:UNFRAMED
				2:PCM-31C(FAS+CRC)
				3:PCM-31(FAS)
				4:PCM-30C(MFAS+CRC)
				5:PCM-30(MFAS)"
		::= { ppMxEventTrapItemVar 58 }

	eventItemPpMx2pLanPort2Lan2MFraming OBJECT-TYPE
		SYNTAX		INTEGER(0..5)
		ACCESS		read-only
		STATUS		mandatory
		DESCRIPTION	"2PORT LAN Port2 2M Framing
				0:INVALID
				1:UNFRAMED
				2:PCM-31C(FAS+CRC)
				3:PCM-31(FAS)
				4:PCM-30C(MFAS+CRC)
				5:PCM-30(MFAS)"
		::= { ppMxEventTrapItemVar 59 }

	eventItemPpMx2pLanPortSwitching OBJECT-TYPE
		SYNTAX		INTEGER(0..2)
		ACCESS		read-only
		STATUS		mandatory
		DESCRIPTION	"2PORT LAN Port Switching
				0:INVALID
				1:P1-2=ENABLED
				2:P1-2=DISABLED"
		::= { ppMxEventTrapItemVar 60 }

	eventItemPpMxSc1Usage OBJECT-TYPE
		SYNTAX		INTEGER(0..2)
		ACCESS		read-only
		STATUS		mandatory
		DESCRIPTION	"SC1 Usage
				INVALID(0),RS-232C(1),LAN(2)"
		::= { ppMxEventTrapItemVar 61 }

	eventItemPpMxSc2Usage OBJECT-TYPE
		SYNTAX		INTEGER(0..2)
		ACCESS		read-only
		STATUS		mandatory
		DESCRIPTION	"SC2 Usage
				INVALID(0),RS-232C(1),LAN(2)"
		::= { ppMxEventTrapItemVar 62 }

	eventItemPpMxSc3Usage OBJECT-TYPE
		SYNTAX		INTEGER(0..3)
		ACCESS		read-only
		STATUS		mandatory
		DESCRIPTION	"SC3 Usage
				0:INVALID
				1:V.11(CO-DIRECTIONAL)
				2:V.11(CONTRA-DIRECTIONAL)
				3:TNS CARD"
		::= { ppMxEventTrapItemVar 63 }

	eventItemPpMxSc4Usage OBJECT-TYPE
		SYNTAX		INTEGER(0..2)
		ACCESS		read-only
		STATUS		mandatory
		DESCRIPTION	"SC4 Usage
				0:INVALID
				1:V.11(CO-DIRECTIONAL)
				2:V.11(CONTRA-DIRECTIONAL)"
		::= { ppMxEventTrapItemVar 64 }

	eventItemPpMxRelay OBJECT-TYPE
		SYNTAX		OCTET STRING (SIZE (8))
		ACCESS		read-only
		STATUS		mandatory
		DESCRIPTION	"Relay setting bitmap"
		::= { ppMxEventTrapItemVar 65 }

	eventItemPpMxTxFreq OBJECT-TYPE
		SYNTAX		DisplayString
		ACCESS		read-only
		STATUS		mandatory
		DESCRIPTION	"TX Frequency[MHz]"
		::= { ppMxEventTrapItemVar 66 }

	eventItemPpMxRxFreq OBJECT-TYPE
		SYNTAX		DisplayString
		ACCESS		read-only
		STATUS		mandatory
		DESCRIPTION	"RX Frequency[MHz]"
		::= { ppMxEventTrapItemVar 67 }

	eventItemPpMxShiftFreq OBJECT-TYPE
		SYNTAX		DisplayString
		ACCESS		read-only
		STATUS		mandatory
		DESCRIPTION	"Shift Frequency[MHz]"
		::= { ppMxEventTrapItemVar 69 }

	eventItemPpMxSubBand OBJECT-TYPE
		SYNTAX		DisplayString
		ACCESS		read-only
		STATUS		mandatory
		DESCRIPTION	"SubBand"
		::= { ppMxEventTrapItemVar 70 }

	eventItemPpMxInventoryUpdate OBJECT-TYPE
		SYNTAX		INTEGER
		ACCESS		read-only
		STATUS		mandatory
		DESCRIPTION	"eventItemPpMxInventoryUpdate"
		::= { ppMxEventTrapItemVar 71 }

	eventItemPpMxAuxOutput OBJECT-TYPE
		SYNTAX		INTEGER(0..2)
		ACCESS		read-only
		STATUS		mandatory
		DESCRIPTION	"Aux Output Item Value
				INVALID(0),EVENT OFF-OPEN LOOP(1),EVENT ON-CLOSE LOOP(2)"
		::= { ppMxEventTrapItemVar 72 }

	eventItemPpMxInsertedModule OBJECT-TYPE
		SYNTAX		INTEGER(0..13)
		ACCESS		read-only
		STATUS		mandatory
		DESCRIPTION	"Inserted Module
				0:INVALID
				1:2M INTFC-M(32*2M) + BLANK
				2:2M INTFC-M(32*2M) + 2M INTFC-S
				3:2M INTFC-M(32*2M) + LAN INTFC-S
				4:BLANK + LAN INTFC-S
				5:LAN INTFC-M + BLANK
				6:LAN INTFC-M + 2M INTFC-S
				7:LAN INTFC-M + LAN INTFC-S
				8:2M INTFC-M(20*2M) + BLANK
				9:2M INTFC-M(20*2M) + LAN INTFC-S
				10:TNS CARD + BLANK
				11:TNS CARD + LAN INTFC-S
				12:PNMS CARD+ BLANK
				13:PNMS CARD+ LAN INTFC-S"
		::= { ppMxEventTrapItemVar 74 }

	eventItemPpMxModuleDetected OBJECT-TYPE
		SYNTAX		INTEGER(0..2)
		ACCESS		read-only
		STATUS		mandatory
		DESCRIPTION	"Module Detected
				INVALID(0),OFF(1),ON(2)"
		::= { ppMxEventTrapItemVar 75 }

	eventItemPpMxTxMuteReleaseTime OBJECT-TYPE
		SYNTAX		INTEGER
		ACCESS		read-only
		STATUS		mandatory
		DESCRIPTION	"Tx Mute Release Time"
		::= { ppMxEventTrapItemVar 76 }

	eventItemPpMxClusterAlarmUsage OBJECT-TYPE
		SYNTAX		INTEGER(0..2)
		ACCESS		read-only
		STATUS		mandatory
		DESCRIPTION	" Cluster Alarm
				INVALID(0),ENAVLED(1),DISAVLED(2)"
		::= { ppMxEventTrapItemVar 77 }


-----------------------------------------------
-- Mx Status Trap Item Var Group Definitions
-----------------------------------------------

	ppMxStatusTrapItemVar OBJECT IDENTIFIER
		::= { ppMxTrapItemVar 4 }

	statusItemPpMxAuxInput OBJECT-TYPE
		SYNTAX		INTEGER
		ACCESS		read-only
		STATUS		mandatory
		DESCRIPTION	"AUX. Input Item
					0:INVALID, 1:EVENT OFF-OPEN LOOP, 2:EVENT ON-CLOSE LOOP
					FLAG=SUMMARY_AUX
					severity=major
					alarmType=equipmentAlarm
					probableCause=equipmentMalfunction"
		::= { ppMxStatusTrapItemVar 1 }

	statusItemPpMxAisReceived OBJECT-TYPE
		SYNTAX		INTEGER
		ACCESS		read-only
		STATUS		mandatory
		DESCRIPTION	"AIS RECEIVED 
					0:INVALID, 1:NORMAL, 2:RECEIVED
					FLAG=SUMMARY_IDU
					severity=minor
					alarmType=qualityOfServiceAlarm
					probableCause=aIS"
		::= { ppMxStatusTrapItemVar 2 }


-----------------------------------------------
-- Mx System Trap Item Var Group Definitions
-----------------------------------------------

	ppMxSystemTrapItemVar OBJECT IDENTIFIER
		::= { ppMxTrapItemVar 5 }

	systemItemPpMxLocalUpdate OBJECT-TYPE
		SYNTAX		OffOn01Value
		ACCESS		read-only
		STATUS		mandatory
		DESCRIPTION	"systemItemPpMxLocalUpdate
				INVALID(0),OFF(1),ON(2)"
		::= { ppMxSystemTrapItemVar 2 }

	systemItemPpMxGetMeteringRequestID OBJECT-TYPE
			SYNTAX		INTEGER
			ACCESS		read-only
			STATUS		mandatory
			DESCRIPTION	"Request ID"
    	::= { ppMxSystemTrapItemVar  3 }

	systemItemPpMxGetMeteringTargetIpAddress OBJECT-TYPE
			SYNTAX		IpAddress
			ACCESS		read-only
			STATUS		mandatory
			DESCRIPTION	"Pasolink NE IpAddress"
    	::= { ppMxSystemTrapItemVar  4 }
	
	systemItemPpMxGetMeteringResult OBJECT-TYPE
			SYNTAX		INTEGER (0..3)
			ACCESS		read-only
			STATUS		mandatory
			DESCRIPTION	"Request Result
								invalid(0),
								ready(1),
								wait(2),
								fail(3)"
    	::= { ppMxSystemTrapItemVar  5 }
		
	ppMxPartialSummaryTrapOdu	TRAP-TYPE
		ENTERPRISE	pasolinkPlusMx
		VARIABLES	{
					  trapSequenceNumber,
					  trapDate,
					  trapTime,
					  severity,
					  alarmType,
					  probableCause,
					  trapSource,
					  ppMxPartialSummaryItemOdu
					}
		::= 10

	ppMxPartialSummaryTrapIdu	TRAP-TYPE
		ENTERPRISE	pasolinkPlusMx
		VARIABLES	{
					  trapSequenceNumber,
					  trapDate,
					  trapTime,
					  severity,
					  alarmType,
					  probableCause,
					  trapSource,
					  ppMxPartialSummaryItemIdu
					}
		::= 11

	ppMxPartialSummaryTrapPmc	TRAP-TYPE
		ENTERPRISE	pasolinkPlusMx
		VARIABLES	{
					  trapSequenceNumber,
					  trapDate,
					  trapTime,
					  severity,
					  alarmType,
					  probableCause,
					  trapSource,
					  ppMxPartialSummaryItemPmc
					}
		::= 12

	ppMxPartialSummaryTrapAux	TRAP-TYPE
		ENTERPRISE	pasolinkPlusMx
		VARIABLES	{
					  trapSequenceNumber,
					  trapDate,
					  trapTime,
					  severity,
					  alarmType,
					  probableCause,
					  trapSource,
					  ppMxPartialSummaryItemAux
					}
		::= 13

	ppMxPartialSummaryTrapLpm	TRAP-TYPE
		ENTERPRISE	pasolinkPlusMx
		VARIABLES	{
					  trapSequenceNumber,
					  trapDate,
					  trapTime,
					  severity,
					  alarmType,
					  probableCause,
					  trapSource,
					  ppMxPartialSummaryItemLpm
					}
		::= 14

	alarmTrapPpMxOduTxInput	TRAP-TYPE
		ENTERPRISE	pasolinkPlusMx
		VARIABLES	{
					  trapSequenceNumber,
					  trapDate,
					  trapTime,
					  severity,
					  alarmType,
					  probableCause,
					  trapSource,
					  alarmItemPpMxOduTxInput
					}
		::= 101

	alarmTrapPpMxOduTxPower	TRAP-TYPE
		ENTERPRISE	pasolinkPlusMx
		VARIABLES	{
					  trapSequenceNumber,
					  trapDate,
					  trapTime,
					  severity,
					  alarmType,
					  probableCause,
					  trapSource,
					  alarmItemPpMxOduTxPower
					}
		::= 102

	alarmTrapPpMxOduRxLevel	TRAP-TYPE
		ENTERPRISE	pasolinkPlusMx
		VARIABLES	{
					  trapSequenceNumber,
					  trapDate,
					  trapTime,
					  severity,
					  alarmType,
					  probableCause,
					  trapSource,
					  alarmItemPpMxOduRxLevel
					}
		::= 103

	alarmTrapPpMxOduApc	TRAP-TYPE
		ENTERPRISE	pasolinkPlusMx
		VARIABLES	{
					  trapSequenceNumber,
					  trapDate,
					  trapTime,
					  severity,
					  alarmType,
					  probableCause,
					  trapSource,
					  alarmItemPpMxOduApc
					}
		::= 104

	alarmTrapPpMxOduCpuAlm	TRAP-TYPE
		ENTERPRISE	pasolinkPlusMx
		VARIABLES	{
					  trapSequenceNumber,
					  trapDate,
					  trapTime,
					  severity,
					  alarmType,
					  probableCause,
					  trapSource,
					  alarmItemPpMxOduCpuAlm
					}
		::= 105

	alarmTrapPpMxIduMainBoardAlm	TRAP-TYPE
		ENTERPRISE	pasolinkPlusMx
		VARIABLES	{
					  trapSequenceNumber,
					  trapDate,
					  trapTime,
					  severity,
					  alarmType,
					  probableCause,
					  trapSource,
					  alarmItemPpMxIduMainBoardAlm
					}
		::= 106

	alarmTrapPpMxIduInputLoss	TRAP-TYPE
		ENTERPRISE	pasolinkPlusMx
		VARIABLES	{
					  trapSequenceNumber,
					  trapDate,
					  trapTime,
					  severity,
					  alarmType,
					  probableCause,
					  trapSource,
					  alarmItemPpMxIduInputLoss
					}
		::= 107

	alarmTrapPpMxIduOutputLoss	TRAP-TYPE
		ENTERPRISE	pasolinkPlusMx
		VARIABLES	{
					  trapSequenceNumber,
					  trapDate,
					  trapTime,
					  severity,
					  alarmType,
					  probableCause,
					  trapSource,
					  alarmItemPpMxIduOutputLoss
					}
		::= 108

	alarmTrapPpMxIduModAlm	TRAP-TYPE
		ENTERPRISE	pasolinkPlusMx
		VARIABLES	{
					  trapSequenceNumber,
					  trapDate,
					  trapTime,
					  severity,
					  alarmType,
					  probableCause,
					  trapSource,
					  alarmItemPpMxIduModAlm
					}
		::= 109

	alarmTrapPpMxIduDemAlm	TRAP-TYPE
		ENTERPRISE	pasolinkPlusMx
		VARIABLES	{
					  trapSequenceNumber,
					  trapDate,
					  trapTime,
					  severity,
					  alarmType,
					  probableCause,
					  trapSource,
					  alarmItemPpMxIduDemAlm
					}
		::= 110

	alarmTrapPpMxIduIfCableShort	TRAP-TYPE
		ENTERPRISE	pasolinkPlusMx
		VARIABLES	{
					  trapSequenceNumber,
					  trapDate,
					  trapTime,
					  severity,
					  alarmType,
					  probableCause,
					  trapSource,
					  alarmItemPpMxIduIfCableShort
					}
		::= 111

	alarmTrapPpMxIduCpuSubAlm	TRAP-TYPE
		ENTERPRISE	pasolinkPlusMx
		VARIABLES	{
					  trapSequenceNumber,
					  trapDate,
					  trapTime,
					  severity,
					  alarmType,
					  probableCause,
					  trapSource,
					  alarmItemPpMxIduCpuSubAlm
					}
		::= 112

	alarmTrapPpMxIduLanIntfcMAlm	TRAP-TYPE
		ENTERPRISE	pasolinkPlusMx
		VARIABLES	{
					  trapSequenceNumber,
					  trapDate,
					  trapTime,
					  severity,
					  alarmType,
					  probableCause,
					  trapSource,
					  alarmItemPpMxIduLanIntfcMAlm
					}
		::= 113

	alarmTrapPpMxIduLanIntfcSAlm	TRAP-TYPE
		ENTERPRISE	pasolinkPlusMx
		VARIABLES	{
					  trapSequenceNumber,
					  trapDate,
					  trapTime,
					  severity,
					  alarmType,
					  probableCause,
					  trapSource,
					  alarmItemPpMxIduLanIntfcSAlm
					}
		::= 114

	alarmTrapPpMxIduModemAlm	TRAP-TYPE
		ENTERPRISE	pasolinkPlusMx
		VARIABLES	{
					  trapSequenceNumber,
					  trapDate,
					  trapTime,
					  severity,
					  alarmType,
					  probableCause,
					  trapSource,
					  alarmItemPpMxIduModemAlm
					}
		::= 115

	alarmTrapPpMxIduPsAlm	TRAP-TYPE
		ENTERPRISE	pasolinkPlusMx
		VARIABLES	{
					  trapSequenceNumber,
					  trapDate,
					  trapTime,
					  severity,
					  alarmType,
					  probableCause,
					  trapSource,
					  alarmItemPpMxIduPsAlm
					}
		::= 116

	alarmTrapPpMxIduLowBerAlm	TRAP-TYPE
		ENTERPRISE	pasolinkPlusMx
		VARIABLES	{
					  trapSequenceNumber,
					  trapDate,
					  trapTime,
					  severity,
					  alarmType,
					  probableCause,
					  trapSource,
					  alarmItemPpMxIduLowBerAlm
					}
		::= 117

	alarmTrapPpMxIduHighBerAlm	TRAP-TYPE
		ENTERPRISE	pasolinkPlusMx
		VARIABLES	{
					  trapSequenceNumber,
					  trapDate,
					  trapTime,
					  severity,
					  alarmType,
					  probableCause,
					  trapSource,
					  alarmItemPpMxIduHighBerAlm
					}
		::= 118

	alarmTrapPpMxIduLof	TRAP-TYPE
		ENTERPRISE	pasolinkPlusMx
		VARIABLES	{
					  trapSequenceNumber,
					  trapDate,
					  trapTime,
					  severity,
					  alarmType,
					  probableCause,
					  trapSource,
					  alarmItemPpMxIduLof
					}
		::= 119

	alarmTrapPpMxIduUsageError	TRAP-TYPE
		ENTERPRISE	pasolinkPlusMx
		VARIABLES	{
					  trapSequenceNumber,
					  trapDate,
					  trapTime,
					  severity,
					  alarmType,
					  probableCause,
					  trapSource,
					  alarmItemPpMxIduUsageError
					}
		::= 120

	alarmTrapPpMxCalendar	TRAP-TYPE
		ENTERPRISE	pasolinkPlusMx
		VARIABLES	{
					  trapSequenceNumber,
					  trapDate,
					  trapTime,
					  severity,
					  alarmType,
					  probableCause,
					  trapSource,
					  alarmItemPpMxCalendar
					}
		::= 121

	alarmTrapPpMxIdu4pLanLink	TRAP-TYPE
		ENTERPRISE	pasolinkPlusMx
		VARIABLES	{
					  trapSequenceNumber,
					  trapDate,
					  trapTime,
					  severity,
					  alarmType,
					  probableCause,
					  trapSource,
					  alarmItemPpMxIdu4pLanLink
					}
		::= 122

	alarmTrapPpMxIdu2pLanLink	TRAP-TYPE
		ENTERPRISE	pasolinkPlusMx
		VARIABLES	{
					  trapSequenceNumber,
					  trapDate,
					  trapTime,
					  severity,
					  alarmType,
					  probableCause,
					  trapSource,
					  alarmItemPpMxIdu2pLanLink
					}
		::= 123

	alarmTrapPpMxTcnDaily	TRAP-TYPE
		ENTERPRISE	pasolinkPlusMx
		VARIABLES	{
					  trapSequenceNumber,
					  trapDate,
					  trapTime,
					  severity,
					  alarmType,
					  probableCause,
					  trapSource,
					  alarmItemPpMxTcnDaily
					}
		::= 124

	alarmTrapPpMxTcnWeekly	TRAP-TYPE
		ENTERPRISE	pasolinkPlusMx
		VARIABLES	{
					  trapSequenceNumber,
					  trapDate,
					  trapTime,
					  severity,
					  alarmType,
					  probableCause,
					  trapSource,
					  alarmItemPpMxTcnWeekly
					}
		::= 125

	alarmTrapPpMxIduTnsCard	TRAP-TYPE
		ENTERPRISE	pasolinkPlusMx
		VARIABLES	{
					  trapSequenceNumber,
					  trapDate,
					  trapTime,
					  severity,
					  alarmType,
					  probableCause,
					  trapSource,
					  alarmItemPpMxIduTnsCard
					}
		::= 126

	eventTrapPpMxRxSwitchMode	TRAP-TYPE
		ENTERPRISE	pasolinkPlusMx
		VARIABLES	{
					  trapSequenceNumber,
					  trapDate,
					  trapTime,
					  trapSource,
					  eventItemPpMxRxSwitchMode
					}
		::= 201

	eventTrapPpMxSelectedRx	TRAP-TYPE
		ENTERPRISE	pasolinkPlusMx
		VARIABLES	{
					  trapSequenceNumber,
					  trapDate,
					  trapTime,
					  trapSource,
					  eventItemPpMxSelectedRx
					}
		::= 202

	eventTrapPpMxTxSwitchMode	TRAP-TYPE
		ENTERPRISE	pasolinkPlusMx
		VARIABLES	{
					  trapSequenceNumber,
					  trapDate,
					  trapTime,
					  trapSource,
					  eventItemPpMxTxSwitchMode
					}
		::= 203

	eventTrapPpMxSelectedTx	TRAP-TYPE
		ENTERPRISE	pasolinkPlusMx
		VARIABLES	{
					  trapSequenceNumber,
					  trapDate,
					  trapTime,
					  trapSource,
					  eventItemPpMxSelectedTx
					}
		::= 204

	eventTrapPpMxMainChLB1AllOff	TRAP-TYPE
		ENTERPRISE	pasolinkPlusMx
		VARIABLES	{
					  trapSequenceNumber,
					  trapDate,
					  trapTime,
					  trapSource,
					  eventItemPpMxMainChLB1AllOff
					}
		::= 205

	eventTrapPpMxMainChLB2AllOff	TRAP-TYPE
		ENTERPRISE	pasolinkPlusMx
		VARIABLES	{
					  trapSequenceNumber,
					  trapDate,
					  trapTime,
					  trapSource,
					  eventItemPpMxMainChLB2AllOff
					}
		::= 206

	eventTrapPpMxMainChLB1	TRAP-TYPE
		ENTERPRISE	pasolinkPlusMx
		VARIABLES	{
					  trapSequenceNumber,
					  trapDate,
					  trapTime,
					  trapSource,
					  eventItemPpMxMainChLB1
					}
		::= 207

	eventTrapPpMxMainChLB2	TRAP-TYPE
		ENTERPRISE	pasolinkPlusMx
		VARIABLES	{
					  trapSequenceNumber,
					  trapDate,
					  trapTime,
					  trapSource,
					  eventItemPpMxMainChLB2
					}
		::= 208

	eventTrapPpMxAtpcManual	TRAP-TYPE
		ENTERPRISE	pasolinkPlusMx
		VARIABLES	{
					  trapSequenceNumber,
					  trapDate,
					  trapTime,
					  trapSource,
					  eventItemPpMxAtpcManual
					}
		::= 209

	eventTrapPpMxTxPower	TRAP-TYPE
		ENTERPRISE	pasolinkPlusMx
		VARIABLES	{
					  trapSequenceNumber,
					  trapDate,
					  trapTime,
					  trapSource,
					  eventItemPpMxTxPower
					}
		::= 210

	eventTrapPpMxTxMute	TRAP-TYPE
		ENTERPRISE	pasolinkPlusMx
		VARIABLES	{
					  trapSequenceNumber,
					  trapDate,
					  trapTime,
					  trapSource,
					  eventItemPpMxTxMute
					}
		::= 211

	eventTrapPpMxCw	TRAP-TYPE
		ENTERPRISE	pasolinkPlusMx
		VARIABLES	{
					  trapSequenceNumber,
					  trapDate,
					  trapTime,
					  trapSource,
					  eventItemPpMxCw
					}
		::= 212

	eventTrapPpMxIfLB	TRAP-TYPE
		ENTERPRISE	pasolinkPlusMx
		VARIABLES	{
					  trapSequenceNumber,
					  trapDate,
					  trapTime,
					  trapSource,
					  eventItemPpMxIfLB
					}
		::= 213

	eventTrapPpMxIdu4PortLanPortReset	TRAP-TYPE
		ENTERPRISE	pasolinkPlusMx
		VARIABLES	{
					  trapSequenceNumber,
					  trapDate,
					  trapTime,
					  trapSource,
					  eventItemPpMxIdu4PortLanPortReset
					}
		::= 214

	eventTrapPpMxIdu2PortLanPortReset	TRAP-TYPE
		ENTERPRISE	pasolinkPlusMx
		VARIABLES	{
					  trapSequenceNumber,
					  trapDate,
					  trapTime,
					  trapSource,
					  eventItemPpMxIdu2PortLanPortReset
					}
		::= 215

	eventTrapPpMxEquipmentMaint	TRAP-TYPE
		ENTERPRISE	pasolinkPlusMx
		VARIABLES	{
					  trapSequenceNumber,
					  trapDate,
					  trapTime,
					  trapSource,
					  eventItemPpMxEquipmentMaint
					}
		::= 216

	eventTrapPpMxConfigDataInvalid	TRAP-TYPE
		ENTERPRISE	pasolinkPlusMx
		VARIABLES	{
					  trapSequenceNumber,
					  trapDate,
					  trapTime,
					  trapSource,
					  eventItemPpMxConfigDataInvalid
					}
		::= 217

	eventTrapPpMxConfigDataUp	TRAP-TYPE
		ENTERPRISE	pasolinkPlusMx
		VARIABLES	{
					  trapSequenceNumber,
					  trapDate,
					  trapTime,
					  trapSource,
					  eventItemPpMxConfigDataUp
					}
		::= 218

	eventTrapPpMxIduAisGenerated	TRAP-TYPE
		ENTERPRISE	pasolinkPlusMx
		VARIABLES	{
					  trapSequenceNumber,
					  trapDate,
					  trapTime,
					  trapSource,
					  eventItemPpMxIduAisGenerated
					}
		::= 219

	eventTrapPpMxIdu4pLanCollision	TRAP-TYPE
		ENTERPRISE	pasolinkPlusMx
		VARIABLES	{
					  trapSequenceNumber,
					  trapDate,
					  trapTime,
					  trapSource,
					  eventItemPpMxIdu4pLanCollision
					}
		::= 220

	eventTrapPpMxIdu4pLanPortSpeedDuplex	TRAP-TYPE
		ENTERPRISE	pasolinkPlusMx
		VARIABLES	{
					  trapSequenceNumber,
					  trapDate,
					  trapTime,
					  trapSource,
					  eventItemPpMxIdu4pLanPortSpeedDuplex
					}
		::= 221

	eventTrapPpMxIdu4pLanLinkLosForwarding	TRAP-TYPE
		ENTERPRISE	pasolinkPlusMx
		VARIABLES	{
					  trapSequenceNumber,
					  trapDate,
					  trapTime,
					  trapSource,
					  eventItemPpMxIdu4pLanLinkLosForwarding
					}
		::= 222

	eventTrapPpMxIdu2pLanCollision	TRAP-TYPE
		ENTERPRISE	pasolinkPlusMx
		VARIABLES	{
					  trapSequenceNumber,
					  trapDate,
					  trapTime,
					  trapSource,
					  eventItemPpMxIdu2pLanCollision
					}
		::= 223

	eventTrapPpMxIdu2pLanPortSpeedDuplex	TRAP-TYPE
		ENTERPRISE	pasolinkPlusMx
		VARIABLES	{
					  trapSequenceNumber,
					  trapDate,
					  trapTime,
					  trapSource,
					  eventItemPpMxIdu2pLanPortSpeedDuplex
					}
		::= 224

	eventTrapPpMxIdu2pLanLinkLosForwarding	TRAP-TYPE
		ENTERPRISE	pasolinkPlusMx
		VARIABLES	{
					  trapSequenceNumber,
					  trapDate,
					  trapTime,
					  trapSource,
					  eventItemPpMxIdu2pLanLinkLosForwarding
					}
		::= 225

	eventTrapPpMxTcnDailyOccur	TRAP-TYPE
		ENTERPRISE	pasolinkPlusMx
		VARIABLES	{
					  trapSequenceNumber,
					  trapDate,
					  trapTime,
					  trapSource,
					  eventItemPpMxTcnDailyOccur
					}
		::= 226

	eventTrapPpMxTcnDailyRecover	TRAP-TYPE
		ENTERPRISE	pasolinkPlusMx
		VARIABLES	{
					  trapSequenceNumber,
					  trapDate,
					  trapTime,
					  trapSource,
					  eventItemPpMxTcnDailyRecover
					}
		::= 227

	eventTrapPpMxTcnWeeklyOccur	TRAP-TYPE
		ENTERPRISE	pasolinkPlusMx
		VARIABLES	{
					  trapSequenceNumber,
					  trapDate,
					  trapTime,
					  trapSource,
					  eventItemPpMxTcnWeeklyOccur
					}
		::= 228

	eventTrapPpMxTcnWeeklyRecover	TRAP-TYPE
		ENTERPRISE	pasolinkPlusMx
		VARIABLES	{
					  trapSequenceNumber,
					  trapDate,
					  trapTime,
					  trapSource,
					  eventItemPpMxTcnWeeklyRecover
					}
		::= 229

	eventTrapPpMxBerThreshold	TRAP-TYPE
		ENTERPRISE	pasolinkPlusMx
		VARIABLES	{
					  trapSequenceNumber,
					  trapDate,
					  trapTime,
					  trapSource,
					  eventItemPpMxBerThreshold
					}
		::= 230

	eventTrapPpMxAdditionalAtt	TRAP-TYPE
		ENTERPRISE	pasolinkPlusMx
		VARIABLES	{
					  trapSequenceNumber,
					  trapDate,
					  trapTime,
					  trapSource,
					  eventItemPpMxAdditionalAtt
					}
		::= 231

	eventTrapPpMxAtpcMax	TRAP-TYPE
		ENTERPRISE	pasolinkPlusMx
		VARIABLES	{
					  trapSequenceNumber,
					  trapDate,
					  trapTime,
					  trapSource,
					  eventItemPpMxAtpcMax
					}
		::= 232

	eventTrapPpMxAtpcMin	TRAP-TYPE
		ENTERPRISE	pasolinkPlusMx
		VARIABLES	{
					  trapSequenceNumber,
					  trapDate,
					  trapTime,
					  trapSource,
					  eventItemPpMxAtpcMin
					}
		::= 233

	eventTrapPpMxAtpcRxThresholdLevel	TRAP-TYPE
		ENTERPRISE	pasolinkPlusMx
		VARIABLES	{
					  trapSequenceNumber,
					  trapDate,
					  trapTime,
					  trapSource,
					  eventItemPpMxAtpcRxThresholdLevel
					}
		::= 234

	eventTrapPpMxOduAlarmMode	TRAP-TYPE
		ENTERPRISE	pasolinkPlusMx
		VARIABLES	{
					  trapSequenceNumber,
					  trapDate,
					  trapTime,
					  trapSource,
					  eventItemPpMxOduAlarmMode
					}
		::= 236

	eventTrapPpMxMtpcTxPower	TRAP-TYPE
		ENTERPRISE	pasolinkPlusMx
		VARIABLES	{
					  trapSequenceNumber,
					  trapDate,
					  trapTime,
					  trapSource,
					  eventItemPpMxMtpcTxPower
					}
		::= 237

	eventTrapPpMxTxSwPriority	TRAP-TYPE
		ENTERPRISE	pasolinkPlusMx
		VARIABLES	{
					  trapSequenceNumber,
					  trapDate,
					  trapTime,
					  trapSource,
					  eventItemPpMxTxSwPriority
					}
		::= 238

	eventTrapPpMxRxSwPriority	TRAP-TYPE
		ENTERPRISE	pasolinkPlusMx
		VARIABLES	{
					  trapSequenceNumber,
					  trapDate,
					  trapTime,
					  trapSource,
					  eventItemPpMxRxSwPriority
					}
		::= 239

	eventTrapPpMxAisActivationCondition	TRAP-TYPE
		ENTERPRISE	pasolinkPlusMx
		VARIABLES	{
					  trapSequenceNumber,
					  trapDate,
					  trapTime,
					  trapSource,
					  eventItemPpMxAisActivationCondition
					}
		::= 241

	eventTrapPpMxMainChAisReceivedReport	TRAP-TYPE
		ENTERPRISE	pasolinkPlusMx
		VARIABLES	{
					  trapSequenceNumber,
					  trapDate,
					  trapTime,
					  trapSource,
					  eventItemPpMxMainChAisReceivedReport
					}
		::= 242

	eventTrapPpMxMainChAisReceivedConditionSetting	TRAP-TYPE
		ENTERPRISE	pasolinkPlusMx
		VARIABLES	{
					  trapSequenceNumber,
					  trapDate,
					  trapTime,
					  trapSource,
					  eventItemPpMxMainChAisReceivedConditionSetting
					}
		::= 243

	eventTrapPpMxMainChAisGeneratedReport	TRAP-TYPE
		ENTERPRISE	pasolinkPlusMx
		VARIABLES	{
					  trapSequenceNumber,
					  trapDate,
					  trapTime,
					  trapSource,
					  eventItemPpMxMainChAisGeneratedReport
					}
		::= 244

	eventTrapPpMxMainChUsage	TRAP-TYPE
		ENTERPRISE	pasolinkPlusMx
		VARIABLES	{
					  trapSequenceNumber,
					  trapDate,
					  trapTime,
					  trapSource,
					  eventItemPpMxMainChUsage
					}
		::= 245

	eventTrapPpMxMainChErrorReport	TRAP-TYPE
		ENTERPRISE	pasolinkPlusMx
		VARIABLES	{
					  trapSequenceNumber,
					  trapDate,
					  trapTime,
					  trapSource,
					  eventItemPpMxMainChErrorReport
					}
		::= 246

	eventTrapPpMx4pLanPortUsage	TRAP-TYPE
		ENTERPRISE	pasolinkPlusMx
		VARIABLES	{
					  trapSequenceNumber,
					  trapDate,
					  trapTime,
					  trapSource,
					  eventItemPpMx4pLanPortUsage
					}
		::= 247

	eventTrapPpMx4pLanPortSpeedDuplex	TRAP-TYPE
		ENTERPRISE	pasolinkPlusMx
		VARIABLES	{
					  trapSequenceNumber,
					  trapDate,
					  trapTime,
					  trapSource,
					  eventItemPpMx4pLanPortSpeedDuplex
					}
		::= 248

	eventTrapPpMx4pLanFlowControl	TRAP-TYPE
		ENTERPRISE	pasolinkPlusMx
		VARIABLES	{
					  trapSequenceNumber,
					  trapDate,
					  trapTime,
					  trapSource,
					  eventItemPpMx4pLanFlowControl
					}
		::= 249

	eventTrapPpMx4pLanCollisionReport	TRAP-TYPE
		ENTERPRISE	pasolinkPlusMx
		VARIABLES	{
					  trapSequenceNumber,
					  trapDate,
					  trapTime,
					  trapSource,
					  eventItemPpMx4pLanCollisionReport
					}
		::= 250

	eventTrapPpMx4pLanLinkLossForwarding	TRAP-TYPE
		ENTERPRISE	pasolinkPlusMx
		VARIABLES	{
					  trapSequenceNumber,
					  trapDate,
					  trapTime,
					  trapSource,
					  eventItemPpMx4pLanLinkLossForwarding
					}
		::= 251

	eventTrapPpMx4pLanPortSwitching	TRAP-TYPE
		ENTERPRISE	pasolinkPlusMx
		VARIABLES	{
					  trapSequenceNumber,
					  trapDate,
					  trapTime,
					  trapSource,
					  eventItemPpMx4pLanPortSwitching
					}
		::= 252

	eventTrapPpMx2pLanPortUsage	TRAP-TYPE
		ENTERPRISE	pasolinkPlusMx
		VARIABLES	{
					  trapSequenceNumber,
					  trapDate,
					  trapTime,
					  trapSource,
					  eventItemPpMx2pLanPortUsage
					}
		::= 253

	eventTrapPpMx2pLanPortSpeedDuplex	TRAP-TYPE
		ENTERPRISE	pasolinkPlusMx
		VARIABLES	{
					  trapSequenceNumber,
					  trapDate,
					  trapTime,
					  trapSource,
					  eventItemPpMx2pLanPortSpeedDuplex
					}
		::= 254

	eventTrapPpMx2pLanFlowControl	TRAP-TYPE
		ENTERPRISE	pasolinkPlusMx
		VARIABLES	{
					  trapSequenceNumber,
					  trapDate,
					  trapTime,
					  trapSource,
					  eventItemPpMx2pLanFlowControl
					}
		::= 255

	eventTrapPpMx2pLanCollisionReport	TRAP-TYPE
		ENTERPRISE	pasolinkPlusMx
		VARIABLES	{
					  trapSequenceNumber,
					  trapDate,
					  trapTime,
					  trapSource,
					  eventItemPpMx2pLanCollisionReport
					}
		::= 256

	eventTrapPpMx2pLanLinkLossForwarding	TRAP-TYPE
		ENTERPRISE	pasolinkPlusMx
		VARIABLES	{
					  trapSequenceNumber,
					  trapDate,
					  trapTime,
					  trapSource,
					  eventItemPpMx2pLanLinkLossForwarding
					}
		::= 257

	eventTrapPpMx2pLanPort1or12Lan2MFraming	TRAP-TYPE
		ENTERPRISE	pasolinkPlusMx
		VARIABLES	{
					  trapSequenceNumber,
					  trapDate,
					  trapTime,
					  trapSource,
					  eventItemPpMx2pLanPort1or12Lan2MFraming
					}
		::= 258

	eventTrapPpMx2pLanPort2Lan2MFraming	TRAP-TYPE
		ENTERPRISE	pasolinkPlusMx
		VARIABLES	{
					  trapSequenceNumber,
					  trapDate,
					  trapTime,
					  trapSource,
					  eventItemPpMx2pLanPort2Lan2MFraming
					}
		::= 259

	eventTrapPpMx2pLanPortSwitching	TRAP-TYPE
		ENTERPRISE	pasolinkPlusMx
		VARIABLES	{
					  trapSequenceNumber,
					  trapDate,
					  trapTime,
					  trapSource,
					  eventItemPpMx2pLanPortSwitching
					}
		::= 260

	eventTrapPpMxSc1Usage	TRAP-TYPE
		ENTERPRISE	pasolinkPlusMx
		VARIABLES	{
					  trapSequenceNumber,
					  trapDate,
					  trapTime,
					  trapSource,
					  eventItemPpMxSc1Usage
					}
		::= 261

	eventTrapPpMxSc2Usage	TRAP-TYPE
		ENTERPRISE	pasolinkPlusMx
		VARIABLES	{
					  trapSequenceNumber,
					  trapDate,
					  trapTime,
					  trapSource,
					  eventItemPpMxSc2Usage
					}
		::= 262

	eventTrapPpMxSc3Usage	TRAP-TYPE
		ENTERPRISE	pasolinkPlusMx
		VARIABLES	{
					  trapSequenceNumber,
					  trapDate,
					  trapTime,
					  trapSource,
					  eventItemPpMxSc3Usage
					}
		::= 263

	eventTrapPpMxSc4Usage	TRAP-TYPE
		ENTERPRISE	pasolinkPlusMx
		VARIABLES	{
					  trapSequenceNumber,
					  trapDate,
					  trapTime,
					  trapSource,
					  eventItemPpMxSc4Usage
					}
		::= 264

	eventTrapPpMxRelay	TRAP-TYPE
		ENTERPRISE	pasolinkPlusMx
		VARIABLES	{
					  trapSequenceNumber,
					  trapDate,
					  trapTime,
					  trapSource,
					  eventItemPpMxRelay
					}
		::= 265

	eventTrapPpMxTxFreq	TRAP-TYPE
		ENTERPRISE	pasolinkPlusMx
		VARIABLES	{
					  trapSequenceNumber,
					  trapDate,
					  trapTime,
					  trapSource,
					  eventItemPpMxTxFreq
					}
		::= 266

	eventTrapPpMxRxFreq	TRAP-TYPE
		ENTERPRISE	pasolinkPlusMx
		VARIABLES	{
					  trapSequenceNumber,
					  trapDate,
					  trapTime,
					  trapSource,
					  eventItemPpMxRxFreq
					}
		::= 267

	eventTrapPpMxShiftFreq	TRAP-TYPE
		ENTERPRISE	pasolinkPlusMx
		VARIABLES	{
					  trapSequenceNumber,
					  trapDate,
					  trapTime,
					  trapSource,
					  eventItemPpMxShiftFreq
					}
		::= 269

	eventTrapPpMxSubBand	TRAP-TYPE
		ENTERPRISE	pasolinkPlusMx
		VARIABLES	{
					  trapSequenceNumber,
					  trapDate,
					  trapTime,
					  trapSource,
					  eventItemPpMxSubBand
					}
		::= 270

	eventTrapPpMxInventoryUpdate	TRAP-TYPE
		ENTERPRISE	pasolinkPlusMx
		VARIABLES	{
					  trapSequenceNumber,
					  trapDate,
					  trapTime,
					  trapSource,
					  eventItemPpMxInventoryUpdate
					}
		::= 271

	eventTrapPpMxAuxOutput	TRAP-TYPE
		ENTERPRISE	pasolinkPlusMx
		VARIABLES	{
					  trapSequenceNumber,
					  trapDate,
					  trapTime,
					  trapSource,
					  eventItemPpMxAuxOutput
					}
		::= 272

	eventTrapPpMxInsertedModule	TRAP-TYPE
		ENTERPRISE	pasolinkPlusMx
		VARIABLES	{
					  trapSequenceNumber,
					  trapDate,
					  trapTime,
					  trapSource,
					  eventItemPpMxInsertedModule
					}
		::= 274

	eventTrapPpMxModuleDetected	TRAP-TYPE
		ENTERPRISE	pasolinkPlusMx
		VARIABLES	{
					  trapSequenceNumber,
					  trapDate,
					  trapTime,
					  trapSource,
					  eventItemPpMxModuleDetected
					}
		::= 275

	eventTrapPpMxTxMuteReleaseTime	TRAP-TYPE
		ENTERPRISE	pasolinkPlusMx
		VARIABLES	{
					  trapSequenceNumber,
					  trapDate,
					  trapTime,
					  trapSource,
					  eventItemPpMxTxMuteReleaseTime
					}
		::= 276

	eventTrapPpMxClusterAlarmUsage	TRAP-TYPE
		ENTERPRISE	pasolinkPlusMx
		VARIABLES	{
					  trapSequenceNumber,
					  trapDate,
					  trapTime,
					  trapSource,
					  eventItemPpMxClusterAlarmUsage
					}
		::= 277

	statusTrapPpMxAuxInput	TRAP-TYPE
		ENTERPRISE	pasolinkPlusMx
		VARIABLES	{
					  trapSequenceNumber,
					  trapDate,
					  trapTime,
					  trapSource,
					  severity,
					  alarmType,
					  probableCause,
					  statusTypeAux,
					  statusItemPpMxAuxInput
					}
		::= 501

	statusTrapPpMxAisReceived	TRAP-TYPE
		ENTERPRISE	pasolinkPlusMx
		VARIABLES	{
					  trapSequenceNumber,
					  trapDate,
					  trapTime,
					  trapSource,
					  severity,
					  alarmType,
					  probableCause,
					  statusTypeAis,
					  statusItemPpMxAisReceived
					}
		::= 502

	systemTrapPpMxGetResult TRAP-TYPE
		ENTERPRISE  pasolinkPlusMx     
		VARIABLES {
					  trapSequenceNumber,
					  trapDate,
					  trapTime,
					  systemItemPpMxGetMeteringRequestID,
					  systemItemPpMxGetMeteringTargetIpAddress,      
					  systemItemPpMxGetMeteringResult
					}
		DESCRIPTION	"The result of Request"
		::= 601


-----------------------------------------------
-- ppMxAlarmStatusInfo Group Definitions
-----------------------------------------------

	ppMxasControlStatus OBJECT IDENTIFIER
		::= { ppMxAlarmStatusInfo 1 }

	ppMxasControlStatusCom OBJECT IDENTIFIER
		::= { ppMxasControlStatus 1 }

	ppMxcsComTable OBJECT-TYPE
		SYNTAX		SEQUENCE OF PpMxcsComEntry
		ACCESS		not-accessible
		STATUS		optional
		DESCRIPTION	"Control Status Common Table"
		::= { ppMxasControlStatusCom 1 }

	ppMxcsComEntry OBJECT-TYPE
		SYNTAX		PpMxcsComEntry
		ACCESS		not-accessible
		STATUS		optional
		DESCRIPTION	"Control Status Common Table Entry"
		INDEX		{
					ppMxcsComPasoIndex	
					}
		::= { ppMxcsComTable 1 }

	PpMxcsComEntry ::= SEQUENCE {
					  ppMxcsComPasoIndex 		IpAddress,
					  ppMxcsRxSwitchCtrl		SwitchCtrlValue,
					  ppMxcsTxSwitchCtrl		SwitchCtrlValue,
					  ppMxcsRxSwitchMode		SwitchModeValue, 
					  ppMxcsSelectedRx		SwitchStatusValue,
					  ppMxcsTxSwitchMode		SwitchModeValue, 
					  ppMxcsSelectedTx		SwitchStatusValue,
					  ppMxcsMainChLB1AllOff	INTEGER, 
					  ppMxcsMainChLB2AllOff	INTEGER	
					 }			
					 
	
	ppMxcsComPasoIndex OBJECT-TYPE
		SYNTAX		IpAddress 
		ACCESS		read-only
		STATUS		mandatory
		DESCRIPTION	"Pasolink IP Address Index"
		::= { ppMxcsComEntry 1 }
		
	ppMxcsRxSwitchCtrl OBJECT-TYPE
		SYNTAX		SwitchCtrlValue
		ACCESS		read-only
		STATUS		mandatory
		DESCRIPTION	"(Not used) 
                             RX Switch Control 0:INVALID, 1:AUTO, 2:No.1, 3:No.2
					
					FLAG=EVLOG|NONTC_10
					LOGITEM='RX SWITCH'
					LOGSTATUS='INVALID(0),AUTO(1),No.1(2),No.2(3)'
					LOGFLAG='LII_I_ZERO'"
		::= { ppMxcsComEntry 2 }

	ppMxcsTxSwitchCtrl OBJECT-TYPE
		SYNTAX		SwitchCtrlValue
		ACCESS		read-only
		STATUS		mandatory
		DESCRIPTION	"(Not used)
                             TX Switch Control 0:INVALID, 1:AUTO, 2:No.1, 3:No.2
					
					FLAG=EVLOG|NONTC_10|NONTC_TP
					LOGITEM='TX SWITCH'
					LOGSTATUS='INVALID(0),AUTO(1),No.1(2),No.2(3)'
					LOGFLAG='LII_I_ZERO'"
		::= { ppMxcsComEntry 3 }

	ppMxcsRxSwitchMode OBJECT-TYPE
		SYNTAX		SwitchModeValue
		ACCESS		read-only
		STATUS		mandatory
		DESCRIPTION	"RX Switch Mode 0:INVALID, 2:MANUAL, 1:AUTO
					
					FLAG=TRAP|EVLOG|NONTC_10
					LOGITEM='RX SWITCH MODE'
					LOGSTATUS='INVALID(0),AUTO(1),MANUAL(2)'
					LOGFLAG='LII_I_ZERO'
					TRAP=eventTrapPpMxRxSwitchMode"
		::= { ppMxcsComEntry 4 }

	ppMxcsSelectedRx OBJECT-TYPE
		SYNTAX		SwitchStatusValue
		ACCESS		read-only
		STATUS		mandatory
		DESCRIPTION	"Selected RX 0:INVALID, 1:No.1, 2:No.2
					
					FLAG=TRAP|EVLOG|NONTC_10
					LOGITEM='SELECTED RX'
					LOGSTATUS='INVALID(0),No.1(1),No.2(2)'
					LOGFLAG='LII_I_ZERO'
					TRAP=eventTrapPpMxSelectedRx"
		::= { ppMxcsComEntry 5 }

	ppMxcsTxSwitchMode OBJECT-TYPE
		SYNTAX		SwitchModeValue
		ACCESS		read-only
		STATUS		mandatory
		DESCRIPTION	"TX Switch Mode 0:INVALID, 2:MANUAL, 1:AUTO
					FLAG=TRAP|EVLOG|NONTC_10|NONTC_TP
					LOGITEM='TX SWITCH MODE'
					LOGSTATUS='INVALID(0),AUTO(1),MANUAL(2)'
					LOGFLAG='LII_I_ZERO'
					TRAP=eventTrapPpMxTxSwitchMode"
		::= { ppMxcsComEntry 6 }

	ppMxcsSelectedTx OBJECT-TYPE
		SYNTAX		SwitchStatusValue
		ACCESS		read-only
		STATUS		mandatory
		DESCRIPTION	"Selected TX 0:INVALID, 1:No.1,  2:No.2
					FLAG=TRAP|EVLOG|NONTC_10|NONTC_TP
					LOGITEM='SELECTED TX'
					LOGSTATUS='INVALID(0),No.1(1),No.2(2)'
					LOGFLAG='LII_I_ZERO'
					TRAP=eventTrapPpMxSelectedTx"
		::= { ppMxcsComEntry 7 }

	ppMxcsMainChLB1AllOff OBJECT-TYPE
		SYNTAX		INTEGER {
					    execute(1)
					}
		ACCESS		read-only
		STATUS		mandatory
		DESCRIPTION	"2M CH LOOPBACK-1 ALL OFF
					1:EXECUTE
					
					
					FLAG=TRAP|EVLOG|FORCED_NTC
					LOGITEM='2M CH LOOPBACK-1 ALL OFF'
					LOGSTATUS='EXECUTE(1)'
					TRAP=eventTrapPpMxMainChLB1AllOff"
		::= { ppMxcsComEntry 8 }

	ppMxcsMainChLB2AllOff OBJECT-TYPE
		SYNTAX		INTEGER {
					    execute(1)
					}
		ACCESS		read-only
		STATUS		mandatory
		DESCRIPTION	"2M CH  LOOPBACK-2  ALL OFF
					1:EXECUTE
					
					
					FLAG=TRAP|EVLOG|FORCED_NTC
					LOGITEM='2M CH LOOPBACK-2 ALL OFF'
					LOGSTATUS='EXECUTE(1)'
					TRAP=eventTrapPpMxMainChLB2AllOff"
		::= { ppMxcsComEntry 9 }
		

	ppMxcsChTable OBJECT-TYPE
		SYNTAX		SEQUENCE OF PpMxcsChEntry
		ACCESS		not-accessible
		STATUS		mandatory
		DESCRIPTION	"Control Ch Table"
		::= { ppMxasControlStatus 2 }

	ppMxcsChEntry OBJECT-TYPE
		SYNTAX		PpMxcsChEntry
		ACCESS		not-accessible
		STATUS		mandatory
		DESCRIPTION	"Control Ch Table Entry"
		INDEX		{
						ppMxcsChPasoIndex,
						ppMxcsChIndex
					}
		::= { ppMxcsChTable 1 }

	PpMxcsChEntry ::= SEQUENCE {
					  ppMxcsChPasoIndex        IpAddress,
					  ppMxcsChIndex           INTEGER,
					  ppMxcsMainChLB1         OffOn01Value,
					  ppMxcsMainChLB2         OffOn01Value
					}

	ppMxcsChPasoIndex OBJECT-TYPE
		SYNTAX		IpAddress 
		ACCESS		read-only
		STATUS		mandatory
		DESCRIPTION	"Pasolink IP Address Index"
		::= { ppMxcsChEntry 1 }
		
	ppMxcsChIndex OBJECT-TYPE
		SYNTAX		INTEGER( 1..40 )
		ACCESS		read-only
		STATUS		mandatory
		DESCRIPTION	"Index CH 
					1:CH1,2:CH2,...,40:CH40"
		::= { ppMxcsChEntry 2 }

	ppMxcsMainChLB1 OBJECT-TYPE
		SYNTAX		OffOn01Value
		ACCESS		read-only
		STATUS		mandatory
		DESCRIPTION	"2M CHxx  LOOPBACK-1 Control
					0:INVALID,  1:OFF,  2:ON
					
					FLAG=TRAP|EVLOG
					LOGITEM='2M CH%d LOOPBACK-1'
					LOGSTATUS='INVALID(0),OFF(1),ON(2)'
					LOGFLAG='LII_I_TABIX'
					TRAP=eventTrapPpMxMainChLB1"
		::= { ppMxcsChEntry 3 }

	ppMxcsMainChLB2 OBJECT-TYPE
		SYNTAX		OffOn01Value
		ACCESS		read-only
		STATUS		mandatory
		DESCRIPTION	"2M CHxx  LOOPBACK-2 Control
					0:INVALID,  1:OFF,  2:ON
					
					FLAG=TRAP|EVLOG
					LOGITEM='2M CH%d LOOPBACK-2'
					LOGSTATUS='INVALID(0),OFF(1),ON(2)'
					LOGFLAG='LII_I_TABIX'
					TRAP=eventTrapPpMxMainChLB2"
		::= { ppMxcsChEntry 4 }

	ppMxcsIndvTable OBJECT-TYPE
		SYNTAX		SEQUENCE OF PpMxcsIndvEntry
		ACCESS		not-accessible
		STATUS		mandatory
		DESCRIPTION	"Control Status No.1/No.2 Table"
		::= { ppMxasControlStatus 3 }

	ppMxcsIndvEntry OBJECT-TYPE
		SYNTAX		PpMxcsIndvEntry
		ACCESS		not-accessible
		STATUS		mandatory
		DESCRIPTION	"Control Status No.1/No.2 Table Entry"
		INDEX		{
						ppMxcsIndvPasoIndex,
						ppMxcsIndvIndex
					}
		::= { ppMxcsIndvTable 1 }

	PpMxcsIndvEntry ::= SEQUENCE {
					  ppMxcsIndvPasoIndex         IpAddress,
					  ppMxcsIndvIndex             INTEGER,
					  ppMxcsAtpcManual            INTEGER,
					  ppMxcsTxPower               INTEGER,
					  ppMxcsCw                    OffOn01Value,
					  ppMxcsTxMute                OffOn01Value,
					  ppMxcsTxMuteReleaseTime     INTEGER,
					  ppMxcsIfLB                  OffOn01Value
					}

	ppMxcsIndvPasoIndex OBJECT-TYPE
		SYNTAX		IpAddress 
		ACCESS		read-only
		STATUS		mandatory
		DESCRIPTION	"Pasolink IP Address Index"
		::= { ppMxcsIndvEntry 1 }
		
	ppMxcsIndvIndex OBJECT-TYPE
		SYNTAX		INTEGER {
					  no1(1),
					  no2(2)
					}
		ACCESS		read-only
		STATUS		mandatory
		DESCRIPTION	"Index
					1:No.1, 2:No.2"
		::= { ppMxcsIndvEntry 2 }

	ppMxcsAtpcManual OBJECT-TYPE
		SYNTAX		INTEGER (0..2)
		ACCESS		read-only
		STATUS		mandatory
		DESCRIPTION	"ATPC MANUAL CONTROL 0:INVALID, 2:MANUAL, 1:AUTO
					if This item is MANUAL(1) ,ppMxcsTxPower is used.
					
					FLAG=TRAP|EVLOG
					LOGITEM='ATPC MANUAL'
					LOGSTATUS='INVALID(0),OFF(1),ON(2)'
					LOGFLAG='LII_I_SYSTEM'
					TRAP=eventTrapPpMxAtpcManual"
		::= { ppMxcsIndvEntry 3 }

	ppMxcsTxPower OBJECT-TYPE
		SYNTAX		INTEGER
		ACCESS		read-only
		STATUS		mandatory
		DESCRIPTION	"TX POWER
					
					Range:ppMxpdiTxPwrCtrlAtpcMaxValue,ppMxpdiTxPwrCtrlAtpcMinValue
					
					if ppMxcsAtpcManual is AUTO(0), This value is ignored.
					
					FLAG=TRAP|EVLOG
					LOGITEM='TX POWER [dB]'
					LOGSTATUS='%d'
					LOGFLAG='LII_S_DEC|LII_I_SYSTEM'
					TRAP=eventTrapPpMxTxPower"
		::= { ppMxcsIndvEntry 4 }

	ppMxcsCw OBJECT-TYPE
		SYNTAX		OffOn01Value
		ACCESS		read-only
		STATUS		mandatory
		DESCRIPTION	"Carrier Wave CONTROL 0:INVALID, 1:OFF, 2:ON
					
					FLAG=TRAP|EVLOG
					LOGITEM='CW '
					LOGSTATUS='INVALID(0),OFF(1),ON(2)'
					LOGFLAG='LII_I_SYSTEM'
					TRAP=eventTrapPpMxCw"
		::= { ppMxcsIndvEntry 5 }

	ppMxcsTxMute OBJECT-TYPE
		SYNTAX		OffOn01Value
		ACCESS		read-only
		STATUS		mandatory
		DESCRIPTION	"TX MUTE CONTROL  0:INVALID, 1:OFF, 2:ON
					
					FLAG=TRAP|EVLOG
					LOGITEM='TX MUTE'
					LOGSTATUS='INVALID(0),OFF(1),ON(2)'
					LOGFLAG='LII_I_SYSTEM'
					TRAP=eventTrapPpMxTxMute"
		::= { ppMxcsIndvEntry 6 }

	ppMxcsTxMuteReleaseTime OBJECT-TYPE
		SYNTAX		INTEGER
		ACCESS		read-only
		STATUS		mandatory
		DESCRIPTION	"TX MUTE RELEASE TIME
					FLAG=TRAP|EVLOG
					LOGITEM='TX MUTE RELEASE TIME[SEC]'
					LOGSTATUS='%d'
					LOGFLAG='LII_S_DEC|LII_I_NOWRITE_CTRL|LII_I_SYSTEM'
					TRAP=eventTrapPpMxTxMuteReleaseTime"
		::= { ppMxcsIndvEntry 7 }

	ppMxcsIfLB OBJECT-TYPE
		SYNTAX		OffOn01Value
		ACCESS		read-only
		STATUS		mandatory
		DESCRIPTION	"IF LOOPBACK CONTROL  0;INVALID, 1:OFF, 2:ON
					
					
					FLAG=TRAP|EVLOG
					LOGITEM='IF LOOPBACK'
					LOGSTATUS='INVALID(0),OFF(1),ON(2)'
					LOGFLAG='LII_I_SYSTEM'
					TRAP=eventTrapPpMxIfLB"
		::= { ppMxcsIndvEntry 8 }

	ppMxcs4PortLanTable OBJECT-TYPE
		SYNTAX		SEQUENCE OF PpMxcs4PortLanEntry
		ACCESS		not-accessible
		STATUS		mandatory
		DESCRIPTION	"Control 4PORT LAN Table"
		::= { ppMxasControlStatus 4 }

	ppMxcs4PortLanEntry OBJECT-TYPE
		SYNTAX		PpMxcs4PortLanEntry
		ACCESS		not-accessible
		STATUS		mandatory
		DESCRIPTION	"Control 4PORT LAN Table Entry"
		INDEX		{
						ppMxcs4PortLanPasoIndex,
						ppMxcs4PortLanIndex
					}
		::= { ppMxcs4PortLanTable 1 }

	PpMxcs4PortLanEntry ::= SEQUENCE {
					  ppMxcs4PortLanPasoIndex  IpAddress,
					  ppMxcs4PortLanIndex      INTEGER,
					  ppMxcs4PortLanPortReset  INTEGER
					}

	ppMxcs4PortLanPasoIndex OBJECT-TYPE
		SYNTAX		IpAddress 
		ACCESS		read-only
		STATUS		mandatory
		DESCRIPTION	"Pasolink IP Address Index"
		::= { ppMxcs4PortLanEntry 1 }
		
	ppMxcs4PortLanIndex OBJECT-TYPE
		SYNTAX		INTEGER {
					  port12(1),
					  port34(2)
					}
		ACCESS		read-only
		STATUS		mandatory
		DESCRIPTION	"Index 4PORT LAN Device
					4PORT LAN1-2(1),
					4PORT LAN3-4(2)
					"
		::= { ppMxcs4PortLanEntry 2 }

	ppMxcs4PortLanPortReset OBJECT-TYPE
		SYNTAX		INTEGER {
					    execute(1)
					}
		ACCESS		read-only
		STATUS		mandatory
		DESCRIPTION	"4PORT LAN PORT RESET
					1:EXECUTE
					FLAG=TRAP|EVLOG|FORCED_NTC|NONTC_BT
					LOGITEM='4PORT LAN PORT%s RESET'
					LOGSTATUS='EXECUTE(1)'
					LOGFLAG='LII_I_LAN_RESET'
					TRAP=eventTrapPpMxIdu4PortLanPortReset"
		::= { ppMxcs4PortLanEntry 3 }

	ppMxcs2PortLanTable OBJECT-TYPE
		SYNTAX		SEQUENCE OF PpMxcs2PortLanEntry
		ACCESS		not-accessible
		STATUS		mandatory
		DESCRIPTION	"Control 2PORT LAN Table"
		::= { ppMxasControlStatus 5 }

	ppMxcs2PortLanEntry OBJECT-TYPE
		SYNTAX		PpMxcs2PortLanEntry
		ACCESS		not-accessible
		STATUS		mandatory
		DESCRIPTION	"Control 2PORT LAN Table Entry"
		INDEX		{
						ppMxcs2PortLanPasoIndex,
						ppMxcs2PortLanIndex
					}
		::= { ppMxcs2PortLanTable 1 }

	PpMxcs2PortLanEntry ::= SEQUENCE {
					  ppMxcs2PortLanPasoIndex  IpAddress,
					  ppMxcs2PortLanIndex      INTEGER,
					  ppMxcs2PortLanPortReset  INTEGER
					}

	ppMxcs2PortLanPasoIndex OBJECT-TYPE
		SYNTAX		IpAddress 
		ACCESS		read-only
		STATUS		mandatory
		DESCRIPTION	"Pasolink IP Address Index"
		::= { ppMxcs2PortLanEntry 1 }
		
	ppMxcs2PortLanIndex OBJECT-TYPE
		SYNTAX		INTEGER {
					  port1(1),
					  port2(2)
					}
		ACCESS		read-only
		STATUS		mandatory
		DESCRIPTION	"Index 2PORT LAN Device
					  2PORT LAN1(1),
					  2PORT LAN2(2)
					"
		::= { ppMxcs2PortLanEntry 2 }

	ppMxcs2PortLanPortReset OBJECT-TYPE
		SYNTAX		INTEGER {
					    execute(1)
					}
		ACCESS		read-only
		STATUS		mandatory
		DESCRIPTION	"2PORT LAN PORT RESET
					1:EXECUTE
					FLAG=TRAP|EVLOG|FORCED_NTC
					LOGITEM='2PORT LAN PORT%d RESET'
					LOGSTATUS='EXECUTE(1)'
					LOGFLAG='LII_I_TABIX'
					TRAP=eventTrapPpMxIdu2PortLanPortReset"
		::= { ppMxcs2PortLanEntry 3 }

	ppMxasEquipmentStatus OBJECT IDENTIFIER
		::= { ppMxAlarmStatusInfo 2 }

	ppMxesMaintTable OBJECT-TYPE
		SYNTAX		SEQUENCE OF PpMxesMaintEntry
		ACCESS		not-accessible
		STATUS		optional
		DESCRIPTION	"Equipment Status Maint Table"
		::= { ppMxasEquipmentStatus 1 }

	ppMxesMaintEntry OBJECT-TYPE
		SYNTAX		PpMxesMaintEntry
		ACCESS		not-accessible
		STATUS		optional
		DESCRIPTION	"Equipment Status Maint Table Entry"
		INDEX		{
					ppMxesCmnMaintPasoIndex	
					}
		::= { ppMxesMaintTable 1 }

	PpMxesMaintEntry ::= SEQUENCE {
					  ppMxesCmnMaintPasoIndex    IpAddress,
					  ppMxesMaint                OffOn01Value
					 }					  
					         
	ppMxesCmnMaintPasoIndex OBJECT-TYPE
		SYNTAX		IpAddress 
		ACCESS		read-only
		STATUS		mandatory
		DESCRIPTION	"Pasolink IP Address Index"
		::= { ppMxesMaintEntry 1 }
		
	ppMxesMaint OBJECT-TYPE
		SYNTAX		OffOn01Value
		ACCESS		read-only
		STATUS		mandatory
		DESCRIPTION	"MAINT CONTROL
					0:INVALID, 1:OFF, 2:ON
					
					
					FLAG=TRAP|EVLOG
					LOGITEM='MAINT'
					LOGSTATUS='INVALID(0),OFF(1),ON(2)'
					TRAP=eventTrapPpMxEquipmentMaint"
		::= { ppMxesMaintEntry 2 }

	ppMxesSupportabilityTable OBJECT-TYPE
		SYNTAX		SEQUENCE OF PpMxesSupportabilityEntry
		ACCESS		not-accessible
		STATUS		mandatory
		DESCRIPTION	"Equipment Status Supportability Table"
		::= { ppMxasEquipmentStatus 2 }

	ppMxesSupportabilityEntry OBJECT-TYPE
		SYNTAX		PpMxesSupportabilityEntry
		ACCESS		not-accessible
		STATUS		mandatory
		DESCRIPTION	"Equipment Status Supportability Table Entry"
		INDEX		{
						ppMxesSupportabilityPasoIndex,
						ppMxesSupportabilityIndex
					}
		::= { ppMxesSupportabilityTable 1 }

	PpMxesSupportabilityEntry ::= SEQUENCE {
					  ppMxesSupportabilityPasoIndex    IpAddress,
					  ppMxesSupportabilityIndex        INTEGER,
					  ppMxesSupportability             INTEGER
					}
					
	ppMxesSupportabilityPasoIndex OBJECT-TYPE
		SYNTAX		IpAddress 
		ACCESS		read-only
		STATUS		mandatory
		DESCRIPTION	"Pasolink IP Address Index"
		::= { ppMxesSupportabilityEntry 1 }

	ppMxesSupportabilityIndex OBJECT-TYPE
		SYNTAX		INTEGER ( 1..3 )
		ACCESS		read-only
		STATUS		mandatory
		DESCRIPTION	" Supportability Index
					 1:4PLAN
					 2:20E1
					 3:RMON"
		::= { ppMxesSupportabilityEntry 2 }

	ppMxesSupportability OBJECT-TYPE
		SYNTAX		INTEGER ( 0..2 )
		ACCESS		read-only
		STATUS		mandatory
		DESCRIPTION	"Supportability 
					2:SUPPORTABLE
					1:UNSUPPORTABLE
					0:INVALID"
		::= { ppMxesSupportabilityEntry 3 }
		
	ppMxesComTable OBJECT-TYPE
		SYNTAX		SEQUENCE OF PpMxesComEntry
		ACCESS		not-accessible
		STATUS		optional
		DESCRIPTION	"Equipment Status Common Table"
		::= { ppMxasEquipmentStatus 3  }

	ppMxesComEntry OBJECT-TYPE
		SYNTAX		PpMxesComEntry
		ACCESS		not-accessible
		STATUS		optional
		DESCRIPTION	"Equipment Status Common Table Entry"
		INDEX		{
					ppMxesComPasoIndex
					}
		::= { ppMxesComTable 1 }

	PpMxesComEntry ::= SEQUENCE {
					  ppMxesComPasoIndex    IpAddress,	
					  ppMxesInsertedModule  INTEGER,
					  ppMxesEquipment       INTEGER,
					  ppMxesModuleDetected  OffOn01Value
					 }					  
					         
	ppMxesComPasoIndex OBJECT-TYPE
		SYNTAX		IpAddress 
		ACCESS		read-only
		STATUS		mandatory
		DESCRIPTION	"Pasolink IP Address Index"
		::= { ppMxesComEntry 1 }
		
	ppMxesInsertedModule OBJECT-TYPE
		SYNTAX		INTEGER ( 0..13 )
		ACCESS		read-only
		STATUS		mandatory
		DESCRIPTION	"INSERTED MODULE
					0:INVALID
					1:2M INTFC-M(32*2M) + BLANK
					2:2M INTFC-M(32*2M) + 2M INTFC-S
					3:2M INTFC-M(32*2M) + LAN INTFC-S
					4:BLANK + LAN INTFC-S
					5:LAN INTFC-M + BLANK
					6:LAN INTFC-M + 2M INTFC-S
					7:LAN INTFC-M + LAN INTFC-S
					8:2M INTFC-M(20*2M) + BLANK
					9:2M INTFC-M(20*2M) + LAN INTFC-S
					10:TNS CARD + BLANK
					11:TNS CARD + LAN INTFC-S
					12:PNMS CARD+ BLANK
					13:PNMS CARD+ LAN INTFC-S
					
					FLAG=TRAP|EVLOG
					LOGITEM='INSERTED MODULE'
					LOGSTATUS='CHANGED'
					TRAP=eventTrapPpMxInsertedModule"
		::= { ppMxesComEntry 2 }

	ppMxesEquipment OBJECT-TYPE
		SYNTAX		INTEGER
		ACCESS		read-only
		STATUS		mandatory
		DESCRIPTION	"EQUIPMENT
					0:INVALID
					1:Global/1+0
					2:Global/1+1
					3:Global/20*E1/1+0
					4:Global/20*E1/1+1
					5:BT/4*E1/1+0
					6:BT/20*E1/1+0"
		::= { ppMxesComEntry 3 }

	ppMxesModuleDetected OBJECT-TYPE
		SYNTAX		OffOn01Value
		ACCESS		read-only
		STATUS		mandatory
		DESCRIPTION	"MODULE DETECTED
					0:INVALID, 1:OFF, 2:ON
					
					FLAG=TRAP|EVLOG
					LOGITEM='MODULE DETECTED'
					LOGSTATUS='INVALID(0),OFF(1),ON(2)'
					TRAP=eventTrapPpMxModuleDetected"
		::= { ppMxesComEntry 4 }

	ppMxasOduStatus OBJECT IDENTIFIER
		::= { ppMxAlarmStatusInfo 3 }

	ppMxosIndvTable OBJECT-TYPE
		SYNTAX		SEQUENCE OF PpMxosIndvEntry
		ACCESS		not-accessible
		STATUS		mandatory
		DESCRIPTION	"ODU Status No.1/No.2 Table"
		::= { ppMxasOduStatus 1 }

	ppMxosIndvEntry OBJECT-TYPE
		SYNTAX		PpMxosIndvEntry
		ACCESS		not-accessible
		STATUS		mandatory
		DESCRIPTION	"ODU Status No.1/No.2 Table Entry"
		INDEX		{
						ppMxosIndvPasoIndex,
						ppMxosIndvIndex
					}
		::= { ppMxosIndvTable 1 }

	PpMxosIndvEntry ::= SEQUENCE {
					  ppMxosIndvPasoIndex   IpAddress,	
					  ppMxosIndvIndex   INTEGER,
					  ppMxosTxPowerAlm  NormalAlarm01Value,
					  ppMxosTxInputAlm  NormalAlarm01Value,
					  ppMxosRxLevelAlm  NormalAlarm01Value,
					  ppMxosApcAlm      NormalAlarm01Value,
					  ppMxosOduCpuAlm   NormalAlarm01Value
					}

	ppMxosIndvPasoIndex OBJECT-TYPE
		SYNTAX		IpAddress 
		ACCESS		read-only
		STATUS		mandatory
		DESCRIPTION	"Pasolink IP Address Index"
		::= { ppMxosIndvEntry 1 }
		
	ppMxosIndvIndex OBJECT-TYPE
		SYNTAX		INTEGER {
					  no1(1),
					  no2(2)
					}
		ACCESS		read-only
		STATUS		mandatory
		DESCRIPTION	"Index
					1:No.1, 2:No.2"
		::= { ppMxosIndvEntry 2 }

	ppMxosTxPowerAlm OBJECT-TYPE
		SYNTAX		NormalAlarm01Value
		ACCESS		read-only
		STATUS		mandatory
		DESCRIPTION	"0:INVALID,  1:NORMAL,  2:ALARM 
					FLAG=TRAP|EVLOG
					LOGITEM='TX POWER'
					LOGSTATUS='INVALID(0),NORMAL(1),ALARM(2)'
					LOGFLAG='LII_I_SYSTEM'
					TRAP=alarmTrapPpMxOduTxPower"
		::= { ppMxosIndvEntry 3 }

	ppMxosTxInputAlm OBJECT-TYPE
		SYNTAX		NormalAlarm01Value
		ACCESS		read-only
		STATUS		mandatory
		DESCRIPTION	"0:INVALID, 1:NORMAL,  2:ALARM 
					FLAG=TRAP|EVLOG
					LOGITEM='TX INPUT'
					LOGSTATUS='INVALID(0),NORMAL(1),ALARM(2)'
					LOGFLAG='LII_I_SYSTEM'
					TRAP=alarmTrapPpMxOduTxInput"
		::= { ppMxosIndvEntry 4 }

	ppMxosRxLevelAlm OBJECT-TYPE
		SYNTAX		NormalAlarm01Value
		ACCESS		read-only
		STATUS		mandatory
		DESCRIPTION	"0:INVALID, 1:NORMAL,  2:ALARM 
					FLAG=TRAP|EVLOG
					LOGITEM='RX LEVEL'
					LOGSTATUS='INVALID(0),NORMAL(1),ALARM(2)'
					LOGFLAG='LII_I_SYSTEM'
					TRAP=alarmTrapPpMxOduRxLevel"
		::= { ppMxosIndvEntry 5 }

	ppMxosApcAlm OBJECT-TYPE
		SYNTAX		NormalAlarm01Value
		ACCESS		read-only
		STATUS		mandatory
		DESCRIPTION	"0:INVALID, 1:NORMAL,  2:ALARM 
					FLAG=TRAP|EVLOG
					LOGITEM='APC'
					LOGSTATUS='INVALID(0),NORMAL(1),ALARM(2)'
					LOGFLAG='LII_I_SYSTEM'
					TRAP=alarmTrapPpMxOduApc"
		::= { ppMxosIndvEntry 6 }

	ppMxosOduCpuAlm OBJECT-TYPE
		SYNTAX		NormalAlarm01Value
		ACCESS		read-only
		STATUS		mandatory
		DESCRIPTION	"0:INVALID, 1:NORMAL,  2:ALARM 
					FLAG=TRAP|EVLOG
					LOGITEM='ODU CPU'
					LOGSTATUS='INVALID(0),NORMAL(1),ALARM(2)'
					LOGFLAG='LII_I_SYSTEM'
					TRAP=alarmTrapPpMxOduCpuAlm"
		::= { ppMxosIndvEntry 7 }

	ppMxasIduStatus OBJECT IDENTIFIER
		::= { ppMxAlarmStatusInfo 4 }

	ppMxasIduStatusCom OBJECT IDENTIFIER
		::= { ppMxasIduStatus 1 }

	ppMxisComTable OBJECT-TYPE
		SYNTAX		SEQUENCE OF PpMxisComEntry
		ACCESS		not-accessible
		STATUS		optional
		DESCRIPTION	"IDU Status Common Table"
		::= { ppMxasIduStatusCom 1 }

	ppMxisComEntry OBJECT-TYPE
		SYNTAX		PpMxisComEntry
		ACCESS		not-accessible
		STATUS		optional
		DESCRIPTION	"IDU Status Common Table Entry"
		INDEX		{
					ppMxisComPasoIndex
					}
		::= { ppMxisComTable 1 }

	PpMxisComEntry ::= SEQUENCE {
					  ppMxisComPasoIndex       IpAddress,	
					  ppMxisConfigDataInvalid  INTEGER,
					  ppMxisConfigDataUp       INTEGER,
					  ppMxisCalendarAlm        NormalAlarm01Value,
					  ppMxisMainBoardAlm       NormalAlarm01Value,
					  ppMxisCpuSubAlm          NormalAlarm01Value,
					  ppMxisLanIntfcMAlm       NormalAlarm01Value,
					  ppMxisLanIntfcSAlm       NormalAlarm01Value,
					  ppMxisTnsCard            INTEGER
					 }					  
					         
	ppMxisComPasoIndex OBJECT-TYPE
		SYNTAX		IpAddress 
		ACCESS		read-only
		STATUS		mandatory
		DESCRIPTION	"Pasolink IP Address Index"
		::= { ppMxisComEntry 1 }
		
	ppMxisConfigDataInvalid OBJECT-TYPE
		SYNTAX		INTEGER ( 0..1 )
		ACCESS		read-only
		STATUS		mandatory
		DESCRIPTION	"CONFIG DATA INVALID 0:INVALID, 1:VALID    
					FLAG=TRAP|EVLOG
					LOGITEM='EQUIPMENT CONFIGURATION DATA'
					LOGSTATUS='INVALID(0),VALID(1)'
					TRAP=eventTrapPpMxConfigDataInvalid"
		::= { ppMxisComEntry 2 }

	ppMxisConfigDataUp OBJECT-TYPE
		SYNTAX		INTEGER {
					  update(1)
					}
		ACCESS		read-only
		STATUS		mandatory
		DESCRIPTION	"CONFIG DATA UP FLG 1:UPDATE
					FLAG=TRAP|EVLOG
					LOGITEM='EQUIPMENT CONFIGURATION DATA'
					LOGSTATUS='UPDATED(1)'
					LOGFLAG='LII_I_UPDATE_ONLY'
					TRAP=eventTrapPpMxConfigDataUp"
		::= { ppMxisComEntry 3 }

	ppMxisCalendarAlm OBJECT-TYPE
		SYNTAX		NormalAlarm01Value
		ACCESS		read-only
		STATUS		mandatory
		DESCRIPTION	"0:INVALID, 1:NORMAL,  2:ALARM 
					FLAG=TRAP|EVLOG
					LOGITEM='CALENDAR ALM'
					LOGSTATUS='INVALID(0),NORMAL(1),ALARM(2)'
					TRAP=alarmTrapPpMxCalendar"
		::= { ppMxisComEntry 4 }

	ppMxisMainBoardAlm OBJECT-TYPE
		SYNTAX		NormalAlarm01Value
		ACCESS		read-only
		STATUS		mandatory
		DESCRIPTION	"0:INVALID,  1:NORMAL,  2:ALARM 
					FLAG=TRAP|EVLOG
					LOGITEM='MAIN BOARD'
					LOGSTATUS='INVALID(0),NORMAL(1),ALARM(2)'
					TRAP=alarmTrapPpMxIduMainBoardAlm"
		::= { ppMxisComEntry 5 }

	ppMxisCpuSubAlm OBJECT-TYPE
		SYNTAX		NormalAlarm01Value
		ACCESS		read-only
		STATUS		mandatory
		DESCRIPTION	"CPU(SUB) 0:INVALID,  1:NORMAL,  2:ALARM 
					FLAG=TRAP|EVLOG
					LOGITEM='CPU(SUB)'
					LOGSTATUS='INVALID(0),NORMAL(1),ALARM(2)'
					TRAP=alarmTrapPpMxIduCpuSubAlm"
		::= { ppMxisComEntry 6 }

	ppMxisLanIntfcMAlm OBJECT-TYPE
		SYNTAX		NormalAlarm01Value
		ACCESS		read-only
		STATUS		mandatory
		DESCRIPTION	"0:INVALID, 1:NORMAL,  2:ALARM 
					FLAG=TRAP|EVLOG|NONTC_BT
					LOGITEM='INTFC-M'
					LOGSTATUS='INVALID(0),NORMAL(1),ALARM(2)'
					TRAP=alarmTrapPpMxIduLanIntfcMAlm"
		::= { ppMxisComEntry 7 }

	ppMxisLanIntfcSAlm OBJECT-TYPE
		SYNTAX		NormalAlarm01Value
		ACCESS		read-only
		STATUS		mandatory
		DESCRIPTION	"0:INVALID,  1:NORMAL,  2:ALARM 
					FLAG=TRAP|EVLOG
					LOGITEM='INTFC-S'
					LOGSTATUS='INVALID(0),NORMAL(1),ALARM(2)'
					TRAP=alarmTrapPpMxIduLanIntfcSAlm"
		::= { ppMxisComEntry 8 }

	ppMxisTnsCard OBJECT-TYPE
		SYNTAX		INTEGER ( 0..2 )
		ACCESS		read-only
		STATUS		mandatory
		DESCRIPTION	"0:INVALID,  1:NORMAL,  2:ALARM
					FLAG=TRAP|EVLOG|NONTC_GROBAL
					LOGITEM='TNS/PNMS CARD'
					LOGSTATUS='NORMAL(0),ALARM(1)'
					TRAP=alarmTrapPpMxIduTnsCard"
		::= { ppMxisComEntry 9 }

	ppMxisChTable OBJECT-TYPE
		SYNTAX		SEQUENCE OF PpMxisChEntry
		ACCESS		not-accessible
		STATUS		mandatory
		DESCRIPTION	"IDU Status Ch Table"
		::= { ppMxasIduStatus 2 }

	ppMxisChEntry OBJECT-TYPE
		SYNTAX		PpMxisChEntry
		ACCESS		not-accessible
		STATUS		mandatory
		DESCRIPTION	"IDU Status Ch Table Entry"
		INDEX		{
						ppMxisChPasoIndex,
						ppMxisChIndex
					}
		::= { ppMxisChTable 1 }

	PpMxisChEntry ::= SEQUENCE {
					  ppMxisChPasoIndex   IpAddress,	
					  ppMxisChIndex       INTEGER,
					  ppMxisInputLoss     NormalAlarm01Value,
					  ppMxisAisGenerated  NormalGen01Value,
					  ppMxisAisReceived   NormalRcvd01Value,
					  ppMxisOutputLoss    NormalAlarm01Value,
					  ppMxisUsageError    NormalAlarm01Value
					}

	ppMxisChPasoIndex OBJECT-TYPE
		SYNTAX		IpAddress 
		ACCESS		read-only
		STATUS		mandatory
		DESCRIPTION	"Pasolink IP Address Index"
		::= { ppMxisChEntry 1 }
		
		
	ppMxisChIndex OBJECT-TYPE
		SYNTAX		INTEGER( 1..40 )
		ACCESS		read-only
		STATUS		mandatory
		DESCRIPTION	"Index CH 
					1:CH1,2:CH2,...,40:CH40"
		::= { ppMxisChEntry 2 }

	ppMxisInputLoss OBJECT-TYPE
		SYNTAX		NormalAlarm01Value
		ACCESS		read-only
		STATUS		mandatory
		DESCRIPTION	"INPUT LOSS 0:INVALID, 1:NORMAL, 2:ALARM   
					FLAG=EVLOG
					LOGITEM='CH%d INPUT LOSS'
					LOGSTATUS='INVALID(0),NORMAL(1),ALARM(2)'
					LOGFLAG='LII_I_TABIX'
					TRAP=alarmTrapPpMxIduInputLoss"
		::= { ppMxisChEntry 3 }

	ppMxisAisGenerated OBJECT-TYPE
		SYNTAX		NormalGen01Value
		ACCESS		read-only
		STATUS		mandatory
		DESCRIPTION	"AIS GENERATED 0:INVALID, 1:NORMAL, 2:GENERATED  
					FLAG=EVLOG
					LOGITEM='CH%d AIS GENERATED'
					LOGSTATUS='INVALID(0),NORMAL(1),GENERATED(2)'
					LOGFLAG='LII_I_TABIX|LII_T_STATUS'
					TRAP=eventTrapPpMxIduAisGenerated"
		::= { ppMxisChEntry 4 }

	ppMxisAisReceived OBJECT-TYPE
		SYNTAX		NormalRcvd01Value
		ACCESS		read-only
		STATUS		mandatory
		DESCRIPTION	"AIS RECEIVED 0:INVALID, 1:NORMAL, 2:RECEIVED
					FLAG=EVLOG
					LOGITEM='CH%d AIS RECEIVED'
					LOGSTATUS='INVALID(0),NORMAL(1),RECEIVED(2)'
					LOGFLAG='LII_I_TABIX|LII_T_AIS_RCVD'
					TRAP=statusTrapPpMxAisReceived"
		::= { ppMxisChEntry 5 }

	ppMxisOutputLoss OBJECT-TYPE
		SYNTAX		NormalAlarm01Value
		ACCESS		read-only
		STATUS		mandatory
		DESCRIPTION	"OUTPUT LOSS 0:INVALID,1:NORMAL,2:ALARM   
					FLAG=EVLOG
					LOGITEM='CH%d OUTPUT LOSS'
					LOGSTATUS='INVALID(0),NORMAL(1),ALARM(2)'
					LOGFLAG='LII_I_TABIX'
					TRAP=alarmTrapPpMxIduOutputLoss"
		::= { ppMxisChEntry 6 }

	ppMxisUsageError OBJECT-TYPE
		SYNTAX		NormalAlarm01Value
		ACCESS		read-only
		STATUS		mandatory
		DESCRIPTION	"USAGE ERROR 0:INVALID, 1:NORMAL,2:ALARM   
					FLAG=TRAP|EVLOG
					LOGITEM='CH%d USAGE ERROR'
					LOGSTATUS='INVALID(0),NORMAL(1),ALARM(2)'
					LOGFLAG='LII_I_TABIX'
					TRAP=alarmTrapPpMxIduUsageError"
		::= { ppMxisChEntry 7 }

	ppMxisIndvTable OBJECT-TYPE
		SYNTAX		SEQUENCE OF PpMxisIndvEntry
		ACCESS		not-accessible
		STATUS		mandatory
		DESCRIPTION	"IDU Status No.1/No.2 Table"
		::= { ppMxasIduStatus 3 }

	ppMxisIndvEntry OBJECT-TYPE
		SYNTAX		PpMxisIndvEntry
		ACCESS		not-accessible
		STATUS		mandatory
		DESCRIPTION	"IDU Status No.1/No.2 Table Entry"
		INDEX		{
						ppMxisIndvPasoIndex,
						ppMxisIndvIndex
					}
		::= { ppMxisIndvTable 1 }

	PpMxisIndvEntry ::= SEQUENCE {
					  ppMxisIndvPasoIndex    IpAddress,
					  ppMxisIndvIndex        INTEGER,
					  ppMxisHighBerAlm       NormalAlarm01Value,
					  ppMxisLowBerAlm        NormalAlarm01Value,
					  ppMxisLof              NormalAlarm01Value,
					  ppMxisModAlm           NormalAlarm01Value,
					  ppMxisIfCableShortAlm  NormalAlarm01Value,
					  ppMxisDemAlm           NormalAlarm01Value,
					  ppMxisPsAlm            NormalAlarm01Value,
					  ppMxisModemAlm         NormalAlarm01Value
					}

	ppMxisIndvPasoIndex OBJECT-TYPE
		SYNTAX		IpAddress 
		ACCESS		read-only
		STATUS		mandatory
		DESCRIPTION	"Pasolink IP Address Index"
		::= { ppMxisIndvEntry 1 }
		
	ppMxisIndvIndex OBJECT-TYPE
		SYNTAX		INTEGER {
					  no1(1),
					  no2(2)
					}
		ACCESS		read-only
		STATUS		mandatory
		DESCRIPTION	"Index
					1:No.1, 2:No.2"
		::= { ppMxisIndvEntry 2 }

	ppMxisHighBerAlm OBJECT-TYPE
		SYNTAX		NormalAlarm01Value
		ACCESS		read-only
		STATUS		mandatory
		DESCRIPTION	"0:INVALID,  1:NORMAL,  2:ALARM 
					FLAG=TRAP|EVLOG
					LOGITEM='HIGH BER'
					LOGSTATUS='INVALID(0),NORMAL(1),ALARM(2)'
					LOGFLAG='LII_I_SYSTEM'
					TRAP=alarmTrapPpMxIduHighBerAlm"
		::= { ppMxisIndvEntry 3 }

	ppMxisLowBerAlm OBJECT-TYPE
		SYNTAX		NormalAlarm01Value
		ACCESS		read-only
		STATUS		mandatory
		DESCRIPTION	"0:INVALID,  1:NORMAL,  2:ALARM 
					FLAG=TRAP|EVLOG
					LOGITEM='LOW BER'
					LOGSTATUS='INVALID(0),NORMAL(1),ALARM(2)'
					LOGFLAG='LII_I_SYSTEM'
					TRAP=alarmTrapPpMxIduLowBerAlm"
		::= { ppMxisIndvEntry 4 }

	ppMxisLof OBJECT-TYPE
		SYNTAX		NormalAlarm01Value
		ACCESS		read-only
		STATUS		mandatory
		DESCRIPTION	"0:INVALID,  1:NORMAL,  2:ALARM 
					FLAG=TRAP|EVLOG
					LOGITEM='LOF'
					LOGSTATUS='INVALID(0),NORMAL(1),ALARM(2)'
					LOGFLAG='LII_I_SYSTEM'
					TRAP=alarmTrapPpMxIduLof"
		::= { ppMxisIndvEntry 5 }

	ppMxisModAlm OBJECT-TYPE
		SYNTAX		NormalAlarm01Value
		ACCESS		read-only
		STATUS		mandatory
		DESCRIPTION	"0:INVALID,  1:NORMAL,  2:ALRM 
					FLAG=TRAP|EVLOG
					LOGITEM='MOD'
					LOGSTATUS='INVALID(0),NORMAL(1),ALARM(2)'
					LOGFLAG='LII_I_SYSTEM'
					TRAP=alarmTrapPpMxIduModAlm"
		::= { ppMxisIndvEntry 6 }

	ppMxisIfCableShortAlm OBJECT-TYPE
		SYNTAX		NormalAlarm01Value
		ACCESS		read-only
		STATUS		mandatory
		DESCRIPTION	"0:INVALID,  1:NORMAL,  2:ALARM 
					FLAG=TRAP|EVLOG
					LOGITEM='IF CABLE SHORT'
					LOGSTATUS='INVALID(0),NORMAL(1),ALARM(2)'
					LOGFLAG='LII_I_SYSTEM'
					TRAP=alarmTrapPpMxIduIfCableShort"
		::= { ppMxisIndvEntry 7 }

	ppMxisDemAlm OBJECT-TYPE
		SYNTAX		NormalAlarm01Value
		ACCESS		read-only
		STATUS		mandatory
		DESCRIPTION	"0:INVALID,  1:NORMAL,  2:ALARM 
					FLAG=TRAP|EVLOG
					LOGITEM='DEM'
					LOGSTATUS='NORMAL(0),ALARM(1)'
					LOGFLAG='LII_I_SYSTEM'
					TRAP=alarmTrapPpMxIduDemAlm"
		::= { ppMxisIndvEntry 8 }

	ppMxisPsAlm OBJECT-TYPE
		SYNTAX		NormalAlarm01Value
		ACCESS		read-only
		STATUS		mandatory
		DESCRIPTION	"0:INVALID,  1:NORMAL,  2:ALARM 
					FLAG=TRAP|EVLOG
					LOGITEM='POWER SUPPLY'
					LOGSTATUS='INVALID(0),NORMAL(1),ALARM(2)'
					LOGFLAG='LII_I_SYSTEM|LII_I_ZERO'
					TRAP=alarmTrapPpMxIduPsAlm"
		::= { ppMxisIndvEntry 9 }

	ppMxisModemAlm OBJECT-TYPE
		SYNTAX		NormalAlarm01Value
		ACCESS		read-only
		STATUS		mandatory
		DESCRIPTION	"0:INVALID,  1:NORMAL,  2:ALARM 
					FLAG=TRAP|EVLOG
					LOGITEM='MODEM'
					LOGSTATUS='INVALID(0),NORMAL(1),ALARM(2)'
					LOGFLAG='LII_I_SYSTEM'
					TRAP=alarmTrapPpMxIduModemAlm"
		::= { ppMxisIndvEntry 10 }

	ppMxis4pLanTable OBJECT-TYPE
		SYNTAX		SEQUENCE OF PpMxis4pLanEntry
		ACCESS		not-accessible
		STATUS		mandatory
		DESCRIPTION	"4Port LAN Table"
		::= { ppMxasIduStatus 4 }

	ppMxis4pLanEntry OBJECT-TYPE
		SYNTAX		PpMxis4pLanEntry
		ACCESS		not-accessible
		STATUS		mandatory
		DESCRIPTION	"4Port LAN Table Entry"
		INDEX		{
						ppMxis4pLanPasoIndex,
						ppMxis4pLanIndex
					}
		::= { ppMxis4pLanTable 1 }

	PpMxis4pLanEntry ::= SEQUENCE {
					  ppMxis4pLanPasoIndex          IpAddress,
					  ppMxis4pLanIndex              INTEGER,
					  ppMxis4pLanLink               INTEGER,
					  ppMxis4pLanCollision          INTEGER,
					  ppMxis4pLanPortSpeedDuplex    INTEGER,
					  ppMxis4pLanLinkLosForwarding  INTEGER
					}

	ppMxis4pLanPasoIndex OBJECT-TYPE
		SYNTAX		IpAddress 
		ACCESS		read-only
		STATUS		mandatory
		DESCRIPTION	"Pasolink IP Address Index"
		::= { ppMxis4pLanEntry 1 }
		
	ppMxis4pLanIndex OBJECT-TYPE
		SYNTAX		INTEGER {
					  port1(1),
					  port2(2),
					  port3(3),
					  port4(4)
					}
		ACCESS		read-only
		STATUS		mandatory
		DESCRIPTION	"4P LAN INDEX"
		::= { ppMxis4pLanEntry 2 }

	ppMxis4pLanLink OBJECT-TYPE
		SYNTAX		INTEGER ( 0..2 )
		ACCESS		read-only
		STATUS		mandatory
		DESCRIPTION	"PORTx LINK(4P) 0:INVALID, 1:LINK,  2:ALARM
					FLAG=TRAP|EVLOG|NONTC_BT
					LOGITEM='PORT%d LINK(4P)'
					LOGSTATUS='INVALID(0),LINK(1),ALARM(2)'
					LOGFLAG='LII_I_TABIX'
					TRAP=alarmTrapPpMxIdu4pLanLink"
		::= { ppMxis4pLanEntry 3 }

	ppMxis4pLanCollision OBJECT-TYPE
		SYNTAX		INTEGER ( 0..2 )
		ACCESS		read-only
		STATUS		mandatory
		DESCRIPTION	"PORTx COLLISION(4P) 0:INVALID, 1:NORMAL,  2:COLLISION
					FLAG=TRAP|EVLOG|NONTC_BT
					LOGITEM='PORT%d COLLISION(4P)'
					LOGSTATUS='INVALID(0),NORMAL(1),COLLISION(2)'
					LOGFLAG='LII_I_TABIX|LII_T_STATUS'
					TRAP=eventTrapPpMxIdu4pLanCollision"
		::= { ppMxis4pLanEntry 4 }

	ppMxis4pLanPortSpeedDuplex OBJECT-TYPE
		SYNTAX		INTEGER
		ACCESS		read-only
		STATUS		mandatory
		DESCRIPTION	"PORT SPEED & DUPLEX(4P)
					0:INVALID
					1:10M-HALF(MDI)
					2:10M-FULL(MDI)
					3:100M-HALF(MDI)
					4:100M-FULL(MDI)
					5:10M-HALF(MDIX)
					6:10M-FULL(MDIX)
					7:100M-HALF(MDIX)
					8:100M-FULL(MDIX)
					
					FLAG=TRAP|EVLOG|NONTC_BT
					LOGITEM='PORT%d SPEED & DUPLEX(4P)'
					LOGSTATUS='INVALID(0),10M-HALF(MDI)(1),10M-FULL(MDI)(2),100M-HALF(MDI)(3),100M-FULL(MDI)(4),10M-HALF(MDIX)(5),10M-FULL(MDIX)(6),100M-HALF(MDIX)(7),100M-FULL(MDIX)(8)'
					LOGFLAG='LII_I_TABIX'
					TRAP=eventTrapPpMxIdu4pLanPortSpeedDuplex"
		::= { ppMxis4pLanEntry 5 }

	ppMxis4pLanLinkLosForwarding OBJECT-TYPE
		SYNTAX		INTEGER ( 0..2 )
		ACCESS		read-only
		STATUS		mandatory
		DESCRIPTION	"PORTx LINK LOSS FORWARDING 0:INVALID,  1:NORMAL,  2:UNDER EXECUTION
					FLAG=TRAP|EVLOG|NONTC_BT
					LOGITEM='PORT%d LINK LOSS FORWARDING(4P)'
					LOGSTATUS='INVALID(0), NORMAL(1), UNDER EXECUTION(2)'
					LOGFLAG='LII_I_TABIX|LII_T_STATUS'
					TRAP=eventTrapPpMxIdu4pLanLinkLosForwarding"
		::= { ppMxis4pLanEntry 6 }

	ppMxis2pLanTable OBJECT-TYPE
		SYNTAX		SEQUENCE OF PpMxis2pLanEntry
		ACCESS		not-accessible
		STATUS		mandatory
		DESCRIPTION	"2Port LAN Table"
		::= { ppMxasIduStatus 5 }

	ppMxis2pLanEntry OBJECT-TYPE
		SYNTAX		PpMxis2pLanEntry
		ACCESS		not-accessible
		STATUS		mandatory
		DESCRIPTION	"2Port LAN Table Entry"
		INDEX		{
						ppMxis2pLanPasoIndex,
						ppMxis2pLanIndex
					}
		::= { ppMxis2pLanTable 1 }

	PpMxis2pLanEntry ::= SEQUENCE {
					  ppMxis2pLanPasoIndex          IpAddress, 
					  ppMxis2pLanIndex              INTEGER,
					  ppMxis2pLanLink               INTEGER,
					  ppMxis2pLanCollision          INTEGER,
					  ppMxis2pLanPortSpeedDuplex    INTEGER,
					  ppMxis2pLanLinkLosForwarding  INTEGER
					}

	ppMxis2pLanPasoIndex OBJECT-TYPE
		SYNTAX		IpAddress 
		ACCESS		read-only
		STATUS		mandatory
		DESCRIPTION	"Pasolink IP Address Index"
		::= { ppMxis2pLanEntry 1 }
		
	ppMxis2pLanIndex OBJECT-TYPE
		SYNTAX		INTEGER {
					  port1(1),
					  port2(2)
					}
		ACCESS		read-only
		STATUS		mandatory
		DESCRIPTION	"2P LAN INDEX"
		::= { ppMxis2pLanEntry 2 }

	ppMxis2pLanLink OBJECT-TYPE
		SYNTAX		INTEGER ( 0..2 )
		ACCESS		read-only
		STATUS		mandatory
		DESCRIPTION	"PORTx LINK(2P) 0:INVALID,  1:LINK,  2:ALARM
					FLAG=TRAP|EVLOG
					LOGITEM='PORT%d LINK(2P)'
					LOGSTATUS='INVALID(0),LINK(1),ALARM(2)'
					LOGFLAG='LII_I_TABIX'
					TRAP=alarmTrapPpMxIdu2pLanLink"
		::= { ppMxis2pLanEntry 3 }

	ppMxis2pLanCollision OBJECT-TYPE
		SYNTAX		INTEGER ( 0..2 )
		ACCESS		read-only
		STATUS		mandatory
		DESCRIPTION	"PORTx COLLISION(2P) 0:INVALID,  1:NORMAL,  2:COLLISION
					FLAG=TRAP|EVLOG
					LOGITEM='PORT%d COLLISION(2P)'
					LOGSTATUS='INVALID(0),NORMAL(1),COLLISION(2)'
					LOGFLAG='LII_I_TABIX|LII_T_STATUS'
					TRAP=eventTrapPpMxIdu2pLanCollision"
		::= { ppMxis2pLanEntry 4 }

	ppMxis2pLanPortSpeedDuplex OBJECT-TYPE
		SYNTAX		INTEGER
		ACCESS		read-only
		STATUS		mandatory
		DESCRIPTION	"PORT SPEED & DUPLEX(2P)
					0:INVALID
					1:10M-HALF(MDI)
					2:10M-FULL(MDI)
					3:100M-HALF(MDI)
					4:100M-FULL(MDI)
					5:10M-HALF(MDIX)
					6:10M-FULL(MDIX)
					7:100M-HALF(MDIX)
					8:100M-FULL(MDIX)
					FLAG=TRAP|EVLOG
					LOGITEM='PORT%d SPEED & DUPLEX(2P)'
					LOGSTATUS='INVALID(0),10M-HALF(MDI)(1),10M-FULL(MDI)(2),100M-HALF(MDI)(3),100M-FULL(MDI)(4),10M-HALF(MDIX)(5),10M-FULL(MDIX)(6),100M-HALF(MDIX)(7),100M-FULL(MDIX)(8)'
					LOGFLAG='LII_I_TABIX'
					TRAP=eventTrapPpMxIdu2pLanPortSpeedDuplex"
		::= { ppMxis2pLanEntry 5 }

	ppMxis2pLanLinkLosForwarding OBJECT-TYPE
		SYNTAX		INTEGER ( 0..2 )
		ACCESS		read-only
		STATUS		mandatory
		DESCRIPTION	"PORTx LINK LOSS FORWARDING 0:INVALID,  1:NORMAL,  2:UNDER EXECUTION
					FLAG=TRAP|EVLOG
					LOGITEM='PORT%d LINK LOSS FORWARDING(2P)'
					LOGSTATUS='INVALID(0), NORMAL(1), UNDER EXECUTION(2)'
					LOGFLAG='LII_I_TABIX|LII_T_STATUS'
					TRAP=eventTrapPpMxIdu2pLanLinkLosForwarding"
		::= { ppMxis2pLanEntry 6 }


-----------------------------------------------
-- ppMxEquipmentConfigInfo Group Definitions
-----------------------------------------------

	ppMxeciIndvTable OBJECT-TYPE
		SYNTAX		SEQUENCE OF PpMxeciIndvEntry
		ACCESS		not-accessible
		STATUS		mandatory
		DESCRIPTION	"Equipment Config No.1/No.2 Table"
		::= { ppMxEquipmentConfigInfo 1 }

	ppMxeciIndvEntry OBJECT-TYPE
		SYNTAX		PpMxeciIndvEntry
		ACCESS		not-accessible
		STATUS		mandatory
		DESCRIPTION	"Equipment Config No.1/No.2 Table Entry"
		INDEX		{
						ppMxeciIndvPasoIndex,
						ppMxeciIndvIndex
					}
		::= { ppMxeciIndvTable 1 }

	PpMxeciIndvEntry ::= SEQUENCE {
					  ppMxeciIndvPasoIndex  IpAddress,
					  ppMxeciIndvIndex      INTEGER,
					  ppMxeciFrameId        INTEGER
					}

	ppMxeciIndvPasoIndex OBJECT-TYPE
		SYNTAX		IpAddress 
		ACCESS		read-only
		STATUS		mandatory
		DESCRIPTION	"Pasolink IP Address Index"
		::= { ppMxeciIndvEntry 1 }
		
	ppMxeciIndvIndex OBJECT-TYPE
		SYNTAX		INTEGER {
					  no1(1),
					  no2(2)
					}
		ACCESS		read-only
		STATUS		mandatory
		DESCRIPTION	"Index
					1:No.1, 2:No.2"
		::= { ppMxeciIndvEntry 2 }

	ppMxeciFrameId OBJECT-TYPE
		SYNTAX		INTEGER
		ACCESS		read-only
		STATUS		mandatory
		DESCRIPTION	"1:ID1, 2:ID2, .. 32:ID32
					0:Invalid
					FLAG=BITCNT(8)"
		::= { ppMxeciIndvEntry 3 }

	ppMxeciCmnInfo OBJECT IDENTIFIER
		::= { ppMxEquipmentConfigInfo 2 }

	ppMxeciCmnTable OBJECT-TYPE
		SYNTAX		SEQUENCE OF PpMxeciCmnEntry
		ACCESS		not-accessible
		STATUS		optional
		DESCRIPTION	"Equipment Config Common Table"
		::= { ppMxeciCmnInfo 1 }

	ppMxeciCmnEntry OBJECT-TYPE
		SYNTAX		PpMxeciCmnEntry
		ACCESS		not-accessible
		STATUS		optional
		DESCRIPTION	"Equipment Config Common Table Entry"
		INDEX		{
					ppMxeciCmnPasoIndex
					}
		::= { ppMxeciCmnTable 1 }

	PpMxeciCmnEntry ::= SEQUENCE {
					  ppMxeciCmnPasoIndex             IpAddress,	
					  ppMxeciSystemConfiguration      INTEGER,
					  ppMxeciTxPwrCtrl                INTEGER,
					  ppMxeciTransmissionCapacity     INTEGER,
					  ppMxeciIntfcModuleConfiguration INTEGER,
					  ppMxeciModulation               INTEGER,
					  ppMxeciOduType                  INTEGER
					 }					  
					         
	ppMxeciCmnPasoIndex OBJECT-TYPE
		SYNTAX		IpAddress 
		ACCESS		read-only
		STATUS		mandatory
		DESCRIPTION	"Pasolink IP Address Index"
		::= { ppMxeciCmnEntry 1 }
		
	ppMxeciSystemConfiguration OBJECT-TYPE
		SYNTAX		INTEGER ( 1..6 )
					
		ACCESS		read-only
		STATUS		mandatory
		DESCRIPTION	"1:1+0(BT 4*2M),
					2:1+0(BT 20*2M),
					3:1+0, 
					4:HS(1+1),
					5:TWIN PATH (1+1)
					6:1+0(Expandable), 
					FLAG=BITCNT(8)"
		::= { ppMxeciCmnEntry 2 }

	ppMxeciTxPwrCtrl OBJECT-TYPE
		SYNTAX		INTEGER {
					  mtpc(1),
					  atpc(2)
					}
		ACCESS		read-only
		STATUS		mandatory
		DESCRIPTION	"1:MTPC, 2:ATPC
					FLAG=BITCNT(8)"
		::= { ppMxeciCmnEntry 3 }

	ppMxeciTransmissionCapacity OBJECT-TYPE
		SYNTAX		INTEGER ( 1..5 )
		ACCESS		read-only
		STATUS		mandatory
		DESCRIPTION	"TRANSMISSION CAPACITY
					1:10 Mbps
					2:20 Mbps
					3:40 Mbps
					4:80 Mbps
					5:10 Mbps(FIX)
					FLAG=BITCNT(8)"
		::= { ppMxeciCmnEntry 4 }

	ppMxeciIntfcModuleConfiguration OBJECT-TYPE
		SYNTAX		INTEGER ( 0..13 )
		ACCESS		read-only
		STATUS		mandatory
		DESCRIPTION	"INTFC MODULE CONFIGURATION
					
					0:INVALID
					1:2M INTFC-M(32*2M) + BLANK
					2:2M INTFC-M(32*2M) + 2M INTFC-S
					3:2M INTFC-M(32*2M) + LAN INTFC-S
					4:BLANK + LAN INTFC-S
					5:LAN INTFC-M + BLANK
					6:LAN INTFC-M + 2M INTFC-S
					7:LAN INTFC-M + LAN INTFC-S
					8:2M INTFC-M(20*2M) + BLANK
					9:2M INTFC-M(20*2M) + LAN INTFC-S
					10:TNS CARD + BLANK
					11:TNS CARD + LAN INTFC-S
					12:PNMS CARD + BLANK
					13:PNMS CARD + LAN INTFC-S
					
					FLAG=BITCNT(8)"
		::= { ppMxeciCmnEntry 5 }

	ppMxeciModulation OBJECT-TYPE
		SYNTAX		INTEGER ( 1..2 )
		ACCESS		read-only
		STATUS		mandatory
		DESCRIPTION	"MODULATION
					1:QPSK
					2:16QAM
					
					FLAG=BITCNT(8)"
		::= { ppMxeciCmnEntry 6 }

	ppMxeciOduType OBJECT-TYPE
		SYNTAX		INTEGER ( 1..9 )
		ACCESS		read-only
		STATUS		mandatory
		DESCRIPTION	"ODU TYPE
					1:PASO TYPE
					2:PASO+ TYPE-1
					3:PASO+ TYPE-2
					4:PASO+ TYPE-3
					5:PASO+ TYPE-4
					6:PASO+ TYPE-5
					7:PASO+ TYPE-6
					8:PASO+ TYPE-7
					9:PASO+ TYPE-8
					
					FLAG=BITCNT(8)"
		::= { ppMxeciCmnEntry 7 }

	ppMxeciLanInfo OBJECT IDENTIFIER
		::= { ppMxEquipmentConfigInfo 3 }

	ppMxeci2MLanUsageTable OBJECT-TYPE
		SYNTAX		SEQUENCE OF PpMxeci2MLanUsageEntry
		ACCESS		not-accessible
		STATUS		mandatory
		DESCRIPTION	"Equipment Config 2M(E1)/ LAN Usage Table"
		::= { ppMxeciLanInfo 1 }

	ppMxeci2MLanUsageEntry OBJECT-TYPE
		SYNTAX		PpMxeci2MLanUsageEntry
		ACCESS		not-accessible
		STATUS		mandatory
		DESCRIPTION	"Equipment Config 2M(E1)/ LAN Usage Table Entry"
		INDEX		{
						ppMxeci2MLanUsagePasoIndex,
						ppMxeci2MLanUsageIndex
					}
		::= { ppMxeci2MLanUsageTable 1 }

	PpMxeci2MLanUsageEntry ::= SEQUENCE {
					  ppMxeci2MLanUsagePasoIndex IpAddress,
					  ppMxeci2MLanUsageIndex     INTEGER,
					  ppMxeci2MLanUsage          INTEGER 
					}

	ppMxeci2MLanUsagePasoIndex OBJECT-TYPE
		SYNTAX		IpAddress 
		ACCESS		read-only
		STATUS		mandatory
		DESCRIPTION	"Pasolink IP Address Index"
		::= { ppMxeci2MLanUsageEntry 1 }
		
			ppMxeci2MLanUsageIndex OBJECT-TYPE
		SYNTAX		INTEGER {
					  usage1(1),
					  usage2(2),
					  usage3(3),
					  usage4(4),
					  usage5(5)
					}
		ACCESS		read-only
		STATUS		mandatory
		DESCRIPTION	"2MLan INDEX
					1:32*2M USAGE (2M INTFC-M)
					2:8*2M USAGE (2M INTFC-S)
					3:20*2M USAGE (2M INTFC-M)
					4:4*2M USAGE
					5:20*2M USAGE
					"
		::= { ppMxeci2MLanUsageEntry 2 }

	ppMxeci2MLanUsage OBJECT-TYPE
		SYNTAX		INTEGER 
		ACCESS		read-only
		STATUS		mandatory
		DESCRIPTION	"2M / LAN USAGE
					1:USED 2:NOT USED
					This MIB is not Used(Reserved). value is 0 fixed.
					
					FLAG=BITCNT(8)|CMNBIT"
		::= { ppMxeci2MLanUsageEntry 3 }


	ppMxeci4PortLanTable OBJECT-TYPE
		SYNTAX		SEQUENCE OF PpMxeci4PortLanEntry
		ACCESS		not-accessible
		STATUS		optional
		DESCRIPTION	"Equipment Config 4Port LAN Table"
		::= { ppMxeciLanInfo 2  }

	ppMxeci4PortLanEntry OBJECT-TYPE
		SYNTAX		PpMxeci4PortLanEntry
		ACCESS		not-accessible
		STATUS		optional
		DESCRIPTION	"Equipment Config 4Port LAN Table Entry"
		INDEX		{
					ppMxeci4PortLanPasoIndex
					}
		::= { ppMxeci4PortLanTable 1 }

	PpMxeci4PortLanEntry ::= SEQUENCE {
					  ppMxeci4PortLanPasoIndex    IpAddress,	
					  ppMxeci4PortLanUsage        INTEGER,
					  ppMxeci4PortLanRadioMapping INTEGER,
					  ppMxeci4PortLan2MCapacity   INTEGER
					 }					  
					         
	ppMxeci4PortLanPasoIndex OBJECT-TYPE
		SYNTAX		IpAddress 
		ACCESS		read-only
		STATUS		mandatory
		DESCRIPTION	"Pasolink IP Address Index"
		::= { ppMxeci4PortLanEntry 1 }
		
	ppMxeci4PortLanUsage OBJECT-TYPE
		SYNTAX		INTEGER 
		ACCESS		read-only
		STATUS		mandatory
		DESCRIPTION	"4PORT LAN USAGE (LAN INTFC-M)
					1:USED 2:NOT USED
					This MIB is not Used(Reserved). value is 0 fixed.
					FLAG=BITCNT(8)"
		::= { ppMxeci4PortLanEntry 2 }

	ppMxeci4PortLanRadioMapping OBJECT-TYPE
		SYNTAX		INTEGER ( 0..4 )
		ACCESS		read-only
		STATUS		mandatory
		DESCRIPTION	"4PORT LAN >> RADIO MAPPING
					0:INVALID
					1:PORT1-4 SHARED/ 1PORT ONLY
					2:PORT1-2 SHARED, PORT3-4 SHARED
					3:PORT1-4 SEPARATED
					4:NOT USED
					
					FLAG=BITCNT(8)"
		::= { ppMxeci4PortLanEntry 3 }

	ppMxeci4PortLan2MCapacity OBJECT-TYPE
		SYNTAX		INTEGER ( 0..80 )
		ACCESS		read-only
		STATUS		mandatory
		DESCRIPTION	"4PORT LAN & 2M CAPACITY
					0:0Mbps-80:80Mbps
					FLAG=BITCNT(8)"
		::= { ppMxeci4PortLanEntry 4 }

	ppMxeci2PortLanTable OBJECT-TYPE
		SYNTAX		SEQUENCE OF PpMxeci2PortLanEntry
		ACCESS		not-accessible
		STATUS		optional
		DESCRIPTION	"Equipment Config 4Port LAN Table"
		::= { ppMxeciLanInfo 3  }

	ppMxeci2PortLanEntry OBJECT-TYPE
		SYNTAX		PpMxeci2PortLanEntry
		ACCESS		not-accessible
		STATUS		optional
		DESCRIPTION	"Equipment Config 4Port LAN Table Entry"
		INDEX		{
					ppMxeci2PortLanPasoIndex
					}
		::= { ppMxeci2PortLanTable 1 }

	PpMxeci2PortLanEntry ::= SEQUENCE {
					  ppMxeci2PortLanPasoIndex     IpAddress,	
					  ppMxeci2PortLanUsage         INTEGER,
					  ppMxeci2PortLanRadioMapping  INTEGER,
					  ppMxeci2PortLan2MCapacity    INTEGER,
					  ppMxeci2PortLanScAssignment  INTEGER
					 }					  
					         
	ppMxeci2PortLanPasoIndex OBJECT-TYPE
		SYNTAX		IpAddress 
		ACCESS		read-only
		STATUS		mandatory
		DESCRIPTION	"Pasolink IP Address Index"
		::= { ppMxeci2PortLanEntry 1 }
		
	ppMxeci2PortLanUsage OBJECT-TYPE
		SYNTAX		INTEGER
		ACCESS		read-only
		STATUS		mandatory
		DESCRIPTION	"2PORT LAN USAGE (LAN INTFC-S)
					1:USED 2:NOT USED
					This MIB is not Used(Reserved). value is 0 fixed.
					FLAG=BITCNT(8)"
		::= { ppMxeci2PortLanEntry 2 }
  
	ppMxeci2PortLanRadioMapping OBJECT-TYPE
		SYNTAX		INTEGER ( 0..5 )
		ACCESS		read-only
		STATUS		mandatory
		DESCRIPTION	"2PORT LAN >> RADIO MAPPING
					0:INVALID
					1:PORT1-2 SHARED/ 1PORT ONLY(MAIN)
					2:PORT1-2 SEPARATED(MAIN)
					3:PORT1-2 SHARED/ 1PORT ONLY(SC)
					4:PORT1(MAIN), PORT2(SC)
					5:NOT USED
					FLAG=BITCNT(8)"
		::= { ppMxeci2PortLanEntry 3 }
      
	ppMxeci2PortLan2MCapacity OBJECT-TYPE
		SYNTAX		INTEGER ( 0..80 )
		ACCESS		read-only
		STATUS		mandatory
		DESCRIPTION	"2PORT LAN & 2M CAPACITY
					0:0Mbps-80:80Mbps
					FLAG=BITCNT(8)"
		::= { ppMxeci2PortLanEntry 4 }
  
	ppMxeci2PortLanScAssignment OBJECT-TYPE
		SYNTAX		INTEGER ( 0..2 )
		ACCESS		read-only
		STATUS		mandatory
		DESCRIPTION	"2PORT LAN & SC ASSIGNMENT
					0:INVALID
					1:P1-P2/1P= 64K
					2:P1-P2/1P=128K
					FLAG=BITCNT(8)"
		::= { ppMxeci2PortLanEntry 5 }

-----------------------------------------------
-- ppMxProvisioningInfo Group Definitions
-----------------------------------------------

	ppMxpdiBerInfo OBJECT IDENTIFIER
		::= { ppMxProvisioningInfo 1 }

	ppMxpdiBerTable OBJECT-TYPE
		SYNTAX		SEQUENCE OF PpMxpdiBerEntry
		ACCESS		not-accessible
		STATUS		mandatory
		DESCRIPTION	"BER Table"
		::= { ppMxpdiBerInfo 1 }

	ppMxpdiBerEntry OBJECT-TYPE
		SYNTAX		PpMxpdiBerEntry
		ACCESS		not-accessible
		STATUS		mandatory
		DESCRIPTION	"BER Table Entry"
		INDEX		{
						ppMxpdiBerPasoIndex,
						ppMxpdiBerIndex
					}
		::= { ppMxpdiBerTable 1 }

	PpMxpdiBerEntry ::= SEQUENCE {
					  ppMxpdiBerPasoIndex      IpAddress,
					  ppMxpdiBerIndex          INTEGER,
					  ppMxpdiBerThreshold      INTEGER
					}

	ppMxpdiBerPasoIndex OBJECT-TYPE
		SYNTAX		IpAddress 
		ACCESS		read-only
		STATUS		mandatory
		DESCRIPTION	"Pasolink IP Address Index"
		::= { ppMxpdiBerEntry 1 }
		
	ppMxpdiBerIndex OBJECT-TYPE
		SYNTAX		INTEGER(1..2)
		ACCESS		read-only
		STATUS		mandatory
		DESCRIPTION	"BerIndex
					  high-ber(1),
					  low-ber(2)"
		::= { ppMxpdiBerEntry 2 }

	ppMxpdiBerThreshold OBJECT-TYPE
		SYNTAX		INTEGER
		ACCESS		read-only
		STATUS		mandatory
		DESCRIPTION	"BER THRESHOLD
					0x00:NOT USED
					0x34:3E-4(high-ber only)
					0x35:3E-5(high-ber only)
					0x36:3E-6
					0x37:3E-7(low-ber only)
					0x38:3E-8(low-ber only)
					0x39:3E-9(low-ber only)
					0xFF:EARLY WARNING(low-ber only)
					FLAG=TRAP|EVLOG|BITCNT(8)|CMNBIT
					LOGITEM='%s'
					LOGSTATUS='%s'
					LOGFLAG='LII_I_BER_NAME|LII_S_BER'
					TRAP=eventTrapPpMxBerThreshold"
		::= { ppMxpdiBerEntry 3 }

	ppMxpdiAisActivationTable OBJECT-TYPE
		SYNTAX		SEQUENCE OF PpMxpdiAisActivationEntry
		ACCESS		not-accessible
		STATUS		optional
		DESCRIPTION	"AIS Activation Table"
		::= { ppMxpdiBerInfo 2 }

	ppMxpdiAisActivationEntry OBJECT-TYPE
		SYNTAX		PpMxpdiAisActivationEntry
		ACCESS		not-accessible
		STATUS		optional
		DESCRIPTION	"AIS Activation Table Entry"
		INDEX		{
					ppMxpdiAisActivationPasoIndex
					}
		::= { ppMxpdiAisActivationTable 1 }

	PpMxpdiAisActivationEntry ::= SEQUENCE {
					  ppMxpdiAisActivationPasoIndex    IpAddress,
					  ppMxpdiAisActivationCondition    INTEGER
					 }					  
					         
	ppMxpdiAisActivationPasoIndex OBJECT-TYPE
		SYNTAX		IpAddress 
		ACCESS		read-only
		STATUS		mandatory
		DESCRIPTION	"Pasolink IP Address Index"
		::= { ppMxpdiAisActivationEntry 1 }

	ppMxpdiAisActivationCondition OBJECT-TYPE
		SYNTAX		INTEGER ( 0..2 )
		ACCESS		read-only
		STATUS		mandatory
		DESCRIPTION	"AIS ACTIVATION CONDITION
					0:INVALID 1:LOF+HIGH BER 2:LOF
					FLAG=TRAP|EVLOG|BITCNT(8)
					LOGITEM='AIS ACTIVATION CONDITION'
					LOGSTATUS='LOF+HIGH BER(1),LOF(2)'
					LOGFLAG='LII_I_INVALID_HIDE'
					TRAP=eventTrapPpMxAisActivationCondition"
		::= { ppMxpdiAisActivationEntry 2 }

	ppMxpdiClusterAlarmTable OBJECT-TYPE
		SYNTAX		SEQUENCE OF PpMxpdiClusterAlarmEntry
		ACCESS		not-accessible
		STATUS		optional
		DESCRIPTION	"CLUSTER ALARM information table"
		::= { ppMxpdiBerInfo 3 }

	ppMxpdiClusterAlarmEntry OBJECT-TYPE
		SYNTAX		PpMxpdiClusterAlarmEntry
		ACCESS		not-accessible
		STATUS		optional
		DESCRIPTION	"CLUSTER ALARM information table entry"
		INDEX		{
					ppMxpdiClusterAlarmPasoIndex,
					ppMxpdiClusterAlarmIndex
					}
		::= { ppMxpdiClusterAlarmTable 1 }

	PpMxpdiClusterAlarmEntry ::= SEQUENCE {
					  ppMxpdiClusterAlarmPasoIndex    IpAddress,	
					  ppMxpdiClusterAlarmIndex        INTEGER,
					  ppMxpdiClusterAlarmUsage        INTEGER
					 }					  
					         
	ppMxpdiClusterAlarmPasoIndex OBJECT-TYPE
		SYNTAX		IpAddress 
		ACCESS		read-only
		STATUS		mandatory
		DESCRIPTION	"Pasolink IP Address index"
		::= { ppMxpdiClusterAlarmEntry 1 }

	ppMxpdiClusterAlarmIndex OBJECT-TYPE
		SYNTAX		INTEGER ( 1..2 )
		ACCESS		read-only
		STATUS		mandatory
		DESCRIPTION	"ClusterAlarmIndex
					  1,2"
		::= { ppMxpdiClusterAlarmEntry 2 }
		
	ppMxpdiClusterAlarmUsage OBJECT-TYPE
		SYNTAX		INTEGER
		ACCESS		read-only
		STATUS		mandatory
		DESCRIPTION	"CLUSTER ALARM SETTING
					0:INVALID 1:ENABLED,2:DISABLED,
					FLAG=TRAP|EVLOG|BITCNT(8)|CMNBIT
					LOGITEM='CLUSTER ALARM%d SETTING'
					LOGSTATUS='ENABLED(1), DISABLED(2)'
					LOGFLAG='LII_I_INVALID_HIDE|LII_I_TABIX'
					TRAP=eventTrapPpMxClusterAlarmUsage"
		::= { ppMxpdiClusterAlarmEntry 3 }

	ppMxpdiTcnInfo OBJECT IDENTIFIER
		::= { ppMxProvisioningInfo 2 }

	ppMxpdiTcnTable OBJECT-TYPE
		SYNTAX		SEQUENCE OF PpMxpdiTcnEntry
		ACCESS		not-accessible
		STATUS		mandatory
		DESCRIPTION	"TCN Table"
		::= { ppMxpdiTcnInfo 1 }

	ppMxpdiTcnEntry OBJECT-TYPE
		SYNTAX		PpMxpdiTcnEntry
		ACCESS		not-accessible
		STATUS		mandatory
		DESCRIPTION	"TCN Table Entry"
		INDEX		{
						ppMxpdiTcnPasoIndex,
						ppMxpdiTcnItemName
					}
		::= { ppMxpdiTcnTable 1 }

	PpMxpdiTcnEntry ::= SEQUENCE {
					  ppMxpdiTcnPasoIndex      IpAddress,
					  ppMxpdiTcnItemName       INTEGER,
					  ppMxpdiTcnDailyOccur     INTEGER,
					  ppMxpdiTcnDailyRecover   INTEGER,
					  ppMxpdiTcnWeeklyOccur    INTEGER,
					  ppMxpdiTcnWeeklyRecover  INTEGER
					}
					
	ppMxpdiTcnPasoIndex OBJECT-TYPE
		SYNTAX		IpAddress 
		ACCESS		read-only
		STATUS		mandatory
		DESCRIPTION	"Pasolink IP Address Index"
		::= { ppMxpdiTcnEntry 1 }
		
	ppMxpdiTcnItemName OBJECT-TYPE
		SYNTAX		INTEGER {
					  tcnOFS(1),
					  tcnES(2),
					  tcnSES(3),
					  tcnUAS(4),
					  tcnBBE(5)
					}
		ACCESS		read-only
		STATUS		mandatory
		DESCRIPTION	"TCN NAME"
		::= { ppMxpdiTcnEntry 2 }

	ppMxpdiTcnDailyOccur OBJECT-TYPE
		SYNTAX		INTEGER
		ACCESS		read-only
		STATUS		mandatory
		DESCRIPTION	"PMON Threshold: Daily.Occur
					
					
					FLAG=TRAP|EVLOG|BITCNT(32)|CMNBIT
					LOGITEM='%s THRESHOLD(15min)OCCURRED'
					LOGSTATUS='%d'
					LOGFLAG='LII_I_PMON_NAME_TOTAL|LII_S_DEC|LII_T_TCN'
					TRAP=eventTrapPpMxTcnDailyOccur"
		::= { ppMxpdiTcnEntry 3 }

	ppMxpdiTcnDailyRecover OBJECT-TYPE
		SYNTAX		INTEGER
		ACCESS		read-only
		STATUS		mandatory
		DESCRIPTION	"PMON Threshold: Daily.Recover
					
					
					FLAG=TRAP|EVLOG|BITCNT(32)|CMNBIT
					LOGITEM='%s THRESHOLD(15min)RECOVERED'
					LOGSTATUS='%d'
					LOGFLAG='LII_I_PMON_NAME_TOTAL|LII_S_DEC|LII_T_TCN'
					TRAP=eventTrapPpMxTcnDailyRecover"
		::= { ppMxpdiTcnEntry 4 }

	ppMxpdiTcnWeeklyOccur OBJECT-TYPE
		SYNTAX		INTEGER
		ACCESS		read-only
		STATUS		mandatory
		DESCRIPTION	"PMON Threshold: weekly.occur
					
					
					FLAG=TRAP|EVLOG|BITCNT(32)|CMNBIT
					LOGITEM='%s THRESHOLD(1day)OCCURRED'
					LOGSTATUS='%d'
					LOGFLAG='LII_I_PMON_NAME_TOTAL|LII_S_DEC|LII_T_TCN'
					TRAP=eventTrapPpMxTcnWeeklyOccur"
		::= { ppMxpdiTcnEntry 5 }

	ppMxpdiTcnWeeklyRecover OBJECT-TYPE
		SYNTAX		INTEGER
		ACCESS		read-only
		STATUS		mandatory
		DESCRIPTION	"PMON Threshold: weekly.Recover
					
					
					FLAG=TRAP|EVLOG|BITCNT(32)|CMNBIT
					LOGITEM='%s THRESHOLD(1day)RECOVERED'
					LOGSTATUS='%d'
					LOGFLAG='LII_I_PMON_NAME_TOTAL|LII_S_DEC|LII_T_TCN'
					TRAP=eventTrapPpMxTcnWeeklyRecover"
		::= { ppMxpdiTcnEntry 6 }

	ppMxpdiTxPwrCtrl OBJECT IDENTIFIER
		::= { ppMxProvisioningInfo 3 }

	ppMxpdiTxPwrCtrlIndvTable OBJECT-TYPE
		SYNTAX		SEQUENCE OF PpMxpdiTxPwrCtrlIndvEntry
		ACCESS		not-accessible
		STATUS		mandatory
		DESCRIPTION	"TX Power Ctrl No.1/No.2 Table"
		::= { ppMxpdiTxPwrCtrl 1 }

	ppMxpdiTxPwrCtrlIndvEntry OBJECT-TYPE
		SYNTAX		PpMxpdiTxPwrCtrlIndvEntry
		ACCESS		not-accessible
		STATUS		mandatory
		DESCRIPTION	"TX Power Ctrl No.1/No.2 Table Entry"
		INDEX		{
						ppMxpdiTxPwrCtrlIndvPasoIndex,
						ppMxpdiTxPwrCtrlIndvIndex
					}
		::= { ppMxpdiTxPwrCtrlIndvTable 1 }

	PpMxpdiTxPwrCtrlIndvEntry ::= SEQUENCE {
					  ppMxpdiTxPwrCtrlIndvPasoIndex     IpAddress,
					  ppMxpdiTxPwrCtrlIndvIndex         INTEGER,
					  ppMxpdiTxPwrCtrlAtpcMax           INTEGER,
					  ppMxpdiTxPwrCtrlAtpcMin           INTEGER,
					  ppMxpdiTxPwrCtrlMtpcTxPower       INTEGER,
					  ppMxpdiTxPwrCtrlRxThresholdLevel  INTEGER,
					  ppMxpdiTxPwrCtrlAdditionalAtt     INTEGER
					}

	ppMxpdiTxPwrCtrlIndvPasoIndex OBJECT-TYPE
		SYNTAX		IpAddress 
		ACCESS		read-only
		STATUS		mandatory
		DESCRIPTION	"Pasolink IP Address Index"
		::= { ppMxpdiTxPwrCtrlIndvEntry 1 }
		
	ppMxpdiTxPwrCtrlIndvIndex OBJECT-TYPE
		SYNTAX		INTEGER {
					  no1(1),
					  no2(2)
					}
		ACCESS		read-only
		STATUS		mandatory
		DESCRIPTION	"Index
					1:No.1, 2:No.2"
		::= { ppMxpdiTxPwrCtrlIndvEntry 2 }

	ppMxpdiTxPwrCtrlAtpcMax OBJECT-TYPE
		SYNTAX		INTEGER
		ACCESS		read-only
		STATUS		mandatory
		DESCRIPTION	"Range is ppMxiviOduProvAtpcMax,ppMxiviOduProvAtpcMin
					
					FLAG=TRAP|EVLOG|BITCNT(8)
					LOGITEM='ATPC (MAX) [dB]'
					LOGSTATUS='%d'
					LOGFLAG='LII_S_DEC|LII_I_SYSTEM'
					TRAP=eventTrapPpMxAtpcMax"
		::= { ppMxpdiTxPwrCtrlIndvEntry 3 }

	ppMxpdiTxPwrCtrlAtpcMin OBJECT-TYPE
		SYNTAX		INTEGER
		ACCESS		read-only
		STATUS		mandatory
		DESCRIPTION	"Range is ppMxiviOduProvAtpcMax,ppMxiviOduProvAtpcMin
					
					FLAG=TRAP|EVLOG|BITCNT(8)
					LOGITEM='ATPC (MIN) [dB]'
					LOGSTATUS='%d'
					LOGFLAG='LII_S_DEC|LII_I_SYSTEM'
					TRAP=eventTrapPpMxAtpcMin"
		::= { ppMxpdiTxPwrCtrlIndvEntry 4 }

	ppMxpdiTxPwrCtrlMtpcTxPower OBJECT-TYPE
		SYNTAX		INTEGER
		ACCESS		read-only
		STATUS		mandatory
		DESCRIPTION	"Range is ppMxiviOduProvMtpcMax,ppMxiviOduProvMtpcMin
					
					FLAG=TRAP|EVLOG|BITCNT(8)
					LOGITEM='MTPC TX POWER[dB]'
					LOGSTATUS='%d'
					LOGFLAG='LII_S_DEC|LII_I_SYSTEM'
					TRAP=eventTrapPpMxMtpcTxPower"
		::= { ppMxpdiTxPwrCtrlIndvEntry 5 }

	ppMxpdiTxPwrCtrlRxThresholdLevel OBJECT-TYPE
		SYNTAX		INTEGER
		ACCESS		read-only
		STATUS		mandatory
		DESCRIPTION	"Range is  ppMxiviOduProvRxThresholdMax,ppMxiviOduProvRxThresholdMin
					
					FLAG=TRAP|EVLOG|BITCNT(8)
					LOGITEM='RX THRESHOLD LEVEL [dBm]'
					LOGSTATUS='%d'
					LOGFLAG='LII_S_DEC|LII_I_SYSTEM'
					TRAP=eventTrapPpMxAtpcRxThresholdLevel"
		::= { ppMxpdiTxPwrCtrlIndvEntry 6 }

	ppMxpdiTxPwrCtrlAdditionalAtt OBJECT-TYPE
		SYNTAX		INTEGER
		ACCESS		read-only
		STATUS		mandatory
		DESCRIPTION	"Additional ATT
					Range is ppMxiviOduProvAdditionalAttMax,ppMxiviOduProvAdditionalAttMin
					
					FLAG=TRAP|EVLOG|BITCNT(8)
					LOGITEM='ADDITIONAL ATT[dB]'
					LOGSTATUS='%d'
					LOGFLAG='LII_S_DEC|LII_I_SYSTEM'
					TRAP=eventTrapPpMxAdditionalAtt"
		::= { ppMxpdiTxPwrCtrlIndvEntry 7 }

	ppMxpdiTxPwrCtrlComTable OBJECT-TYPE
		SYNTAX		SEQUENCE OF PpMxpdiTxPwrCtrlComEntry
		ACCESS		not-accessible
		STATUS		optional
		DESCRIPTION	"TX Power Ctrl Common Table"
		::= { ppMxpdiTxPwrCtrl 2 }

	ppMxpdiTxPwrCtrlComEntry OBJECT-TYPE
		SYNTAX		PpMxpdiTxPwrCtrlComEntry
		ACCESS		not-accessible
		STATUS		optional
		DESCRIPTION	"TX Power Ctrl Common Table Entry"
		INDEX		{
					ppMxpdiTxPwrCtrlComPasoIndex
					}
		::= { ppMxpdiTxPwrCtrlComTable 1 }

	PpMxpdiTxPwrCtrlComEntry ::= SEQUENCE {
					  ppMxpdiTxPwrCtrlComPasoIndex    IpAddress,	
					  ppMxpdiTxPwrCtrlOduAlarmMode     INTEGER,	
					  ppMxpdiTxPwrCtrlTxSwPriority     INTEGER,	
					  ppMxpdiTxPwrCtrlRxSwPriority     INTEGER
					 }					  
					         
	ppMxpdiTxPwrCtrlComPasoIndex OBJECT-TYPE
		SYNTAX		IpAddress 
		ACCESS		read-only
		STATUS		mandatory
		DESCRIPTION	"Pasolink IP Address Index"
		::= { ppMxpdiTxPwrCtrlComEntry 1 }
		
	ppMxpdiTxPwrCtrlOduAlarmMode OBJECT-TYPE
		SYNTAX		INTEGER {
					  mute(1),
					  max(2),
					  min(3),
					  hold(4)
					}
		ACCESS		read-only
		STATUS		mandatory
		DESCRIPTION	"ODU ALM MODE
					 1:MUTE, 2:MAX, 3:MIN, 4:HOLD
					1:MUTE is prohibited
					
					FLAG=TRAP|EVLOG|BITCNT(8)
					LOGITEM='ODU ALM MODE'
					LOGSTATUS='MUTE(1), MAX(2), MIN(3), HOLD(4)'
					LOGFLAG='LII_I_SYSTEM'
					TRAP=eventTrapPpMxOduAlarmMode"
		::= { ppMxpdiTxPwrCtrlComEntry 2 }

	ppMxpdiTxPwrCtrlTxSwPriority OBJECT-TYPE
		SYNTAX		INTEGER ( 0..2 )
		ACCESS		read-only
		STATUS		mandatory
		DESCRIPTION	"TXSW Priority
					0:INVALID 1:priority NO.1 , 2:non-priority
					FLAG=TRAP|EVLOG|NONTC_10|BITCNT(8)
					LOGITEM='TX SW PRIORITY'
					LOGSTATUS='PRIORITY No.1(1),NON-PRIORITY(2)'
					LOGFLAG='LII_I_INVALID_HIDE|LII_I_ZERO'
					TRAP=eventTrapPpMxTxSwPriority"
		::= { ppMxpdiTxPwrCtrlComEntry 3 }

	ppMxpdiTxPwrCtrlRxSwPriority OBJECT-TYPE
		SYNTAX		INTEGER ( 0..2 )
		ACCESS		read-only
		STATUS		mandatory
		DESCRIPTION	"RXSW Priority
					0:INVALID 1:priority NO.1 , 2:non-priority
					FLAG=TRAP|EVLOG|NONTC_10|BITCNT(8)
					LOGITEM='RX SW PRIORITY'
					LOGSTATUS='PRIORITY No.1(1),NON-PRIORITY(2)'
					LOGFLAG='LII_I_INVALID_HIDE|LII_I_ZERO'
					TRAP=eventTrapPpMxRxSwPriority"
		::= { ppMxpdiTxPwrCtrlComEntry 4 }

	ppMxpdiMainChSetting OBJECT IDENTIFIER
		::= { ppMxProvisioningInfo 4 }

	ppMxpdiMainChTable OBJECT-TYPE
		SYNTAX		SEQUENCE OF PpMxpdiMainChEntry
		ACCESS		not-accessible
		STATUS		mandatory
		DESCRIPTION	"Main Ch Table"
		::= { ppMxpdiMainChSetting 1 }

	ppMxpdiMainChEntry OBJECT-TYPE
		SYNTAX		PpMxpdiMainChEntry
		ACCESS		not-accessible
		STATUS		mandatory
		DESCRIPTION	"Main Ch Table Entry"
		INDEX		{
						ppMxpdiMainChPasoIndex,
						ppMxpdiMainChIndex
					}
		::= { ppMxpdiMainChTable 1 }

	PpMxpdiMainChEntry ::= SEQUENCE {
					  ppMxpdiMainChPasoIndex IpAddress,
					  ppMxpdiMainChIndex     INTEGER,
					  ppMxpdiMainChUsage     INTEGER
					}

	ppMxpdiMainChPasoIndex OBJECT-TYPE
		SYNTAX		IpAddress 
		ACCESS		read-only
		STATUS		mandatory
		DESCRIPTION	"Pasolink IP Address Index"
		::= { ppMxpdiMainChEntry 1 }
		
	ppMxpdiMainChIndex OBJECT-TYPE
		SYNTAX		INTEGER( 1..40 )
		ACCESS		read-only
		STATUS		mandatory
		DESCRIPTION	"Index CH 
					1:CH1,2:CH2,...,40:CH40"
		::= { ppMxpdiMainChEntry 2 }

	ppMxpdiMainChUsage OBJECT-TYPE
		SYNTAX		INTEGER ( 0..3 )
		ACCESS		read-only
		STATUS		mandatory
		DESCRIPTION	"CHANNEL USAGE 
					0:INVALID 1:USED,2:NOT USED,3:LAN RESERVED
					FLAG=TRAP|EVLOG|CMNBIT|BITCNT(8)
					LOGITEM='CH%d USAGE '
					LOGSTATUS='USED(1),NOT USED(2),LAN RESERVED(3)'
					LOGFLAG='LII_I_INVALID_HIDE|LII_I_TABIX'
					TRAP=eventTrapPpMxMainChUsage"
		::= { ppMxpdiMainChEntry 3 }

	ppMxpdiMainChComTable OBJECT-TYPE
		SYNTAX		SEQUENCE OF PpMxpdiMainChComEntry
		ACCESS		not-accessible
		STATUS		optional
		DESCRIPTION	"Main Ch Common Table"
		::= { ppMxpdiMainChSetting 2 }

	ppMxpdiMainChComEntry OBJECT-TYPE
		SYNTAX		PpMxpdiMainChComEntry
		ACCESS		not-accessible
		STATUS		optional
		DESCRIPTION	"Main Ch Common Table Entry"
		INDEX		{
					ppMxpdiMainChComPasoIndex
					}
		::= { ppMxpdiMainChComTable 1 }

	PpMxpdiMainChComEntry ::= SEQUENCE {
					  ppMxpdiMainChComPasoIndex    IpAddress,	
					  ppMxpdiMainChAisReceivedReport     INTEGER,	
					  ppMxpdiMainChAisReceivedConditionSetting     INTEGER,	
					  ppMxpdiMainChAisGeneratedReport     INTEGER,	
					  ppMxpdiMainChUsageErrorReport     INTEGER
					 }					  
					         
	ppMxpdiMainChComPasoIndex OBJECT-TYPE
		SYNTAX		IpAddress 
		ACCESS		read-only
		STATUS		mandatory
		DESCRIPTION	"Pasolink IP Address Index"
		::= { ppMxpdiMainChComEntry 1 }
		
	ppMxpdiMainChAisReceivedReport OBJECT-TYPE
		SYNTAX		INTEGER ( 0..2 )
		ACCESS		read-only
		STATUS		mandatory
		DESCRIPTION	"AIS RECEIVED REPORT
					0:INVALID 1:REPORTED , 2:NOT REPORTED
					FLAG=TRAP|EVLOG|BITCNT(8)
					LOGITEM='AIS RECEIVED REPORT'
					LOGSTATUS='REPORTED(1),NOT REPORTED(2)'
					LOGFLAG='LII_I_INVALID_HIDE'
					TRAP=eventTrapPpMxMainChAisReceivedReport"
		::= { ppMxpdiMainChComEntry 2 }

	ppMxpdiMainChAisReceivedConditionSetting OBJECT-TYPE
		SYNTAX		INTEGER ( 0..2 )
		ACCESS		read-only
		STATUS		mandatory
		DESCRIPTION	"AIS RECEIVED CONDITION SETTING
					0:INVALID 1:ALARM , 2:STATUS
					
					FLAG=TRAP|EVLOG|BITCNT(8)
					LOGITEM='AIS RECEIVED CONDITION SETTING'
					LOGSTATUS='ALARM(1),STATUS(2)'
					LOGFLAG='LII_I_INVALID_HIDE|LII_T_STATUS'
					TRAP=eventTrapPpMxMainChAisReceivedConditionSetting"
		::= { ppMxpdiMainChComEntry 3 }

	ppMxpdiMainChAisGeneratedReport OBJECT-TYPE
		SYNTAX		INTEGER ( 0..2 )
		ACCESS		read-only
		STATUS		mandatory
		DESCRIPTION	"AIS GENERATED REPORT
					0:INVALID 1:REPORTED , 2:NOT REPORTED
					FLAG=TRAP|EVLOG|BITCNT(8)
					LOGITEM='AIS GENERATED REPORT'
					LOGSTATUS='REPORTED(1),NOT REPORTED(2)'
					LOGFLAG='LII_I_INVALID_HIDE'
					TRAP=eventTrapPpMxMainChAisGeneratedReport"
		::= { ppMxpdiMainChComEntry 4 }

	ppMxpdiMainChUsageErrorReport OBJECT-TYPE
		SYNTAX		INTEGER ( 0..2 )
		ACCESS		read-only
		STATUS		mandatory
		DESCRIPTION	"CHANNEL USAGE ERROR REPORT
					0:INVALID 1:REPORTED , 2:NOT REPORTED
					FLAG=TRAP|EVLOG|BITCNT(8)
					LOGITEM='CHANNEL USAGE ERROR REPORT'
					LOGSTATUS='REPORTED(1),NOT REPORTED(2)'
					LOGFLAG='LII_I_INVALID_HIDE'
					TRAP=eventTrapPpMxMainChErrorReport"
		::= { ppMxpdiMainChComEntry 5 }

	ppMxpdiLanIntfcM OBJECT IDENTIFIER
		::= { ppMxProvisioningInfo 5 }

	ppMxpdiLanIntfcMTable OBJECT-TYPE
		SYNTAX		SEQUENCE OF PpMxpdiLanIntfcMEntry
		ACCESS		not-accessible
		STATUS		mandatory
		DESCRIPTION	"LAN INTFC-M Table"
		::= { ppMxpdiLanIntfcM 1 }

	ppMxpdiLanIntfcMEntry OBJECT-TYPE
		SYNTAX		PpMxpdiLanIntfcMEntry
		ACCESS		not-accessible
		STATUS		mandatory
		DESCRIPTION	"LAN INTFC-M Table Entry"
		INDEX		{
						ppMxpdiLanIntfcMPasoIndex,
						ppMxpdiLanIntfcMIndex
					}
		::= { ppMxpdiLanIntfcMTable 1 }

	PpMxpdiLanIntfcMEntry ::= SEQUENCE {
					  ppMxpdiLanIntfcMPasoIndex       IpAddress,
					  ppMxpdiLanIntfcMIndex           INTEGER,
					  ppMxpdi4pLanPortUsage           INTEGER,
					  ppMxpdi4pLanPortSpeedDuplex     INTEGER,
					  ppMxpdi4pLanFlowControl         INTEGER,
					  ppMxpdi4pLanCollisionReport     INTEGER,
					  ppMxpdi4pLanLinkLossForwarding  INTEGER
					}

	ppMxpdiLanIntfcMPasoIndex OBJECT-TYPE
		SYNTAX		IpAddress 
		ACCESS		read-only
		STATUS		mandatory
		DESCRIPTION	"Pasolink IP Address Index"
		::= { ppMxpdiLanIntfcMEntry 1 }
		
	ppMxpdiLanIntfcMIndex OBJECT-TYPE
		SYNTAX		INTEGER {
					  port1(1),
					  port2(2),
					  port3(3),
					  port4(4)
					}
		ACCESS		read-only
		STATUS		mandatory
		DESCRIPTION	"LanIntfcM Index"
		::= { ppMxpdiLanIntfcMEntry 2 }

	ppMxpdi4pLanPortUsage OBJECT-TYPE
		SYNTAX		INTEGER ( 0..2 )
		ACCESS		read-only
		STATUS		mandatory
		DESCRIPTION	"PORTx USAGE(4P)
					0:INVALID, 1:USED , 2:NOT USED
					
					FLAG=TRAP|EVLOG|NONTC_BT|CMNBIT|BITCNT(8)
					LOGITEM='PORT%d USAGE(4P)'
					LOGSTATUS='USED(1), NOT USED(2)'
					LOGFLAG='LII_I_INVALID_HIDE|LII_I_TABIX'
					TRAP=eventTrapPpMx4pLanPortUsage"
		::= { ppMxpdiLanIntfcMEntry 3 }

	ppMxpdi4pLanPortSpeedDuplex OBJECT-TYPE
		SYNTAX		INTEGER ( 0..9 )
					
		ACCESS		read-only
		STATUS		mandatory
		DESCRIPTION	"PORTx SPEED & DUPLEX(4P) SETTING
					 1:AUTONEG(AUTO-MDI/MDIX)
					 2:10M-HALF(MDI)
					 3:10M-FULL(MDI)
					 4:100M-HALF(MDI)
					 5:100M-FULL(MDI)
					 6:10M-HALF(MDIX)
					 7:10M-FULL(MDIX)
					 8:100M-HALF(MDIX)
					 9:100M-FULL(MDIX)
					 0:INVALID
					
					FLAG=TRAP|EVLOG|NONTC_BT|CMNBIT|BITCNT(8)
					LOGITEM='PORT%d SPEED & DUPLEX(4P) SETTING'
					LOGSTATUS='AUTONEG(AUTO-MDI/MDIX)(1),10M-HALF(MDI)(2),10M-FULL(MDI)(3),100M-HALF(MDI)(4),100M-FULL(MDI)(5),10M-HALF(MDIX)(6),10M-FULL(MDIX)(7),100M-HALF(MDIX)(8),100M-FULL(MDIX)(9)'
					LOGFLAG='LII_I_INVALID_HIDE|LII_I_TABIX'
					TRAP=eventTrapPpMx4pLanPortSpeedDuplex"
		::= { ppMxpdiLanIntfcMEntry 4 }

	ppMxpdi4pLanFlowControl OBJECT-TYPE
		SYNTAX		INTEGER ( 0..2 )
		ACCESS		read-only
		STATUS		mandatory
		DESCRIPTION	"PORTx FLOW CONTROL(4P)
					0:INVALID 1:ON , 2:OFF
					
					FLAG=TRAP|EVLOG|NONTC_BT|CMNBIT|BITCNT(8)
					LOGITEM='PORT%d FLOW CONTROL(4P)'
					LOGSTATUS='ON(1), OFF(2)'
					LOGFLAG='LII_I_INVALID_HIDE|LII_I_TABIX'
					TRAP=eventTrapPpMx4pLanFlowControl"
		::= { ppMxpdiLanIntfcMEntry 5 }

	ppMxpdi4pLanCollisionReport OBJECT-TYPE
		SYNTAX		INTEGER ( 0..2 )
		ACCESS		read-only
		STATUS		mandatory
		DESCRIPTION	"PORTx COLLISION REPORT(4P)
					0:INVALID  1:REPORTED , 2:NOT REPORTED
					
					FLAG=TRAP|EVLOG|NONTC_BT|CMNBIT|BITCNT(8)
					LOGITEM='PORT%d COLLISION REPORT(4P)'
					LOGSTATUS='REPORTED(1),NOT REPORTED(2)'
					LOGFLAG='LII_I_INVALID_HIDE|LII_I_TABIX'
					TRAP=eventTrapPpMx4pLanCollisionReport"
		::= { ppMxpdiLanIntfcMEntry 6 }

	ppMxpdi4pLanLinkLossForwarding OBJECT-TYPE
		SYNTAX		INTEGER ( 0..2 )
		ACCESS		read-only
		STATUS		mandatory
		DESCRIPTION	"PORTx LINK LOSS FORWARDING(4P)
					0:INVALID 1:ENABLED , 2:DISABLED
					FLAG=TRAP|EVLOG|NONTC_BT|CMNBIT|BITCNT(8)
					LOGITEM='PORT%d LINK LOSS FORWARDING(4P)'
					LOGSTATUS='ENABLED(1), DISABLED(2)'
					LOGFLAG='LII_I_INVALID_HIDE|LII_I_TABIX'
					TRAP=eventTrapPpMx4pLanLinkLossForwarding"
		::= { ppMxpdiLanIntfcMEntry 7 }

	ppMxpdiLanIntfcMComTable OBJECT-TYPE
		SYNTAX		SEQUENCE OF PpMxpdiLanIntfcMComEntry
		ACCESS		not-accessible
		STATUS		optional
		DESCRIPTION	"LAN INTFC-M Common Table"
		::= { ppMxpdiLanIntfcM 2 }

	ppMxpdiLanIntfcMComEntry OBJECT-TYPE
		SYNTAX		PpMxpdiLanIntfcMComEntry
		ACCESS		not-accessible
		STATUS		optional
		DESCRIPTION	"LAN INTFC-M Common Table Entry"
		INDEX		{
					ppMxpdiLanIntfcMComPasoIndex
					}
		::= { ppMxpdiLanIntfcMComTable 1 }

	PpMxpdiLanIntfcMComEntry ::= SEQUENCE {
					  ppMxpdiLanIntfcMComPasoIndex  IpAddress,	
					  ppMxpdi4pLanPortSwitching     INTEGER
					 }					  
					         
	ppMxpdiLanIntfcMComPasoIndex OBJECT-TYPE
		SYNTAX		IpAddress 
		ACCESS		read-only
		STATUS		mandatory
		DESCRIPTION	"Pasolink IP Address Index"
		::= { ppMxpdiLanIntfcMComEntry 1 }
		
	ppMxpdi4pLanPortSwitching OBJECT-TYPE
		SYNTAX		INTEGER ( 0..6 )
		ACCESS		read-only
		STATUS		mandatory
		DESCRIPTION	"PORT SWITCHING(4P)
					0:INVALID
					1:P1-2=ENABLED,P3-4=ENABLED
					2:P1-2=ENABLED,P3-4=DISABLED
					3:P1-2=DISABLED,P3-4=ENABLED
					4:P1-2=DISABLED,P3-4=DISABLED
					5:P1-4=ENABLED
					6:P1-4=DISABLED
					
					FLAG=TRAP|EVLOG|NONTC_BT|BITCNT(8)
					LOGITEM='PORT SWITCHING(4P)'
					LOGSTATUS='%s'
					LOGFLAG='LII_I_INVALID_HIDE|LII_S_LAN_PORT_SW'
					TRAP=eventTrapPpMx4pLanPortSwitching"
		::= { ppMxpdiLanIntfcMComEntry 2 }

	ppMxpdiLanIntfcS OBJECT IDENTIFIER
		::= { ppMxProvisioningInfo 6 }

	ppMxpdiLanIntfcSTable OBJECT-TYPE
		SYNTAX		SEQUENCE OF PpMxpdiLanIntfcSEntry
		ACCESS		not-accessible
		STATUS		mandatory
		DESCRIPTION	"LAN INTFC-S Table"
		::= { ppMxpdiLanIntfcS 1 }

	ppMxpdiLanIntfcSEntry OBJECT-TYPE
		SYNTAX		PpMxpdiLanIntfcSEntry
		ACCESS		not-accessible
		STATUS		mandatory
		DESCRIPTION	"LAN INTFC-S Table Entry"
		INDEX		{
						ppMxpdiLanIntfcSPasoIndex,
						ppMxpdiLanIntfcSIndex
					}
		::= { ppMxpdiLanIntfcSTable 1 }

	PpMxpdiLanIntfcSEntry ::= SEQUENCE {
					  ppMxpdiLanIntfcSPasoIndex       IpAddress,
					  ppMxpdiLanIntfcSIndex           INTEGER,
					  ppMxpdi2pLanPortUsage           INTEGER,
					  ppMxpdi2pLanPortSpeedDuplex     INTEGER,
					  ppMxpdi2pLanFlowControl         INTEGER,
					  ppMxpdi2pLanCollisionReport     INTEGER,
					  ppMxpdi2pLanLinkLossForwarding  INTEGER 
					}

	ppMxpdiLanIntfcSPasoIndex OBJECT-TYPE
		SYNTAX		IpAddress 
		ACCESS		read-only
		STATUS		mandatory
		DESCRIPTION	"Pasolink IP Address Index"
		::= { ppMxpdiLanIntfcSEntry 1 }
		
	ppMxpdiLanIntfcSIndex OBJECT-TYPE
		SYNTAX		INTEGER {
					  port1(1),
					  port2(2)
					}
		ACCESS		read-only
		STATUS		mandatory
		DESCRIPTION	"LanIntfcS Index"
		::= { ppMxpdiLanIntfcSEntry 2 }

	ppMxpdi2pLanPortUsage OBJECT-TYPE
		SYNTAX		INTEGER ( 0..2 )
		ACCESS		read-only
		STATUS		mandatory
		DESCRIPTION	"PORTx USAGE(2P)
					0:INVALID, 1:USED , 2:NOT USED
					
					FLAG=TRAP|EVLOG|BITCNT(8)|CMNBIT
					LOGITEM='PORT%d USAGE(2P)'
					LOGSTATUS='USED(1), NOT USED(2)'
					LOGFLAG='LII_I_INVALID_HIDE|LII_I_TABIX'
					TRAP=eventTrapPpMx2pLanPortUsage"
		::= { ppMxpdiLanIntfcSEntry 3 }

	ppMxpdi2pLanPortSpeedDuplex OBJECT-TYPE
		SYNTAX		INTEGER ( 0..9 )
					
		ACCESS		read-only
		STATUS		mandatory
		DESCRIPTION	"PORTx SPEED & DUPLEX(2P) SETTING
					 1:AUTONEG(AUTO-MDI/MDIX)
					 2:10M-HALF(MDI)
					 3:10M-FULL(MDI)
					 4:100M-HALF(MDI)
					 5:100M-FULL(MDI)
					 6:10M-HALF(MDIX)
					 7:10M-FULL(MDIX)
					 8:100M-HALF(MDIX)
					 9:100M-FULL(MDIX)
					 0:INVALID
					
					FLAG=TRAP|EVLOG|BITCNT(8)|CMNBIT
					LOGITEM='PORT%d SPEED & DUPLEX(2P) SETTING'
					LOGSTATUS='AUTONEG(AUTO-MDI/MDIX)(1),10M-HALF(MDI)(2),10M-FULL(MDI)(3),100M-HALF(MDI)(4),100M-FULL(MDI)(5),10M-HALF(MDIX)(6),10M-FULL(MDIX)(7),100M-HALF(MDIX)(8),100M-FULL(MDIX)(9),INVALID(0)'
					LOGFLAG='LII_I_INVALID_HIDE|LII_I_TABIX'
					TRAP=eventTrapPpMx2pLanPortSpeedDuplex"
		::= { ppMxpdiLanIntfcSEntry 4 }

	ppMxpdi2pLanFlowControl OBJECT-TYPE
		SYNTAX		INTEGER ( 0..2 )
		ACCESS		read-only
		STATUS		mandatory
		DESCRIPTION	"PORTx FLOW CONTROL(2P)
					0:INVALID 1:ON , 2:OFF
					
					FLAG=TRAP|EVLOG|BITCNT(8)|CMNBIT
					LOGITEM='PORT%d FLOW CONTROL(2P)'
					LOGSTATUS='ON(1), OFF(2)'
					LOGFLAG='LII_I_INVALID_HIDE|LII_I_TABIX'
					TRAP=eventTrapPpMx2pLanFlowControl"
		::= { ppMxpdiLanIntfcSEntry 5 }

	ppMxpdi2pLanCollisionReport OBJECT-TYPE
		SYNTAX		INTEGER ( 0..2 )
		ACCESS		read-only
		STATUS		mandatory
		DESCRIPTION	"PORTx COLLISION REPORT(2P)
					0:INVALID  1:REPORTED , 2:NOT REPORTED
					
					FLAG=TRAP|EVLOG|BITCNT(8)|CMNBIT
					LOGITEM='PORT%d COLLISION REPORT(2P)'
					LOGSTATUS='REPORTED(1),NOT REPORTED(2)'
					LOGFLAG='LII_I_INVALID_HIDE|LII_I_TABIX'
					TRAP=eventTrapPpMx2pLanCollisionReport"
		::= { ppMxpdiLanIntfcSEntry 6 }

	ppMxpdi2pLanLinkLossForwarding OBJECT-TYPE
		SYNTAX		INTEGER ( 0..2 )
		ACCESS		read-only
		STATUS		mandatory
		DESCRIPTION	"PORTx LINK LOSS FORWARDING(2P)
					0:INVALID 1:ENABLED , 2:DISABLED
					FLAG=TRAP|EVLOG|BITCNT(8)|CMNBIT
					LOGITEM='PORT%d LINK LOSS FORWARDING(2P)'
					LOGSTATUS='ENABLED(1), DISABLED(2)'
					LOGFLAG='LII_I_INVALID_HIDE|LII_I_TABIX'
					TRAP=eventTrapPpMx2pLanLinkLossForwarding"
		::= { ppMxpdiLanIntfcSEntry 7 }

	ppMxpdiLanIntfcSComTable OBJECT-TYPE
		SYNTAX		SEQUENCE OF PpMxpdiLanIntfcSComEntry
		ACCESS		not-accessible
		STATUS		optional
		DESCRIPTION	"LAN INTFC-S Common Table"
		::= { ppMxpdiLanIntfcS 2 }

	ppMxpdiLanIntfcSComEntry OBJECT-TYPE
		SYNTAX		PpMxpdiLanIntfcSComEntry
		ACCESS		not-accessible
		STATUS		optional
		DESCRIPTION	"LAN INTFC-S Common Table Entry"
		INDEX		{
					ppMxpdiLanIntfcSComPasoIndex
					}
		::= { ppMxpdiLanIntfcSComTable 1 }

	PpMxpdiLanIntfcSComEntry ::= SEQUENCE {
					  ppMxpdiLanIntfcSComPasoIndex      IpAddress,	
					  ppMxpdi2pLanPortSwitching         INTEGER,	
					  ppMxpdi2pLanPort1or12Lan2MFraming INTEGER,	
					  ppMxpdi2pLanPort2Lan2MFraming     INTEGER
					 }					  
					         
	ppMxpdiLanIntfcSComPasoIndex OBJECT-TYPE
		SYNTAX		IpAddress 
		ACCESS		read-only
		STATUS		mandatory
		DESCRIPTION	"Pasolink IP Address Index"
		::= { ppMxpdiLanIntfcSComEntry 1 }
		
	ppMxpdi2pLanPortSwitching OBJECT-TYPE
		SYNTAX		INTEGER ( 0..2 )
		ACCESS		read-only
		STATUS		mandatory
		DESCRIPTION	"PORT SWITCHING(2P)
					0:INVALID
					1:P1-2=ENABLED
					2:P1-2=DISABLED
					
					FLAG=TRAP|EVLOG|BITCNT(8)
					LOGITEM='PORT SWITCHING(2P)'
					LOGSTATUS='P1-2=ENABLED(1),P1-2=DISABLED(2)'
					LOGFLAG='LII_I_INVALID_HIDE'
					TRAP=eventTrapPpMx2pLanPortSwitching"
		::= { ppMxpdiLanIntfcSComEntry 2 }

	ppMxpdi2pLanPort1or12Lan2MFraming OBJECT-TYPE
		SYNTAX		INTEGER ( 0..5 )
		ACCESS		read-only
		STATUS		mandatory
		DESCRIPTION	"PORT1/1-2 LAN >> 2M FRAMING
					0:INVALID
					1:UNFRAMED
					2:PCM-31C(FAS+CRC)
					3:PCM-31(FAS)
					4:PCM-30C(MFAS+CRC)
					5:PCM-30(MFAS)
					
					FLAG=TRAP|EVLOG|BITCNT(8)
					LOGITEM='PORT1/1-2 LAN >> 2M FRAMING'
					LOGSTATUS='UNFRAMED(1),PCM-31C(FAS+CRC)(2),PCM-31(FAS)(3),PCM-30C(MFAS+CRC)(4),PCM-30(MFAS)(5)'
					LOGFLAG='LII_I_INVALID_HIDE'
					TRAP=eventTrapPpMx2pLanPort1or12Lan2MFraming"
		::= { ppMxpdiLanIntfcSComEntry 3 }

	ppMxpdi2pLanPort2Lan2MFraming OBJECT-TYPE
		SYNTAX		INTEGER ( 0..5 )
		ACCESS		read-only
		STATUS		mandatory
		DESCRIPTION	"PORT2 LAN >> 2M FRAMING
					0:INVALID
					1:UNFRAMED
					2:PCM-31C(FAS+CRC)
					3:PCM-31(FAS)
					4:PCM-30C(MFAS+CRC)
					5:PCM-30(MFAS)
					
					FLAG=TRAP|EVLOG|BITCNT(8)
					LOGITEM='PORT2 LAN >> 2M FRAMING'
					LOGSTATUS='UNFRAMED(1),PCM-31C(FAS+CRC)(2),PCM-31(FAS)(3),PCM-30C(MFAS+CRC)(4),PCM-30(MFAS)(5)'
					LOGFLAG='LII_I_INVALID_HIDE'
					TRAP=eventTrapPpMx2pLanPort2Lan2MFraming"
		::= { ppMxpdiLanIntfcSComEntry 4 }

	ppMxpdiScAssign OBJECT IDENTIFIER
		::= { ppMxProvisioningInfo 7 }

	ppMxpdiScAssignTable OBJECT-TYPE
		SYNTAX		SEQUENCE OF PpMxpdiScAssignEntry
		ACCESS		not-accessible
		STATUS		optional
		DESCRIPTION	"SC Assignment Table"
		::= { ppMxpdiScAssign 1 }

	ppMxpdiScAssignEntry OBJECT-TYPE
		SYNTAX		PpMxpdiScAssignEntry
		ACCESS		not-accessible
		STATUS		optional
		DESCRIPTION	"SC Assignment Table Entry"
		INDEX		{
					ppMxpdiScAssignPasoIndex
					}
		::= { ppMxpdiScAssignTable 1 }

	PpMxpdiScAssignEntry ::= SEQUENCE {
					  ppMxpdiScAssignPasoIndex  IpAddress,	
					  ppMxpdiSc1Usage           INTEGER,	
					  ppMxpdiSc2Usage           INTEGER,	
					  ppMxpdiSc3Usage           INTEGER,	
					  ppMxpdiSc4Usage           INTEGER
					 }					  
					         
	ppMxpdiScAssignPasoIndex OBJECT-TYPE
		SYNTAX		IpAddress 
		ACCESS		read-only
		STATUS		mandatory
		DESCRIPTION	"Pasolink IP Address Index"
		::= { ppMxpdiScAssignEntry 1 }
		
	ppMxpdiSc1Usage OBJECT-TYPE
		SYNTAX		INTEGER {
					  rs232c(1),
					  lan(2)
					}
		ACCESS		read-only
		STATUS		mandatory
		DESCRIPTION	"SC1 USAGE
					1:RS-232C
					2:LAN
					
					FLAG=TRAP|EVLOG|BITCNT(8)
					LOGITEM='SC1 USAGE'
					LOGSTATUS='RS-232C(1),LAN(2)'
					TRAP=eventTrapPpMxSc1Usage"
		::= { ppMxpdiScAssignEntry 2 }

	ppMxpdiSc2Usage OBJECT-TYPE
		SYNTAX		INTEGER {
					  rs232c(1),
					  lan(2)
					}
		ACCESS		read-only
		STATUS		mandatory
		DESCRIPTION	"SC2 USAGE
					1:RS-232C
					2:LAN
					
					FLAG=TRAP|EVLOG|BITCNT(8)
					LOGITEM='SC2 USAGE'
					LOGSTATUS='RS-232C(1),LAN(2)'
					TRAP=eventTrapPpMxSc2Usage"
		::= { ppMxpdiScAssignEntry 3 }

	ppMxpdiSc3Usage OBJECT-TYPE
		SYNTAX		INTEGER {
					  v11CoDirectional(1),
					  v11ContraDirectional(2),
					  tnsCard(3)
					}
		ACCESS		read-only
		STATUS		mandatory
		DESCRIPTION	"SC3 USAGE
					1:V.11(CO-DIRECTIONAL)
					2:V.11(CONTRA-DIRECTIONAL)
					3:TNS CARD
					
					FLAG=TRAP|EVLOG|BITCNT(8)
					LOGITEM='SC3 USAGE'
					LOGSTATUS='V.11(CO-DIRECTIONAL)(1),V.11(CONTRA-DIRECTIONAL)(2),TNS CARD(3)'
					TRAP=eventTrapPpMxSc3Usage"
		::= { ppMxpdiScAssignEntry 4 }

	ppMxpdiSc4Usage OBJECT-TYPE
		SYNTAX		INTEGER {
					  v11CoDirectional(1),
					  v11ContraDirectional(2)
					}
		ACCESS		read-only
		STATUS		mandatory
		DESCRIPTION	"SC4 USAGE
					0:INVALID
					1:V.11(CO-DIRECTIONAL)
					2:V.11(CONTRA-DIRECTIONAL)
					
					FLAG=TRAP|EVLOG|BITCNT(8)
					LOGITEM='SC4 USAGE'
					LOGSTATUS='V.11(CO-DIRECTIONAL)(1),V.11(CONTRA-DIRECTIONAL)(2)'
					LOGFLAG='LII_I_INVALID_HIDE'
					TRAP=eventTrapPpMxSc4Usage"
		::= { ppMxpdiScAssignEntry 5 }

	ppMxpdiExtAlarm OBJECT IDENTIFIER
		::= { ppMxProvisioningInfo 8 }

	ppMxpdiExtAlarmTable OBJECT-TYPE
		SYNTAX		SEQUENCE OF PpMxpdiExtAlarmEntry
		ACCESS		not-accessible
		STATUS		mandatory
		DESCRIPTION	"Ext Alarm Table"
		::= { ppMxpdiExtAlarm 1 }

	ppMxpdiExtAlarmEntry OBJECT-TYPE
		SYNTAX		PpMxpdiExtAlarmEntry
		ACCESS		not-accessible
		STATUS		mandatory
		DESCRIPTION	"Ext Alarm Table Entry"
		INDEX		{
						ppMxpdiExtAlarmPasoIndex,
						ppMxpdiExtAlarmIndex
					}
		::= { ppMxpdiExtAlarmTable 1 }

	PpMxpdiExtAlarmEntry ::= SEQUENCE {
					  ppMxpdiExtAlarmPasoIndex  IpAddress,
					  ppMxpdiExtAlarmIndex      INTEGER,
					  ppMxpdiExtAlarmRelay      OCTET STRING
					}

	ppMxpdiExtAlarmPasoIndex OBJECT-TYPE
		SYNTAX		IpAddress 
		ACCESS		read-only
		STATUS		mandatory
		DESCRIPTION	"Pasolink IP Address Index"
		::= { ppMxpdiExtAlarmEntry 1 }
		
	ppMxpdiExtAlarmIndex OBJECT-TYPE
		SYNTAX		INTEGER {
					  relay1(1),
					  relay2(2),
					  relay3(3),
					  relay4(4),
					  relay5(5),
					  relay6(6),
					  relay7(7)
					}
		ACCESS		read-only
		STATUS		mandatory
		DESCRIPTION	"Ext ALM Index
					"
		::= { ppMxpdiExtAlarmEntry 2 }
		
	ppMxpdiExtAlarmRelay OBJECT-TYPE
		SYNTAX		OCTET STRING (SIZE (8))
					
		ACCESS		read-only
		STATUS		mandatory
		DESCRIPTION	"Relay setting bitmap
					FLAG=BITCNT(64)|TRAP|EVLOG|CMNBIT
					LOGITEM='RELAY-%d OUTPUT MODE'
					LOGSTATUS='UPDATED'
					LOGFLAG='LII_I_TABIX'
					TRAP=eventTrapPpMxRelay"
		::= { ppMxpdiExtAlarmEntry 3 }


-----------------------------------------------
-- ppMxInventoryInfo Group Definitions
-----------------------------------------------
 
	ppMxiviSwUnitInfo OBJECT IDENTIFIER
		::= { ppMxInventoryInfo 1 }

	ppMxiviSwUnitTable OBJECT-TYPE
		SYNTAX		SEQUENCE OF PpMxiviSwUnitEntry
		ACCESS		not-accessible
		STATUS		optional
		DESCRIPTION	"Switch Unit Table"
		::= { ppMxiviSwUnitInfo 1 }

	ppMxiviSwUnitEntry OBJECT-TYPE
		SYNTAX		PpMxiviSwUnitEntry
		ACCESS		not-accessible
		STATUS		optional
		DESCRIPTION	"Switch Unit Table Entry"
		INDEX		{
					ppMxiviSwUnitPasoIndex
					}
		::= { ppMxiviSwUnitTable 1 }

	PpMxiviSwUnitEntry ::= SEQUENCE {
					  ppMxiviSwUnitPasoIndex     IpAddress,	
					  ppMxiviSwUnitCodeNo        DisplayString,
					  ppMxiviSwUnitSerialNo      DisplayString,
					  ppMxiviSwUnitDate          DisplayString,
					  ppMxiviSwUnitSwVersion     DisplayString
					 }					  
					         
	ppMxiviSwUnitPasoIndex OBJECT-TYPE
		SYNTAX		IpAddress 
		ACCESS		read-only
		STATUS		mandatory
		DESCRIPTION	"Pasolink IP Address Index"
		::= { ppMxiviSwUnitEntry 1 }
		
	ppMxiviSwUnitCodeNo OBJECT-TYPE
		SYNTAX		DisplayString
		ACCESS		read-only
		STATUS		mandatory
		DESCRIPTION	"SwUnitCodeNo
					VARSZ=6
					FLAG=BITCNT(48)"
		::= { ppMxiviSwUnitEntry 2 }

	ppMxiviSwUnitSerialNo OBJECT-TYPE
		SYNTAX		DisplayString
		ACCESS		read-only
		STATUS		mandatory
		DESCRIPTION	"SwUnitSerialNo
					VARSZ=6
					FLAG=BITCNT(48)"
		::= { ppMxiviSwUnitEntry 3 }

	ppMxiviSwUnitDate OBJECT-TYPE
		SYNTAX		DisplayString
		ACCESS		read-only
		STATUS		mandatory
		DESCRIPTION	"SwUnitDate (YY/MM/DD)
					VARSZ=6
					FLAG=BITCNT(48)"
		::= { ppMxiviSwUnitEntry 4 }

	ppMxiviSwUnitSwVersion OBJECT-TYPE
		SYNTAX		DisplayString
					
		ACCESS		read-only
		STATUS		mandatory
		DESCRIPTION	"CTRL S/W Version of FORE side bank
					Max is 10 bytes
					ex)1.00(main_interface,sub_interface)
					    1.123.456( ctrl )
					VARSZ=10
					FLAG=BITCNT(80)"
		::= { ppMxiviSwUnitEntry 5 }

	ppMxiviIndvTable OBJECT-TYPE
		SYNTAX		SEQUENCE OF PpMxiviIndvEntry
		ACCESS		not-accessible
		STATUS		mandatory
		DESCRIPTION	"Inventory No.1/No.2 Table"
		::= { ppMxInventoryInfo 2 }

	ppMxiviIndvEntry OBJECT-TYPE
		SYNTAX		PpMxiviIndvEntry
		ACCESS		not-accessible
		STATUS		mandatory
		DESCRIPTION	"Inventory No.1/No.2 Table Entry"
		INDEX		{
						ppMxiviIndvPasoIndex,
						ppMxiviIndvIndex,
						ppMxiviIndvName
					}
		::= { ppMxiviIndvTable 1 }

	PpMxiviIndvEntry ::= SEQUENCE {
					  ppMxiviIndvPasoIndex   IpAddress,
					  ppMxiviIndvIndex       INTEGER,
					  ppMxiviIndvName        INTEGER,
					  ppMxiviIndvCodeNo      DisplayString,
					  ppMxiviIndvSerialNo    DisplayString,
					  ppMxiviIndvDate        DisplayString,
					  ppMxiviIndvHwVersion     DisplayString,
					  ppMxiviIndvSwVersion     DisplayString
					}

	ppMxiviIndvPasoIndex OBJECT-TYPE
		SYNTAX		IpAddress 
		ACCESS		read-only
		STATUS		mandatory
		DESCRIPTION	"Pasolink IP Address Index"
		::= { ppMxiviIndvEntry 1 }
		
	ppMxiviIndvIndex OBJECT-TYPE
		SYNTAX		INTEGER {
					  no1(1),
					  no2(2)
					}
		ACCESS		read-only
		STATUS		mandatory
		DESCRIPTION	"Index(no1/no2)
					1:No.1, 2:No.2"
		::= { ppMxiviIndvEntry 2 }

	ppMxiviIndvName OBJECT-TYPE
		SYNTAX		INTEGER {
					  odu(1),
					  modem(2),
					  oduIntfc(3)
					}
		ACCESS		read-only
		STATUS		mandatory
		DESCRIPTION	"Index(odu/modem/oduIntfc)
					"
		::= { ppMxiviIndvEntry 3 }

	ppMxiviIndvCodeNo OBJECT-TYPE
		SYNTAX		DisplayString
		ACCESS		read-only
		STATUS		mandatory
		DESCRIPTION	"IndvCodeNo
					VARSZ=6
					FLAG=BITCNT(48)
					All 0xFF is invalid."
		::= { ppMxiviIndvEntry 4 }

	ppMxiviIndvSerialNo OBJECT-TYPE
		SYNTAX		DisplayString
		ACCESS		read-only
		STATUS		mandatory
		DESCRIPTION	"IndvSerialNo
					VARSZ=6
					FLAG=BITCNT(48)
					All 0xFF is invalid."
		::= { ppMxiviIndvEntry 5 }

	ppMxiviIndvDate OBJECT-TYPE
		SYNTAX		DisplayString
		ACCESS		read-only
		STATUS		mandatory
		DESCRIPTION	"IndvDate (YY/MM/DD)
					VARSZ=6
					FLAG=BITCNT(48)
					All 0xFF is invalid."
		::= { ppMxiviIndvEntry 6 }

	ppMxiviIndvHwVersion OBJECT-TYPE
		SYNTAX		DisplayString
		ACCESS		read-only
		STATUS		mandatory
		DESCRIPTION	"ex)1.00
					VARSZ=4
					FLAG=BITCNT(32)"
		::= { ppMxiviIndvEntry 7 }

	ppMxiviIndvSwVersion OBJECT-TYPE
		SYNTAX		DisplayString
		ACCESS		read-only
		STATUS		mandatory
		DESCRIPTION	"ex)1.00
					VARSZ=4
					FLAG=BITCNT(32)"
		::= { ppMxiviIndvEntry 8 }

	ppMxiviOduFreqInfo OBJECT IDENTIFIER
		::= { ppMxInventoryInfo 3 }

	ppMxiviOduFreqIndvTable OBJECT-TYPE
		SYNTAX		SEQUENCE OF PpMxiviOduFreqIndvEntry
		ACCESS		not-accessible
		STATUS		mandatory
		DESCRIPTION	"ODU Frequency No.1/No.2 Table"
		::= { ppMxiviOduFreqInfo 1 }

	ppMxiviOduFreqIndvEntry OBJECT-TYPE
		SYNTAX		PpMxiviOduFreqIndvEntry
		ACCESS		not-accessible
		STATUS		mandatory
		DESCRIPTION	"ODU Frequency No.1/No.2 Table Entry"
		INDEX		{
						ppMxiviOduFreqIndvPasoIndex,
						ppMxiviOduFreqIndvIndex
					}
		::= { ppMxiviOduFreqIndvTable 1 }

	PpMxiviOduFreqIndvEntry ::= SEQUENCE {
					  ppMxiviOduFreqIndvPasoIndex   IpAddress,
					  ppMxiviOduFreqIndvIndex       INTEGER,
					  ppMxiviOduFreqTxStartFreq     DisplayString,
					  ppMxiviOduFreqTxEndFreq       DisplayString,
					  ppMxiviOduFreqUpperLower      INTEGER
					}

	ppMxiviOduFreqIndvPasoIndex OBJECT-TYPE
		SYNTAX		IpAddress 
		ACCESS		read-only
		STATUS		mandatory
		DESCRIPTION	"Pasolink IP Address Index"
		::= { ppMxiviOduFreqIndvEntry 1 }
		
	ppMxiviOduFreqIndvIndex OBJECT-TYPE
		SYNTAX		INTEGER {
					  no1(1),
					  no2(2)
					}
		ACCESS		read-only
		STATUS		mandatory
		DESCRIPTION	"Index
					1:No.1, 2:No.2"
		::= { ppMxiviOduFreqIndvEntry 2 }

	ppMxiviOduFreqTxStartFreq OBJECT-TYPE
		SYNTAX		DisplayString
		ACCESS		read-only
		STATUS		mandatory
		DESCRIPTION	"Tx Start Frequency[MHz]
					VARSZ=9
					FLAG=BITCNT(72)"
		::= { ppMxiviOduFreqIndvEntry 3 }

	ppMxiviOduFreqTxEndFreq OBJECT-TYPE
		SYNTAX		DisplayString
		ACCESS		read-only
		STATUS		mandatory
		DESCRIPTION	"Tx End Frequency[MHz]
					VARSZ=9
					FLAG=BITCNT(72)"
		::= { ppMxiviOduFreqIndvEntry 4 }

	ppMxiviOduFreqUpperLower OBJECT-TYPE
		SYNTAX		INTEGER
		ACCESS		read-only
		STATUS		mandatory
		DESCRIPTION	"UpperLower
					1:Lower 2:Upper  35:INVALID 42:NOT OBTAIN
					
					FLAG=BITCNT(8)"
		::= { ppMxiviOduFreqIndvEntry 5 }

	ppMxiviFreqSettingInfo OBJECT IDENTIFIER
		::= { ppMxInventoryInfo 4 }

	ppMxiviFreqSettingIndvTable OBJECT-TYPE
		SYNTAX		SEQUENCE OF PpMxiviFreqSettingIndvEntry
		ACCESS		not-accessible
		STATUS		mandatory
		DESCRIPTION	"Frequency Setting No.1/No.2 Table"
		::= { ppMxiviFreqSettingInfo 1 }

	ppMxiviFreqSettingIndvEntry OBJECT-TYPE
		SYNTAX		PpMxiviFreqSettingIndvEntry
		ACCESS		not-accessible
		STATUS		mandatory
		DESCRIPTION	"Frequency Setting No.1/No.2 Table Entry"
		INDEX		{
						ppMxiviFreqSettingIndvPasoIndex,
						ppMxiviFreqSettingIndvIndex
					}
		::= { ppMxiviFreqSettingIndvTable 1 }

	PpMxiviFreqSettingIndvEntry ::= SEQUENCE {
					  ppMxiviFreqSettingIndvPasoIndex  IpAddress,
					  ppMxiviFreqSettingIndvIndex      INTEGER,
					  ppMxiviFreqSettingTxFreq         DisplayString,
					  ppMxiviFreqSettingRxFreq         DisplayString,
					  ppMxiviFreqSettingShiftFreq      DisplayString,
					  ppMxiviFreqSettingSubBand        DisplayString
					}

	ppMxiviFreqSettingIndvPasoIndex OBJECT-TYPE
		SYNTAX		IpAddress 
		ACCESS		read-only
		STATUS		mandatory
		DESCRIPTION	"Pasolink IP Address Index"
		::= { ppMxiviFreqSettingIndvEntry 1 }
		
	ppMxiviFreqSettingIndvIndex OBJECT-TYPE
		SYNTAX		INTEGER {
					  no1(1),
					  no2(2)
					}
		ACCESS		read-only
		STATUS		mandatory
		DESCRIPTION	"Index
					1:No.1, 2:No.2"
		::= { ppMxiviFreqSettingIndvEntry 2 }

	ppMxiviFreqSettingTxFreq OBJECT-TYPE
		SYNTAX		DisplayString
		ACCESS		read-only
		STATUS		mandatory
		DESCRIPTION	"Tx Frequency[MHz]
					VARSZ=9
					FLAG=TRAP|EVLOG|BITCNT(72)
					LOGITEM='TX FREQUENCY [MHz]'
					LOGSTATUS='%s'
					LOGFLAG='LII_S_STR|LII_I_SYSTEM'
					TRAP=eventTrapPpMxTxFreq"
		::= { ppMxiviFreqSettingIndvEntry 3 }

	ppMxiviFreqSettingRxFreq OBJECT-TYPE
		SYNTAX		DisplayString
		ACCESS		read-only
		STATUS		mandatory
		DESCRIPTION	"Rx Frequency[MHz]
					VARSZ=9
					FLAG=TRAP|EVLOG|BITCNT(72)
					LOGITEM='RX FREQUENCY [MHz]'
					LOGSTATUS='%s'
					LOGFLAG='LII_S_STR|LII_I_SYSTEM'
					TRAP=eventTrapPpMxRxFreq"
		::= { ppMxiviFreqSettingIndvEntry 4 }

	ppMxiviFreqSettingShiftFreq OBJECT-TYPE
		SYNTAX		DisplayString
		ACCESS		read-only
		STATUS		mandatory
		DESCRIPTION	"Shift Frequency[MHz]
					VARSZ=8
					FLAG=TRAP|EVLOG|NONTC_GROBAL|BITCNT(64)
					LOGITEM='SHIFT FREQUENCY [MHz]'
					LOGSTATUS='%s'
					LOGFLAG='LII_S_STR|LII_I_SYSTEM'
					TRAP=eventTrapPpMxShiftFreq"
		::= { ppMxiviFreqSettingIndvEntry 5 }

	ppMxiviFreqSettingSubBand OBJECT-TYPE
		SYNTAX		DisplayString
		ACCESS		read-only
		STATUS		mandatory
		DESCRIPTION	"SUB BAND
					1 ascii character
					
					VARSZ=1
					FLAG=TRAP|EVLOG|BITCNT(8)
					LOGITEM='SUB BAND'
					LOGSTATUS='%s'
					LOGFLAG='LII_S_STR|LII_I_SYSTEM'
					TRAP=eventTrapPpMxSubBand"
		::= { ppMxiviFreqSettingIndvEntry 6 }

	ppMxiviOduProvInfo OBJECT IDENTIFIER
		::= { ppMxInventoryInfo 5 }

	ppMxiviOduProvIndvTable OBJECT-TYPE
		SYNTAX		SEQUENCE OF PpMxiviOduProvIndvEntry
		ACCESS		not-accessible
		STATUS		mandatory
		DESCRIPTION	"ODU Provisioning No.1/No.2 Table"
		::= { ppMxiviOduProvInfo 1 }

	ppMxiviOduProvIndvEntry OBJECT-TYPE
		SYNTAX		PpMxiviOduProvIndvEntry
		ACCESS		not-accessible
		STATUS		mandatory
		DESCRIPTION	"ODU Provisioning No.1/No.2 Table Entry"
		INDEX		{
						ppMxiviOduProvIndvPasoIndex,
						ppMxiviOduProvIndvIndex
					}
		::= { ppMxiviOduProvIndvTable 1 }

	PpMxiviOduProvIndvEntry ::= SEQUENCE {
					  ppMxiviOduProvIndvPasoIndex         IpAddress,
					  ppMxiviOduProvIndvIndex             INTEGER,
					  ppMxiviOduProvAtpcMax               INTEGER,
					  ppMxiviOduProvAtpcMin               INTEGER,
					  ppMxiviOduProvMtpcMax               INTEGER,
					  ppMxiviOduProvMtpcMin               INTEGER,
					  ppMxiviOduProvRxThresholdMax        INTEGER,
					  ppMxiviOduProvRxThresholdMin        INTEGER,
					  ppMxiviOduProvAdditionalAttMax      INTEGER,
					  ppMxiviOduProvAdditionalAttMin      INTEGER
					}

	ppMxiviOduProvIndvPasoIndex OBJECT-TYPE
		SYNTAX		IpAddress 
		ACCESS		read-only
		STATUS		mandatory
		DESCRIPTION	"Pasolink IP Address Index"
		::= { ppMxiviOduProvIndvEntry 1 }
		
	ppMxiviOduProvIndvIndex OBJECT-TYPE
		SYNTAX		INTEGER {
					  no1(1),
					  no2(2)
					}
		ACCESS		read-only
		STATUS		mandatory
		DESCRIPTION	"Index
					1:No.1, 2:No.2"
		::= { ppMxiviOduProvIndvEntry 2 }

	ppMxiviOduProvAtpcMax OBJECT-TYPE
		SYNTAX		INTEGER
		ACCESS		read-only
		STATUS		mandatory
		DESCRIPTION	"ATPC MAX(dB)
					
					
					FLAG=BITCNT(8)"
		::= { ppMxiviOduProvIndvEntry 3 }

	ppMxiviOduProvAtpcMin OBJECT-TYPE
		SYNTAX		INTEGER
		ACCESS		read-only
		STATUS		mandatory
		DESCRIPTION	"ATPC MIN(dB)
					
					
					FLAG=BITCNT(8)"
		::= { ppMxiviOduProvIndvEntry 4 }

	ppMxiviOduProvMtpcMax OBJECT-TYPE
		SYNTAX		INTEGER
		ACCESS		read-only
		STATUS		mandatory
		DESCRIPTION	"MTPC MAX(dB)
					
					
					FLAG=BITCNT(8)"
		::= { ppMxiviOduProvIndvEntry 5 }

	ppMxiviOduProvMtpcMin OBJECT-TYPE
		SYNTAX		INTEGER
		ACCESS		read-only
		STATUS		mandatory
		DESCRIPTION	"MTPC MIN(dB)
					
					FLAG=BITCNT(8)"
		::= { ppMxiviOduProvIndvEntry 6 }

	ppMxiviOduProvRxThresholdMax OBJECT-TYPE
		SYNTAX		INTEGER
		ACCESS		read-only
		STATUS		mandatory
		DESCRIPTION	"RX Threshold MAX(dB)
					
					
					FLAG=BITCNT(8)"
		::= { ppMxiviOduProvIndvEntry 7 }

	ppMxiviOduProvRxThresholdMin OBJECT-TYPE
		SYNTAX		INTEGER
		ACCESS		read-only
		STATUS		mandatory
		DESCRIPTION	"RX Threshold MIN(dB)
					
					
					FLAG=BITCNT(8)"
		::= { ppMxiviOduProvIndvEntry 8 }

	ppMxiviOduProvAdditionalAttMax OBJECT-TYPE
		SYNTAX		INTEGER
		ACCESS		read-only
		STATUS		mandatory
		DESCRIPTION	"Additional ATT MAX(dB)
					
					
					FLAG=BITCNT(8)"
		::= { ppMxiviOduProvIndvEntry 9 }

	ppMxiviOduProvAdditionalAttMin OBJECT-TYPE
		SYNTAX		INTEGER
		ACCESS		read-only
		STATUS		mandatory
		DESCRIPTION	"Additional ATT MIN(dB)
					
					
					FLAG=BITCNT(8)"
		::= { ppMxiviOduProvIndvEntry 10 }

	ppMxiviPldCmnTable OBJECT-TYPE
		SYNTAX		SEQUENCE OF PpMxiviPldCmnEntry
		ACCESS		not-accessible
		STATUS		mandatory
		DESCRIPTION	"PLD Common Table"
		::= { ppMxInventoryInfo 6 }

	ppMxiviPldCmnEntry OBJECT-TYPE
		SYNTAX		PpMxiviPldCmnEntry
		ACCESS		not-accessible
		STATUS		mandatory
		DESCRIPTION	"PLD Common Table Entry"
		INDEX		{
						ppMxiviPldCmnPasoIndex,
						ppMxiviPldCmnIndex
					}
		::= { ppMxiviPldCmnTable 1 }

	PpMxiviPldCmnEntry ::= SEQUENCE {
					  ppMxiviPldCmnPasoIndex       IpAddress,
					  ppMxiviPldCmnIndex           INTEGER,
					  ppMxiviPldCmnProgramNo       DisplayString,
					  ppMxiviPldCmnProgramVersion  DisplayString,
					  ppMxiviPldCmnName            DisplayString
					}

	ppMxiviPldCmnPasoIndex OBJECT-TYPE
		SYNTAX		IpAddress 
		ACCESS		read-only
		STATUS		mandatory
		DESCRIPTION	"Pasolink IP Address Index"
		::= { ppMxiviPldCmnEntry 1 }
		
	ppMxiviPldCmnIndex OBJECT-TYPE
		SYNTAX		INTEGER {
					  pldInf(1),
					  pldCtrl(2),
					  pldCpuSub(3),
					  pldCnfg(4)
					}
		ACCESS		read-only
		STATUS		mandatory
		DESCRIPTION	"PLD Common INVENTORY INDEX"
		::= { ppMxiviPldCmnEntry 2 }

	ppMxiviPldCmnProgramNo OBJECT-TYPE
		SYNTAX		DisplayString
		ACCESS		read-only
		STATUS		mandatory
		DESCRIPTION	"ProgramNo
					VARSZ=8
					FLAG=BITCNT(64)"
		::= { ppMxiviPldCmnEntry 3 }

	ppMxiviPldCmnProgramVersion OBJECT-TYPE
		SYNTAX		DisplayString
					
		ACCESS		read-only
		STATUS		mandatory
		DESCRIPTION	"ProgramVersion
					ex)1.00
					VARSZ=8
					FLAG=BITCNT(64)"
		::= { ppMxiviPldCmnEntry 4 }

	ppMxiviPldCmnName OBJECT-TYPE
		SYNTAX		DisplayString
		ACCESS		read-only
		STATUS		mandatory
		DESCRIPTION	"Name
					VARSZ=8
					FLAG=BITCNT(64)"
		::= { ppMxiviPldCmnEntry 5 }

	ppMxiviPldDpuTable OBJECT-TYPE
		SYNTAX		SEQUENCE OF PpMxiviPldDpuEntry
		ACCESS		not-accessible
		STATUS		mandatory
		DESCRIPTION	"PLD DPU Table"
		::= { ppMxInventoryInfo 7 }

	ppMxiviPldDpuEntry OBJECT-TYPE
		SYNTAX		PpMxiviPldDpuEntry
		ACCESS		not-accessible
		STATUS		mandatory
		DESCRIPTION	"PLD DPU Table Entry"
		INDEX		{
						ppMxiviPldDpuPasoIndex,
						ppMxiviPldDpuIndex
					}
		::= { ppMxiviPldDpuTable 1 }

	PpMxiviPldDpuEntry ::= SEQUENCE {
					  ppMxiviPldDpuPasoIndex       IpAddress,
					  ppMxiviPldDpuIndex           INTEGER,
					  ppMxiviPldDpuProgramNo       DisplayString,
					  ppMxiviPldDpuProgramVersion  DisplayString
					,
					  ppMxiviPldDpuName            DisplayString
					}

	ppMxiviPldDpuPasoIndex OBJECT-TYPE
		SYNTAX		IpAddress 
		ACCESS		read-only
		STATUS		mandatory
		DESCRIPTION	"Pasolink IP Address Index"
		::= { ppMxiviPldDpuEntry 1 }
		
	ppMxiviPldDpuIndex OBJECT-TYPE
		SYNTAX		INTEGER {
					  pldDpu1(1),
					  pldDpu2(2)
					}
		ACCESS		read-only
		STATUS		mandatory
		DESCRIPTION	"PLD Dpu INVENTORY INDEX"
		::= { ppMxiviPldDpuEntry 2 }

	ppMxiviPldDpuProgramNo OBJECT-TYPE
		SYNTAX		DisplayString
		ACCESS		read-only
		STATUS		mandatory
		DESCRIPTION	"ProgramNo
					VARSZ=8
					FLAG=BITCNT(64)"
		::= { ppMxiviPldDpuEntry 3 }

	ppMxiviPldDpuProgramVersion OBJECT-TYPE
		SYNTAX		DisplayString
					
		ACCESS		read-only
		STATUS		mandatory
		DESCRIPTION	"ProgramVersion
					ex)1.00
					VARSZ=8
					FLAG=BITCNT(64)"
		::= { ppMxiviPldDpuEntry 4 }

	ppMxiviPldDpuName OBJECT-TYPE
		SYNTAX		DisplayString
		ACCESS		read-only
		STATUS		mandatory
		DESCRIPTION	"Name
					VARSZ=8
					FLAG=BITCNT(64)"
		::= { ppMxiviPldDpuEntry 5 }

	ppMxiviPldLanTable OBJECT-TYPE
		SYNTAX		SEQUENCE OF PpMxiviPldLanEntry
		ACCESS		not-accessible
		STATUS		mandatory
		DESCRIPTION	"PLD LAN Table"
		::= { ppMxInventoryInfo 8 }

	ppMxiviPldLanEntry OBJECT-TYPE
		SYNTAX		PpMxiviPldLanEntry
		ACCESS		not-accessible
		STATUS		mandatory
		DESCRIPTION	"PLD LAN Table Entry"
		INDEX		{
						ppMxiviPldLanPasoIndex,
						ppMxiviPldLanIndex
					}
		::= { ppMxiviPldLanTable 1 }

	PpMxiviPldLanEntry ::= SEQUENCE {
					  ppMxiviPldLanPasoIndex       IpAddress,
					  ppMxiviPldLanIndex           INTEGER,
					  ppMxiviPldLanProgramNo       DisplayString,
					  ppMxiviPldLanProgramVersion  DisplayString,
					  ppMxiviPldLanName            DisplayString
					}
					
	ppMxiviPldLanPasoIndex OBJECT-TYPE
		SYNTAX		IpAddress 
		ACCESS		read-only
		STATUS		mandatory
		DESCRIPTION	"Pasolink IP Address Index"
		::= { ppMxiviPldLanEntry 1 }
		
	ppMxiviPldLanIndex OBJECT-TYPE
		SYNTAX		INTEGER {
					  pld2pLan(1),
					  pld4pLan(2)
					}
		ACCESS		read-only
		STATUS		mandatory
		DESCRIPTION	"PLD Lan INVENTORY INDEX"
		::= { ppMxiviPldLanEntry 2 }

	ppMxiviPldLanProgramNo OBJECT-TYPE
		SYNTAX		DisplayString
		ACCESS		read-only
		STATUS		mandatory
		DESCRIPTION	"ProgramNo
					VARSZ=8
					FLAG=BITCNT(64)"
		::= { ppMxiviPldLanEntry 3 }

	ppMxiviPldLanProgramVersion OBJECT-TYPE
		SYNTAX		DisplayString
					
		ACCESS		read-only
		STATUS		mandatory
		DESCRIPTION	"ProgramVersion
					ex)1.00
					VARSZ=8
					FLAG=BITCNT(64)"
		::= { ppMxiviPldLanEntry 4 }

	ppMxiviPldLanName OBJECT-TYPE
		SYNTAX		DisplayString
		ACCESS		read-only
		STATUS		mandatory
		DESCRIPTION	"Name
					VARSZ=8
					FLAG=BITCNT(64)"
		::= { ppMxiviPldLanEntry 5 }

	ppMxiviPldMdromTable OBJECT-TYPE
		SYNTAX		SEQUENCE OF PpMxiviPldMdromEntry
		ACCESS		not-accessible
		STATUS		optional
		DESCRIPTION	"PLD Mdrom INVENTORY information table"
		::= { ppMxInventoryInfo 9 }

	ppMxiviPldMdromEntry OBJECT-TYPE
		SYNTAX		PpMxiviPldMdromEntry
		ACCESS		not-accessible
		STATUS		optional
		DESCRIPTION	"PLD Mdrom INVENTORY information table entry"
		INDEX		{
					ppMxiviPldMdromPasoIndex,
					ppMxiviPldMdromIndex
					}
		::= { ppMxiviPldMdromTable 1 }

	PpMxiviPldMdromEntry ::= SEQUENCE {
					  ppMxiviPldMdromPasoIndex       IpAddress,	
					  ppMxiviPldMdromIndex           INTEGER,
					  ppMxiviPldMdromProgramNo       DisplayString,
					  ppMxiviPldMdromProgramVersion  DisplayString,
					  ppMxiviPldMdromName            DisplayString
					 }					  
					         
	ppMxiviPldMdromPasoIndex OBJECT-TYPE
		SYNTAX		IpAddress 
		ACCESS		read-only
		STATUS		mandatory
		DESCRIPTION	"Pasolink IP Address index"
		::= { ppMxiviPldMdromEntry 1 }

	ppMxiviPldMdromIndex OBJECT-TYPE
		SYNTAX		INTEGER {
					  pldMdrom1(1),
					  pldMdrom2(2)
					}
		ACCESS		read-only
		STATUS		mandatory
		DESCRIPTION	"PLD Mdrom INVENTORY INDEX"
		::= { ppMxiviPldMdromEntry 2 }

	ppMxiviPldMdromProgramNo OBJECT-TYPE
		SYNTAX		DisplayString
		ACCESS		read-only
		STATUS		mandatory
		DESCRIPTION	"ProgramNo
					VARSZ=8
					FLAG=BITCNT(64)"
		::= { ppMxiviPldMdromEntry 3 }

	ppMxiviPldMdromProgramVersion OBJECT-TYPE
		SYNTAX		DisplayString
					
		ACCESS		read-only
		STATUS		mandatory
		DESCRIPTION	"ProgramVersion
					ex)1.00
					VARSZ=8
					FLAG=BITCNT(64)"
		::= { ppMxiviPldMdromEntry 4 }

	ppMxiviPldMdromName OBJECT-TYPE
		SYNTAX		DisplayString
		ACCESS		read-only
		STATUS		mandatory
		DESCRIPTION	"Name
					VARSZ=8
					FLAG=BITCNT(64)"
		::= { ppMxiviPldMdromEntry 5 }

-----------------------------------------------
-- ppMxMeteringInfo Group Definitions
-----------------------------------------------

	ppMxmdiIndvTable OBJECT-TYPE
		SYNTAX		SEQUENCE OF PpMxmdiIndvEntry
		ACCESS		not-accessible
		STATUS		mandatory
		DESCRIPTION	"Metering No.1/No.2 Table"
		::= { ppMxMeteringInfo 1 }

	ppMxmdiIndvEntry OBJECT-TYPE
		SYNTAX		PpMxmdiIndvEntry
		ACCESS		not-accessible
		STATUS		mandatory
		DESCRIPTION	"Metering No.1/No.2 Table Entry"
		INDEX		{
						ppMxmdiIndvPasoIndex,
						ppMxmdiIndvIndex
					}
		::= { ppMxmdiIndvTable 1 }

	PpMxmdiIndvEntry ::= SEQUENCE {
					  ppMxmdiIndvPasoIndex  IpAddress,
					  ppMxmdiIndvIndex      INTEGER,
					  ppMxmdiTxPower        DisplayString,
					  ppMxmdiRxLevel        DisplayString,
					  ppMxmdiOduPs          DisplayString
					}

        ppMxmdiIndvPasoIndex OBJECT-TYPE
		SYNTAX		IpAddress 
		ACCESS		read-only
		STATUS		mandatory
		DESCRIPTION	"Pasolink IP Address Index"
		::= { ppMxmdiIndvEntry 1 }

	ppMxmdiIndvIndex OBJECT-TYPE
		SYNTAX		INTEGER {
					  no-1(1),
					  no-2(2)
					}
		ACCESS		read-only
		STATUS		mandatory
		DESCRIPTION	"Indv index"
		::= { ppMxmdiIndvEntry 2 }

	ppMxmdiTxPower OBJECT-TYPE
		SYNTAX		DisplayString
		ACCESS		read-only
		STATUS		mandatory
		DESCRIPTION	"TX Power [dBm]"
		::= { ppMxmdiIndvEntry 3 }

	ppMxmdiRxLevel OBJECT-TYPE
		SYNTAX	        DisplayString
		ACCESS		read-only
		STATUS		mandatory
		DESCRIPTION	"RX Level [dBm]"
		::= { ppMxmdiIndvEntry 4 }

	ppMxmdiOduPs OBJECT-TYPE
		SYNTAX		DisplayString
		ACCESS		read-only
		STATUS		mandatory
		DESCRIPTION	"ODU PS [V]"
		::= { ppMxmdiIndvEntry 5 }

-----------------------------------------------
-- Mx BER Table
-----------------------------------------------

	ppMxmdiBerTable OBJECT-TYPE
		SYNTAX		SEQUENCE OF PpMxmdiBerEntry
		ACCESS		not-accessible
		STATUS		mandatory
		DESCRIPTION	"Metering BER Table"
		::= { ppMxMeteringInfo 2 }

	ppMxmdiBerEntry OBJECT-TYPE
		SYNTAX		PpMxmdiBerEntry
		ACCESS		not-accessible
		STATUS		mandatory
		DESCRIPTION	"Metering BER Table Entry"
		INDEX		{
						ppMxmdiBerPasoIndex
					}
		::= { ppMxmdiBerTable 1 }

	PpMxmdiBerEntry ::= SEQUENCE {
					  ppMxmdiBerPasoIndex  IpAddress,
					  ppMxmdiBer           DisplayString           
					}

        ppMxmdiBerPasoIndex OBJECT-TYPE
		SYNTAX		IpAddress 
		ACCESS		read-only
		STATUS		mandatory
		DESCRIPTION	"Pasolink IP Address Index"
		::= { ppMxmdiBerEntry 1 }

	ppMxmdiBer OBJECT-TYPE
		SYNTAX		DisplayString
		ACCESS		read-only
		STATUS		mandatory
		DESCRIPTION	"Ber"
		::= { ppMxmdiBerEntry 2 }


-----------------------------------------------
-- ppMxPmonInfo Group Definitions
-----------------------------------------------

	ppMxpmDailyData OBJECT IDENTIFIER
		::= { ppMxPmonInfo 1 }

	ppMxpmDailyDataInfo OBJECT IDENTIFIER
		::= { ppMxpmDailyData 1 }
		
	ppMxpmDailyDataInfoTable OBJECT-TYPE
		SYNTAX		SEQUENCE OF PpMxpmDailyDataInfoEntry
		ACCESS		not-accessible
		STATUS		optional
		DESCRIPTION	"Pmon Daily Data Information Table"
		::= { ppMxpmDailyDataInfo 1 }

	ppMxpmDailyDataInfoEntry OBJECT-TYPE
		SYNTAX		PpMxpmDailyDataInfoEntry
		ACCESS		not-accessible
		STATUS		optional
		DESCRIPTION	"Pmon Daily Data Information Table Entry"
		INDEX		{
					ppMxpmDailyDataInfoPasoIndex
					}
		::= { ppMxpmDailyDataInfoTable 1 }

	PpMxpmDailyDataInfoEntry ::= SEQUENCE {
					  ppMxpmDailyDataInfoPasoIndex    IpAddress,	
					  ppMxpmDailyStatus               INTEGER
					 }					  
					         
	ppMxpmDailyDataInfoPasoIndex OBJECT-TYPE
		SYNTAX		IpAddress 
		ACCESS		read-only
		STATUS		mandatory
		DESCRIPTION	"Pasolink IP Address Index"
		::= { ppMxpmDailyDataInfoEntry 1 }

	ppMxpmDailyStatus OBJECT-TYPE
		SYNTAX		INTEGER ( 0..4 )
					
		ACCESS		read-only
		STATUS		mandatory
		DESCRIPTION	"PM STATUS
					  not_obtain(0),
					  valid_not_maint(1),
					  valid_maint(2),
					  invalid_not_maint(3),
					  invalid_maint(4)"
		::= { ppMxpmDailyDataInfoEntry 2 }

	ppMxpmDailyDataValue OBJECT IDENTIFIER
		::= { ppMxpmDailyData 2 }

	ppMxpmDailyDataTable OBJECT-TYPE
		SYNTAX		SEQUENCE OF PpMxpmDailyDataEntry
		ACCESS		not-accessible
		STATUS		mandatory
		DESCRIPTION	"Pmon Daily Data Value Table"
		::= { ppMxpmDailyDataValue 1 }

	ppMxpmDailyDataEntry OBJECT-TYPE
		SYNTAX		PpMxpmDailyDataEntry
		ACCESS		not-accessible
		STATUS		mandatory
		DESCRIPTION	"Pmon Daily Data Value Table Entry"
		INDEX		{
						ppMxpmDailyDataPasoIndex,
						ppMxpmDailyItemName
					}
		::= { ppMxpmDailyDataTable 1 }

	PpMxpmDailyDataEntry ::= SEQUENCE {
					  ppMxpmDailyDataPasoIndex    IpAddress,
					  ppMxpmDailyItemName         INTEGER,
					  ppMxpmDailyCurrentData      INTEGER,
					  ppMxpmDailyCurrentAlarm     NormalAlarm01Value,
					  ppMxpmDailyHistoricalAlarm  INTEGER
					}

	ppMxpmDailyDataPasoIndex OBJECT-TYPE
		SYNTAX		IpAddress 
		ACCESS		read-only
		STATUS		mandatory
		DESCRIPTION	"Pasolink IP Address Index"
		::= { ppMxpmDailyDataEntry 1 }
		
	ppMxpmDailyItemName OBJECT-TYPE
		SYNTAX		INTEGER {
					  pmonOFS(1),
					  pmonES(2),
					  pmonSES(3),
					  pmonUAS(4),
					  pmonBBE(5)
					}
		ACCESS		read-only
		STATUS		mandatory
		DESCRIPTION	"PMON DAILY INDEX"
		::= { ppMxpmDailyDataEntry 2 }

	ppMxpmDailyCurrentData OBJECT-TYPE
		SYNTAX		INTEGER
		ACCESS		read-only
		STATUS		mandatory
		DESCRIPTION	"DailyCurrentData"
		::= { ppMxpmDailyDataEntry 3 }

	ppMxpmDailyCurrentAlarm OBJECT-TYPE
		SYNTAX		NormalAlarm01Value
		ACCESS		read-only
		STATUS		mandatory
		DESCRIPTION	"0:INVALID, 1:Normal, 2:Alarm
					FLAG=TRAP|EVLOG
					LOGITEM='%s TCN(15min)'
					LOGSTATUS='INVALID(0),NORMAL(1),ALARM(2)'
					LOGFLAG='LII_I_PMON_NAME_TOTAL'
					TRAP=alarmTrapPpMxTcnDaily"
		::= { ppMxpmDailyDataEntry 4 }

	ppMxpmDailyHistoricalAlarm OBJECT-TYPE
		SYNTAX		INTEGER
		ACCESS		read-only
		STATUS		mandatory
		DESCRIPTION	"Daily historical alarm
					1Bit per day is used for the alarm status as follows.
					  0 Bit: (Not used for Mx, Used for  NLite L)
					  1 Bit: 1st older Daily data (Usually yesterday)
					  N Bit: Nth older Daily data (Usually N days before)
					Meaning of status
					  0 : No alarm
					  1 : Alarm
					Max 7days data are kept, lower 8 bits are used.
					'0' is set in 9th bit and higher.
					"
		::= { ppMxpmDailyDataEntry 5 }
		
	ppMxpmWeeklyData OBJECT IDENTIFIER
		::= { ppMxPmonInfo 2 }

	ppMxpmWeeklyDataInfo OBJECT IDENTIFIER
		::= { ppMxpmWeeklyData 1 }

	ppMxpmWeeklyDataInfoTable OBJECT-TYPE
		SYNTAX		SEQUENCE OF PpMxpmWeeklyDataInfoEntry
		ACCESS		not-accessible
		STATUS		optional
		DESCRIPTION	"Pmon Weekly Data Information Table"
		::= { ppMxpmWeeklyDataInfo 1 }

	ppMxpmWeeklyDataInfoEntry OBJECT-TYPE
		SYNTAX		PpMxpmWeeklyDataInfoEntry
		ACCESS		not-accessible
		STATUS		optional
		DESCRIPTION	"Pmon Weekly Data Information Table Entry"
		INDEX		{
					ppMxpmWeeklyDataInfoPasoIndex
					}
		::= { ppMxpmWeeklyDataInfoTable 1 }

	PpMxpmWeeklyDataInfoEntry ::= SEQUENCE {
					  ppMxpmWeeklyDataInfoPasoIndex    IpAddress,	
					  ppMxpmWeeklyStatus               INTEGER
					 }					  
					         
	ppMxpmWeeklyDataInfoPasoIndex OBJECT-TYPE
		SYNTAX		IpAddress 
		ACCESS		read-only
		STATUS		mandatory
		DESCRIPTION	"Pasolink IP Address Index"
		::= { ppMxpmWeeklyDataInfoEntry 1 }

	ppMxpmWeeklyStatus OBJECT-TYPE
		SYNTAX		INTEGER ( 0..4 )
					
		ACCESS		read-only
		STATUS		mandatory
		DESCRIPTION	"PM STATUS
					  not_obtain(0),
					  valid_not_maint(1),
					  valid_maint(2),
					  invalid_not_maint(3),
					  invalid_maint(4)"
		::= { ppMxpmWeeklyDataInfoEntry 2 }

	ppMxpmWeeklyDataValue OBJECT IDENTIFIER
		::= { ppMxpmWeeklyData 2 }

	ppMxpmWeeklyDataTable OBJECT-TYPE
		SYNTAX		SEQUENCE OF PpMxpmWeeklyDataEntry
		ACCESS		not-accessible
		STATUS		mandatory
		DESCRIPTION	"Pmon Weekly Data Value Table"
		::= { ppMxpmWeeklyDataValue 1 }

	ppMxpmWeeklyDataEntry OBJECT-TYPE
		SYNTAX		PpMxpmWeeklyDataEntry
		ACCESS		not-accessible
		STATUS		mandatory
		DESCRIPTION	"Pmon Weekly Data Value Table Entry"
		INDEX		{
						ppMxpmWeeklyDataPasoIndex,
						ppMxpmWeeklyItemName
					}
		::= { ppMxpmWeeklyDataTable 1 }

	PpMxpmWeeklyDataEntry ::= SEQUENCE {
					  ppMxpmWeeklyDataPasoIndex    IpAddress,
					  ppMxpmWeeklyItemName         INTEGER,
					  ppMxpmWeeklyCurrentData      INTEGER,
					  ppMxpmWeeklyCurrentAlarm     NormalAlarm01Value,
					  ppMxpmWeeklyHistoricalAlarm  INTEGER
					}

	ppMxpmWeeklyDataPasoIndex OBJECT-TYPE
		SYNTAX		IpAddress 
		ACCESS		read-only
		STATUS		mandatory
		DESCRIPTION	"Pasolink IP Address Index"
		::= { ppMxpmWeeklyDataEntry 1 }

	ppMxpmWeeklyItemName OBJECT-TYPE
		SYNTAX		INTEGER {
					  pmonOFS(1),
					  pmonES(2),
					  pmonSES(3),
					  pmonUAS(4),
					  pmonBBE(5)
					}
		ACCESS		read-only
		STATUS		mandatory
		DESCRIPTION	"PMON WEEKLY INDEX"
		::= { ppMxpmWeeklyDataEntry 2 }

	ppMxpmWeeklyCurrentData OBJECT-TYPE
		SYNTAX		INTEGER
		ACCESS		read-only
		STATUS		mandatory
		DESCRIPTION	"WeeklyCurrentData"
		::= { ppMxpmWeeklyDataEntry 3 }

	ppMxpmWeeklyCurrentAlarm OBJECT-TYPE
		SYNTAX		NormalAlarm01Value
		ACCESS		read-only
		STATUS		mandatory
		DESCRIPTION	"0:INVALID, 1:Normal, 2:Alarm
					FLAG=TRAP|EVLOG
					LOGITEM='%s TCN(1day)'
					LOGSTATUS='INVALID(0),NORMAL(1),ALARM(2)'
					LOGFLAG='LII_I_PMON_NAME_TOTAL'
					TRAP=alarmTrapPpMxTcnWeekly"
		::= { ppMxpmWeeklyDataEntry 4 }

	ppMxpmWeeklyHistoricalAlarm OBJECT-TYPE
		SYNTAX		INTEGER
		ACCESS		read-only
		STATUS		mandatory
		DESCRIPTION	"Weekly historical alarm
					1Bit per day is used for the alarm status as follows.
					  0 Bit: (Not used )
					  1 Bit: 1st older Daily data (Usually yesterday)
					  N Bit: Nth older Daily data (Usually N days before)
					Meaning of status
					  0 : No alarm
					  1 : Alarm
					Max 7days data are kept, lower 8 bits are used.
					'0' is set in 9th bit and higher.
					"
		::= { ppMxpmWeeklyDataEntry 5 }

	ppMxpmRmonDailyData OBJECT IDENTIFIER
		::= { ppMxPmonInfo 3 }

	ppMxpmRmonDailyIntfcMData OBJECT IDENTIFIER
		::= { ppMxpmRmonDailyData 1 }

	ppMxpmRmonDailyIntfcMInfoDataTable OBJECT-TYPE
		SYNTAX		SEQUENCE OF PpMxpmRmonDailyIntfcMInfoDataEntry
		ACCESS		not-accessible
		STATUS		mandatory
		DESCRIPTION	"ppMxpmRmonDailyIntfcMInfoDataTable
					TABSZ=8"
		::= { ppMxpmRmonDailyIntfcMData 1 }

	ppMxpmRmonDailyIntfcMInfoDataEntry OBJECT-TYPE
		SYNTAX		PpMxpmRmonDailyIntfcMInfoDataEntry
		ACCESS		not-accessible
		STATUS		mandatory
		DESCRIPTION	"ppMxpmRmonDailyIntfcMInfoDataEntry"
		INDEX		{
					  ppMxpmRmonDailyIntfcMInfoPasoIndex,	
					  ppMxpmRmonDailyIntfcMInfoPortName
					}
		::= { ppMxpmRmonDailyIntfcMInfoDataTable 1 }

	PpMxpmRmonDailyIntfcMInfoDataEntry ::= SEQUENCE {
					  ppMxpmRmonDailyIntfcMInfoPasoIndex  IpAddress,
					  ppMxpmRmonDailyIntfcMInfoPortName   INTEGER,
					  ppMxpmRmonDailyIntfcMInfoStatus     INTEGER,
					  ppMxpmRmonDailyIntfcMInfoPortUsage  INTEGER
					}

	ppMxpmRmonDailyIntfcMInfoPasoIndex OBJECT-TYPE
		SYNTAX		IpAddress 
		ACCESS		read-only
		STATUS		mandatory
		DESCRIPTION	"(Not used) Pasolink IP Address Index"
		::= { ppMxpmRmonDailyIntfcMInfoDataEntry 1 }
		
	ppMxpmRmonDailyIntfcMInfoPortName OBJECT-TYPE
		SYNTAX		INTEGER {
					  linePort1(1),
					  linePort2(2),
					  linePort3(3),
					  linePort4(4),
					  dmrPort1(5),
					  dmrPort2(6),
					  dmrPort3(7),
					  dmrPort4(8)
					}
		ACCESS		read-only
		STATUS		mandatory
		DESCRIPTION	"(Not used) Rmon PORT INDEX(IntfcMInfo)
					1:LINE PORT1
					2:LINE PORT2
					3:LINE PORT3
					4:LINE PORT4
					5:DMR PORT1
					6:DMR PORT2
					7:DMR PORT3
					8:DMR PORT4"
		::= { ppMxpmRmonDailyIntfcMInfoDataEntry 2 }

	ppMxpmRmonDailyIntfcMInfoStatus OBJECT-TYPE
		SYNTAX		INTEGER ( 0..4 )
					
		ACCESS		read-only
		STATUS		mandatory
		DESCRIPTION	" (Not used) STATUS
					  not_obtain(0),
					  valid_not_maint(1),
					  valid_maint(2),
					  invalid_not_maint(3),
					  invalid_maint(4)"
		::= { ppMxpmRmonDailyIntfcMInfoDataEntry 3 }

	ppMxpmRmonDailyIntfcMInfoPortUsage OBJECT-TYPE
		SYNTAX		INTEGER ( 0..2 )
					
		ACCESS		read-only
		STATUS		mandatory
		DESCRIPTION	"(Not used) PORT USAGE
					  Invalid(0),
					  used(1),
					  not_used(2)
					"
		::= { ppMxpmRmonDailyIntfcMInfoDataEntry 4 }

	ppMxpmRmonDailyIntfcMDataTable OBJECT-TYPE
		SYNTAX		SEQUENCE OF PpMxpmRmonDailyIntfcMDataEntry
		ACCESS		not-accessible
		STATUS		mandatory
		DESCRIPTION	"ppMxpmRmonDailyIntfcMDataTable
					TABSZ=8"
		::= { ppMxpmRmonDailyIntfcMData 2 }

	ppMxpmRmonDailyIntfcMDataEntry OBJECT-TYPE
		SYNTAX		PpMxpmRmonDailyIntfcMDataEntry
		ACCESS		not-accessible
		STATUS		mandatory
		DESCRIPTION	"Each item of this table is represented as follows: 
					o OCTET STRING of each value is represented 4byte Interger( little endian ).
					o When a value is overflow, most significant bit is 1.
					"
		INDEX		{
						ppMxpmRmonDailyIntfcMPasoIndex,
						ppMxpmRmonDailyIntfcMPortName
					}
		::= { ppMxpmRmonDailyIntfcMDataTable 1 }

	PpMxpmRmonDailyIntfcMDataEntry ::= SEQUENCE {
					  ppMxpmRmonDailyIntfcMPasoIndex              IpAddress,
					  ppMxpmRmonDailyIntfcMPortName               INTEGER,
					  ppMxpmRmonDailyIntfcMRxUnicast              OCTET STRING,
					  ppMxpmRmonDailyIntfcMRxBroadcast            OCTET STRING,
					  ppMxpmRmonDailyIntfcMRxMulticast            OCTET STRING,
					  ppMxpmRmonDailyIntfcMRxPause                OCTET STRING,
					  ppMxpmRmonDailyIntfcMRxCrcError             OCTET STRING,
					  ppMxpmRmonDailyIntfcMRxFragments            OCTET STRING,
					  ppMxpmRmonDailyIntfcMRx64Octets             OCTET STRING,
					  ppMxpmRmonDailyIntfcMRx65to127Octets        OCTET STRING,
					  ppMxpmRmonDailyIntfcMRx128to255Octets       OCTET STRING,
					  ppMxpmRmonDailyIntfcMRx256to511Octets       OCTET STRING,
					  ppMxpmRmonDailyIntfcMRx512to1023Octets      OCTET STRING,
					  ppMxpmRmonDailyIntfcMRx1024to1536Octets     OCTET STRING,
					  ppMxpmRmonDailyIntfcMRx1537toMaxSizeOctets  OCTET STRING,
					  ppMxpmRmonDailyIntfcMRxJabbers              OCTET STRING,
					  ppMxpmRmonDailyIntfcMTxUnicast              OCTET STRING,
					  ppMxpmRmonDailyIntfcMTxBroadcast            OCTET STRING,
					  ppMxpmRmonDailyIntfcMTxMulticast            OCTET STRING,
					  ppMxpmRmonDailyIntfcMTxPause                OCTET STRING,
					  ppMxpmRmonDailyIntfcMTxTotalCollision       OCTET STRING,
					  ppMxpmRmonDailyIntfcMRxAlignmentError       OCTET STRING,
					  ppMxpmRmonDailyIntfcMRxSymbolError          OCTET STRING,
					  ppMxpmRmonDailyIntfcMRxUndersize            OCTET STRING
					}


	ppMxpmRmonDailyIntfcMPasoIndex OBJECT-TYPE
		SYNTAX		IpAddress 
		ACCESS		read-only
		STATUS		mandatory
		DESCRIPTION	"(Not used) Pasolink IP Address Index"
		::= { ppMxpmRmonDailyIntfcMDataEntry 1 }
		
	ppMxpmRmonDailyIntfcMPortName OBJECT-TYPE
		SYNTAX		INTEGER {
					  linePort1(1),
					  linePort2(2),
					  linePort3(3),
					  linePort4(4),
					  dmrPort1(5),
					  dmrPort2(6),
					  dmrPort3(7),
					  dmrPort4(8)
					}
		ACCESS		read-only
		STATUS		mandatory
		DESCRIPTION	"(Not used) Rmon PORT INDEX(IntfcM)
					1:LINE PORT1
					2:LINE PORT2
					3:LINE PORT3
					4:LINE PORT4
					5:DMR PORT1
					6:DMR PORT2
					7:DMR PORT3
					8:DMR PORT4"
		::= { ppMxpmRmonDailyIntfcMDataEntry 2 }

	ppMxpmRmonDailyIntfcMRxUnicast OBJECT-TYPE
		SYNTAX		OCTET STRING (SIZE (4))
		ACCESS		read-only
		STATUS		mandatory
		DESCRIPTION	"(Not used) ppMxpmRmonDailyIntfcMRxUnicast
					FLAG=BITCNT(32)"
		::= { ppMxpmRmonDailyIntfcMDataEntry 3 }

	ppMxpmRmonDailyIntfcMRxBroadcast OBJECT-TYPE
		SYNTAX		OCTET STRING (SIZE (4))
		ACCESS		read-only
		STATUS		mandatory
		DESCRIPTION	"(Not used) ppMxpmRmonDailyIntfcMRxBroadcast
					FLAG=BITCNT(32)"
		::= { ppMxpmRmonDailyIntfcMDataEntry 4 }

	ppMxpmRmonDailyIntfcMRxMulticast OBJECT-TYPE
		SYNTAX		OCTET STRING (SIZE (4))
		ACCESS		read-only
		STATUS		mandatory
		DESCRIPTION	"(Not used) ppMxpmRmonDailyIntfcMRxMulticast
					FLAG=BITCNT(32)"
		::= { ppMxpmRmonDailyIntfcMDataEntry 5 }

	ppMxpmRmonDailyIntfcMRxPause OBJECT-TYPE
		SYNTAX		OCTET STRING (SIZE (4))
		ACCESS		read-only
		STATUS		mandatory
		DESCRIPTION	"(Not used) ppMxpmRmonDailyIntfcMRxPause
					FLAG=BITCNT(32)"
		::= { ppMxpmRmonDailyIntfcMDataEntry 6 }

	ppMxpmRmonDailyIntfcMRxCrcError OBJECT-TYPE
		SYNTAX		OCTET STRING (SIZE (4))
		ACCESS		read-only
		STATUS		mandatory
		DESCRIPTION	"(Not used) ppMxpmRmonDailyIntfcMRxCrcError
					FLAG=BITCNT(32)"
		::= { ppMxpmRmonDailyIntfcMDataEntry 7 }

	ppMxpmRmonDailyIntfcMRxFragments OBJECT-TYPE
		SYNTAX		OCTET STRING (SIZE (4))
		ACCESS		read-only
		STATUS		mandatory
		DESCRIPTION	"(Not used) ppMxpmRmonDailyIntfcMRxFragments
					FLAG=BITCNT(32)"
		::= { ppMxpmRmonDailyIntfcMDataEntry 8 }

	ppMxpmRmonDailyIntfcMRx64Octets OBJECT-TYPE
		SYNTAX		OCTET STRING (SIZE (4))
		ACCESS		read-only
		STATUS		mandatory
		DESCRIPTION	"(Not used) ppMxpmRmonDailyIntfcMRx64Octets
					FLAG=BITCNT(32)"
		::= { ppMxpmRmonDailyIntfcMDataEntry 9 }

	ppMxpmRmonDailyIntfcMRx65to127Octets OBJECT-TYPE
		SYNTAX		OCTET STRING (SIZE (4))
		ACCESS		read-only
		STATUS		mandatory
		DESCRIPTION	"(Not used) ppMxpmRmonDailyIntfcMRx65to127Octets
					FLAG=BITCNT(32)"
		::= { ppMxpmRmonDailyIntfcMDataEntry 10 }

	ppMxpmRmonDailyIntfcMRx128to255Octets OBJECT-TYPE
		SYNTAX		OCTET STRING (SIZE (4))
		ACCESS		read-only
		STATUS		mandatory
		DESCRIPTION	"(Not used) ppMxpmRmonDailyIntfcMRx128to255Octets
					FLAG=BITCNT(32)"
		::= { ppMxpmRmonDailyIntfcMDataEntry 11 }

	ppMxpmRmonDailyIntfcMRx256to511Octets OBJECT-TYPE
		SYNTAX		OCTET STRING (SIZE (4))
		ACCESS		read-only
		STATUS		mandatory
		DESCRIPTION	"(Not used) ppMxpmRmonDailyIntfcMRx256to511Octets
					FLAG=BITCNT(32)"
		::= { ppMxpmRmonDailyIntfcMDataEntry 12 }

	ppMxpmRmonDailyIntfcMRx512to1023Octets OBJECT-TYPE
		SYNTAX		OCTET STRING (SIZE (4))
		ACCESS		read-only
		STATUS		mandatory
		DESCRIPTION	"(Not used) ppMxpmRmonDailyIntfcMRx512to1023Octets
					FLAG=BITCNT(32)"
		::= { ppMxpmRmonDailyIntfcMDataEntry 13 }

	ppMxpmRmonDailyIntfcMRx1024to1536Octets OBJECT-TYPE
		SYNTAX		OCTET STRING (SIZE (4))
		ACCESS		read-only
		STATUS		mandatory
		DESCRIPTION	"(Not used) ppMxpmRmonDailyIntfcMRx1024to1536Octets
					FLAG=BITCNT(32)"
		::= { ppMxpmRmonDailyIntfcMDataEntry 14 }

	ppMxpmRmonDailyIntfcMRx1537toMaxSizeOctets OBJECT-TYPE
		SYNTAX		OCTET STRING (SIZE (4))
		ACCESS		read-only
		STATUS		mandatory
		DESCRIPTION	"(Not used) ppMxpmRmonDailyIntfcMRx1537toMaxSizeOctets
					FLAG=BITCNT(32)"
		::= { ppMxpmRmonDailyIntfcMDataEntry 15 }

	ppMxpmRmonDailyIntfcMRxJabbers OBJECT-TYPE
		SYNTAX		OCTET STRING (SIZE (4))
		ACCESS		read-only
		STATUS		mandatory
		DESCRIPTION	"(Not used) ppMxpmRmonDailyIntfcMRxJabbers
					FLAG=BITCNT(32)"
		::= { ppMxpmRmonDailyIntfcMDataEntry 16 }

	ppMxpmRmonDailyIntfcMTxUnicast OBJECT-TYPE
		SYNTAX		OCTET STRING (SIZE (4))
		ACCESS		read-only
		STATUS		mandatory
		DESCRIPTION	"(Not used) ppMxpmRmonDailyIntfcMTxUnicast
					FLAG=BITCNT(32)"
		::= { ppMxpmRmonDailyIntfcMDataEntry 17 }

	ppMxpmRmonDailyIntfcMTxBroadcast OBJECT-TYPE
		SYNTAX		OCTET STRING (SIZE (4))
		ACCESS		read-only
		STATUS		mandatory
		DESCRIPTION	"(Notused) ppMxpmRmonDailyIntfcMTxBroadcast
					FLAG=BITCNT(32)"
		::= { ppMxpmRmonDailyIntfcMDataEntry 18 }

	ppMxpmRmonDailyIntfcMTxMulticast OBJECT-TYPE
		SYNTAX		OCTET STRING (SIZE (4))
		ACCESS		read-only
		STATUS		mandatory
		DESCRIPTION	"(Not used) ppMxpmRmonDailyIntfcMTxMulticast
					FLAG=BITCNT(32)"
		::= { ppMxpmRmonDailyIntfcMDataEntry 19 }

	ppMxpmRmonDailyIntfcMTxPause OBJECT-TYPE
		SYNTAX		OCTET STRING (SIZE (4))
		ACCESS		read-only
		STATUS		mandatory
		DESCRIPTION	"(Not used) ppMxpmRmonDailyIntfcMTxPause
					FLAG=BITCNT(32)"
		::= { ppMxpmRmonDailyIntfcMDataEntry 20 }

	ppMxpmRmonDailyIntfcMTxTotalCollision OBJECT-TYPE
		SYNTAX		OCTET STRING (SIZE (4))
		ACCESS		read-only
		STATUS		mandatory
		DESCRIPTION	"(Not used) ppMxpmRmonDailyIntfcMTxTotalCollision
					When PortName is dmrPort1(5) to DmrPort4(8), Not Used (0 fixed)
					FLAG=BITCNT(32)"
		::= { ppMxpmRmonDailyIntfcMDataEntry 21 }

	ppMxpmRmonDailyIntfcMRxAlignmentError OBJECT-TYPE
		SYNTAX		OCTET STRING (SIZE (4))
		ACCESS		read-only
		STATUS		mandatory
		DESCRIPTION	"(Not used) ppMxpmRmonDailyIntfcMRxAlignmentError
					When PortName is dmrPort1(5) to DmrPort4(8), Not Used (0 fixed)
					FLAG=BITCNT(32)"
		::= { ppMxpmRmonDailyIntfcMDataEntry 22 }

	ppMxpmRmonDailyIntfcMRxSymbolError OBJECT-TYPE
		SYNTAX		OCTET STRING (SIZE (4))
		ACCESS		read-only
		STATUS		mandatory
		DESCRIPTION	"(Not used) ppMxpmRmonDailyIntfcMRxSymbolError
					When PortName is dmrPort1(5) to DmrPort4(8), Not Used (0 fixed)
					FLAG=BITCNT(32)"
		::= { ppMxpmRmonDailyIntfcMDataEntry 23 }

	ppMxpmRmonDailyIntfcMRxUndersize OBJECT-TYPE
		SYNTAX		OCTET STRING (SIZE (4))
		ACCESS		read-only
		STATUS		mandatory
		DESCRIPTION	"(Not used) ppMxpmRmonDailyIntfcMRxUndersize
					When PortName is dmrPort1(5) to DmrPort4(8), Not Used (0 fixed)
					FLAG=BITCNT(32)"
		::= { ppMxpmRmonDailyIntfcMDataEntry 24 }

	ppMxpmRmonDailyIntfcSData OBJECT IDENTIFIER
		::= { ppMxpmRmonDailyData 2 }

	ppMxpmRmonDailyIntfcSInfoDataTable OBJECT-TYPE
		SYNTAX		SEQUENCE OF PpMxpmRmonDailyIntfcSInfoDataEntry
		ACCESS		not-accessible
		STATUS		mandatory
		DESCRIPTION	"ppMxpmRmonDailyIntfcSInfoDataTable
					TABSZ=4"
		::= { ppMxpmRmonDailyIntfcSData 1 }

	ppMxpmRmonDailyIntfcSInfoDataEntry OBJECT-TYPE
		SYNTAX		PpMxpmRmonDailyIntfcSInfoDataEntry
		ACCESS		not-accessible
		STATUS		mandatory
		DESCRIPTION	"ppMxpmRmonDailyIntfcSInfoDataEntry"
		INDEX		{
						ppMxpmRmonDailyIntfcSInfoPasoIndex,
						ppMxpmRmonDailyIntfcSInfoPortName
					}
		::= { ppMxpmRmonDailyIntfcSInfoDataTable 1 }

	PpMxpmRmonDailyIntfcSInfoDataEntry ::= SEQUENCE {
					  ppMxpmRmonDailyIntfcSInfoPasoIndex  IpAddress,
					  ppMxpmRmonDailyIntfcSInfoPortName   INTEGER,
					  ppMxpmRmonDailyIntfcSInfoStatus     INTEGER,
					  ppMxpmRmonDailyIntfcSInfoPortUsage  INTEGER
					}

	ppMxpmRmonDailyIntfcSInfoPasoIndex OBJECT-TYPE
		SYNTAX		IpAddress 
		ACCESS		read-only
		STATUS		mandatory
		DESCRIPTION	"Pasolink IP Address Index"
		::= { ppMxpmRmonDailyIntfcSInfoDataEntry 1 }
		
	ppMxpmRmonDailyIntfcSInfoPortName OBJECT-TYPE
		SYNTAX		INTEGER {
					  linePort1(1),
					  linePort2(2),
					  dmrPort1(3),
					  dmrPort2(4)
					}
		ACCESS		read-only
		STATUS		mandatory
		DESCRIPTION	"Rmon PORT INDEX(IntfcS)
					1:LINE PORT1
					2:LINE PORT2
					3:DMR PORT1
					4:DMR PORT2
					"
		::= { ppMxpmRmonDailyIntfcSInfoDataEntry 2 }

	ppMxpmRmonDailyIntfcSInfoStatus OBJECT-TYPE
		SYNTAX		INTEGER ( 0..4 )
					
		ACCESS		read-only
		STATUS		mandatory
		DESCRIPTION	" STATUS
					  not_obtain(0),
					  valid_not_maint(1),
					  valid_maint(2),
					  invalid_not_maint(3),
					  invalid_maint(4)"
		::= { ppMxpmRmonDailyIntfcSInfoDataEntry 3 }

	ppMxpmRmonDailyIntfcSInfoPortUsage OBJECT-TYPE
		SYNTAX		INTEGER ( 0..2 )
					
		ACCESS		read-only
		STATUS		mandatory
		DESCRIPTION	" PORT USAGE
					  Invalid(0),
					  used(1),
					  not_used(2)
					"
		::= { ppMxpmRmonDailyIntfcSInfoDataEntry 4 }

	ppMxpmRmonDailyIntfcSDataTable OBJECT-TYPE
		SYNTAX		SEQUENCE OF PpMxpmRmonDailyIntfcSDataEntry
		ACCESS		not-accessible
		STATUS		mandatory
		DESCRIPTION	"ppMxpmRmonDailyIntfcSDataTable
					TABSZ=4"
		::= { ppMxpmRmonDailyIntfcSData 2 }

	ppMxpmRmonDailyIntfcSDataEntry OBJECT-TYPE
		SYNTAX		PpMxpmRmonDailyIntfcSDataEntry
		ACCESS		not-accessible
		STATUS		mandatory
		DESCRIPTION	"Each item of this table is represented as follows: 
					o OCTET STRING of each value is represented 4byte Interger( little endian ).
					o When a value is overflow, most significant bit is 1.
					"
		INDEX		{
						ppMxpmRmonDailyIntfcSPasoIndex,
						ppMxpmRmonDailyIntfcSPortName
					}
		::= { ppMxpmRmonDailyIntfcSDataTable 1 }

	PpMxpmRmonDailyIntfcSDataEntry ::= SEQUENCE {
					  ppMxpmRmonDailyIntfcSPasoIndex              IpAddress,
					  ppMxpmRmonDailyIntfcSPortName               INTEGER,
					  ppMxpmRmonDailyIntfcSRxUnicast              OCTET STRING,
					  ppMxpmRmonDailyIntfcSRxBroadcast            OCTET STRING,
					  ppMxpmRmonDailyIntfcSRxMulticast            OCTET STRING,
					  ppMxpmRmonDailyIntfcSRxPause                OCTET STRING,
					  ppMxpmRmonDailyIntfcSRxCrcError             OCTET STRING,
					  ppMxpmRmonDailyIntfcSRxFragments            OCTET STRING,
					  ppMxpmRmonDailyIntfcSRx64Octets             OCTET STRING,
					  ppMxpmRmonDailyIntfcSRx65to127Octets        OCTET STRING,
					  ppMxpmRmonDailyIntfcSRx128to255Octets       OCTET STRING,
					  ppMxpmRmonDailyIntfcSRx256to511Octets       OCTET STRING,
					  ppMxpmRmonDailyIntfcSRx512to1023Octets      OCTET STRING,
					  ppMxpmRmonDailyIntfcSRx1024to1536Octets     OCTET STRING,
					  ppMxpmRmonDailyIntfcSRx1537toMaxSizeOctets  OCTET STRING,
					  ppMxpmRmonDailyIntfcSRxJabbers              OCTET STRING,
					  ppMxpmRmonDailyIntfcSTxUnicast              OCTET STRING,
					  ppMxpmRmonDailyIntfcSTxBroadcast            OCTET STRING,
					  ppMxpmRmonDailyIntfcSTxMulticast            OCTET STRING,
					  ppMxpmRmonDailyIntfcSTxPause                OCTET STRING,
					  ppMxpmRmonDailyIntfcSTxTotalCollision       OCTET STRING,
					  ppMxpmRmonDailyIntfcSRxAlignmentError       OCTET STRING,
					  ppMxpmRmonDailyIntfcSRxSymbolError          OCTET STRING,
					  ppMxpmRmonDailyIntfcSRxUndersize            OCTET STRING
					}

	ppMxpmRmonDailyIntfcSPasoIndex OBJECT-TYPE
		SYNTAX		IpAddress 
		ACCESS		read-only
		STATUS		mandatory
		DESCRIPTION	"Pasolink IP Address Index"
		::= { ppMxpmRmonDailyIntfcSDataEntry 1 }
		
		
	ppMxpmRmonDailyIntfcSPortName OBJECT-TYPE
		SYNTAX		INTEGER {
					  linePort1(1),
					  linePort2(2),
					  dmrPort1(3),
					  dmrPort2(4)
					}
		ACCESS		read-only
		STATUS		mandatory
		DESCRIPTION	"Rmon PORT INDEX(IntfcS)
					1:LINE PORT1
					2:LINE PORT2
					3:DMR PORT1
					4:DMR PORT2
					"
		::= { ppMxpmRmonDailyIntfcSDataEntry 2 }

	ppMxpmRmonDailyIntfcSRxUnicast OBJECT-TYPE
		SYNTAX		OCTET STRING (SIZE (4))
		ACCESS		read-only
		STATUS		mandatory
		DESCRIPTION	"ppMxpmRmonDailyIntfcSRxUnicast
					FLAG=BITCNT(32)"
		::= { ppMxpmRmonDailyIntfcSDataEntry 3 }

	ppMxpmRmonDailyIntfcSRxBroadcast OBJECT-TYPE
		SYNTAX		OCTET STRING (SIZE (4))
		ACCESS		read-only
		STATUS		mandatory
		DESCRIPTION	"ppMxpmRmonDailyIntfcSRxBroadcast
					FLAG=BITCNT(32)"
		::= { ppMxpmRmonDailyIntfcSDataEntry 4 }

	ppMxpmRmonDailyIntfcSRxMulticast OBJECT-TYPE
		SYNTAX		OCTET STRING (SIZE (4))
		ACCESS		read-only
		STATUS		mandatory
		DESCRIPTION	"ppMxpmRmonDailyIntfcSRxMulticast
					FLAG=BITCNT(32)"
		::= { ppMxpmRmonDailyIntfcSDataEntry 5 }

	ppMxpmRmonDailyIntfcSRxPause OBJECT-TYPE
		SYNTAX		OCTET STRING (SIZE (4))
		ACCESS		read-only
		STATUS		mandatory
		DESCRIPTION	"ppMxpmRmonDailyIntfcSRxPause
					FLAG=BITCNT(32)"
		::= { ppMxpmRmonDailyIntfcSDataEntry 6 }

	ppMxpmRmonDailyIntfcSRxCrcError OBJECT-TYPE
		SYNTAX		OCTET STRING (SIZE (4))
		ACCESS		read-only
		STATUS		mandatory
		DESCRIPTION	"ppMxpmRmonDailyIntfcSRxCrcError
					FLAG=BITCNT(32)"
		::= { ppMxpmRmonDailyIntfcSDataEntry 7 }

	ppMxpmRmonDailyIntfcSRxFragments OBJECT-TYPE
		SYNTAX		OCTET STRING (SIZE (4))
		ACCESS		read-only
		STATUS		mandatory
		DESCRIPTION	"ppMxpmRmonDailyIntfcSRxFragments
					FLAG=BITCNT(32)"
		::= { ppMxpmRmonDailyIntfcSDataEntry 8 }

	ppMxpmRmonDailyIntfcSRx64Octets OBJECT-TYPE
		SYNTAX		OCTET STRING (SIZE (4))
		ACCESS		read-only
		STATUS		mandatory
		DESCRIPTION	"ppMxpmRmonDailyIntfcSRx64Octets
					FLAG=BITCNT(32)"
		::= { ppMxpmRmonDailyIntfcSDataEntry 9 }

	ppMxpmRmonDailyIntfcSRx65to127Octets OBJECT-TYPE
		SYNTAX		OCTET STRING (SIZE (4))
		ACCESS		read-only
		STATUS		mandatory
		DESCRIPTION	"ppMxpmRmonDailyIntfcSRx65to127Octets
					FLAG=BITCNT(32)"
		::= { ppMxpmRmonDailyIntfcSDataEntry 10 }

	ppMxpmRmonDailyIntfcSRx128to255Octets OBJECT-TYPE
		SYNTAX		OCTET STRING (SIZE (4))
		ACCESS		read-only
		STATUS		mandatory
		DESCRIPTION	"ppMxpmRmonDailyIntfcSRx128to255Octets
					FLAG=BITCNT(32)"
		::= { ppMxpmRmonDailyIntfcSDataEntry 11 }

	ppMxpmRmonDailyIntfcSRx256to511Octets OBJECT-TYPE
		SYNTAX		OCTET STRING (SIZE (4))
		ACCESS		read-only
		STATUS		mandatory
		DESCRIPTION	"ppMxpmRmonDailyIntfcSRx256to511Octets
					FLAG=BITCNT(32)"
		::= { ppMxpmRmonDailyIntfcSDataEntry 12 }

	ppMxpmRmonDailyIntfcSRx512to1023Octets OBJECT-TYPE
		SYNTAX		OCTET STRING (SIZE (4))
		ACCESS		read-only
		STATUS		mandatory
		DESCRIPTION	"ppMxpmRmonDailyIntfcSRx512to1023Octets
					FLAG=BITCNT(32)"
		::= { ppMxpmRmonDailyIntfcSDataEntry 13 }

	ppMxpmRmonDailyIntfcSRx1024to1536Octets OBJECT-TYPE
		SYNTAX		OCTET STRING (SIZE (4))
		ACCESS		read-only
		STATUS		mandatory
		DESCRIPTION	"ppMxpmRmonDailyIntfcSRx1024to1536Octets
					FLAG=BITCNT(32)"
		::= { ppMxpmRmonDailyIntfcSDataEntry 14 }

	ppMxpmRmonDailyIntfcSRx1537toMaxSizeOctets OBJECT-TYPE
		SYNTAX		OCTET STRING (SIZE (4))
		ACCESS		read-only
		STATUS		mandatory
		DESCRIPTION	"ppMxpmRmonDailyIntfcSRx1537toMaxSizeOctets
					FLAG=BITCNT(32)"
		::= { ppMxpmRmonDailyIntfcSDataEntry 15 }

	ppMxpmRmonDailyIntfcSRxJabbers OBJECT-TYPE
		SYNTAX		OCTET STRING (SIZE (4))
		ACCESS		read-only
		STATUS		mandatory
		DESCRIPTION	"ppMxpmRmonDailyIntfcSRxJabbers
					FLAG=BITCNT(32)"
		::= { ppMxpmRmonDailyIntfcSDataEntry 16 }

	ppMxpmRmonDailyIntfcSTxUnicast OBJECT-TYPE
		SYNTAX		OCTET STRING (SIZE (4))
		ACCESS		read-only
		STATUS		mandatory
		DESCRIPTION	"ppMxpmRmonDailyIntfcSTxUnicast
					FLAG=BITCNT(32)"
		::= { ppMxpmRmonDailyIntfcSDataEntry 17 }

	ppMxpmRmonDailyIntfcSTxBroadcast OBJECT-TYPE
		SYNTAX		OCTET STRING (SIZE (4))
		ACCESS		read-only
		STATUS		mandatory
		DESCRIPTION	"ppMxpmRmonDailyIntfcSTxBroadcast
					FLAG=BITCNT(32)"
		::= { ppMxpmRmonDailyIntfcSDataEntry 18 }

	ppMxpmRmonDailyIntfcSTxMulticast OBJECT-TYPE
		SYNTAX		OCTET STRING (SIZE (4))
		ACCESS		read-only
		STATUS		mandatory
		DESCRIPTION	"ppMxpmRmonDailyIntfcSTxMulticast
					FLAG=BITCNT(32)"
		::= { ppMxpmRmonDailyIntfcSDataEntry 19 }

	ppMxpmRmonDailyIntfcSTxPause OBJECT-TYPE
		SYNTAX		OCTET STRING (SIZE (4))
		ACCESS		read-only
		STATUS		mandatory
		DESCRIPTION	"ppMxpmRmonDailyIntfcSTxPause
					FLAG=BITCNT(32)"
		::= { ppMxpmRmonDailyIntfcSDataEntry 20 }

	ppMxpmRmonDailyIntfcSTxTotalCollision OBJECT-TYPE
		SYNTAX		OCTET STRING (SIZE (4))
		ACCESS		read-only
		STATUS		mandatory
		DESCRIPTION	"ppMxpmRmonDailyIntfcSTxTotalCollision
					When PortName is dmrPort1(3) to DmrPort2(4), Not Used (0 fixed)
					FLAG=BITCNT(32)"
		::= { ppMxpmRmonDailyIntfcSDataEntry 21 }

	ppMxpmRmonDailyIntfcSRxAlignmentError OBJECT-TYPE
		SYNTAX		OCTET STRING (SIZE (4))
		ACCESS		read-only
		STATUS		mandatory
		DESCRIPTION	"ppMxpmRmonDailyIntfcSRxAlignmentError
					When PortName is dmrPort1(3) to DmrPort2(4), Not Used (0 fixed)
					FLAG=BITCNT(32)"
		::= { ppMxpmRmonDailyIntfcSDataEntry 22 }

	ppMxpmRmonDailyIntfcSRxSymbolError OBJECT-TYPE
		SYNTAX		OCTET STRING (SIZE (4))
		ACCESS		read-only
		STATUS		mandatory
		DESCRIPTION	"ppMxpmRmonDailyIntfcSRxSymbolError
					When PortName is dmrPort1(3) to DmrPort2(4), Not Used (0 fixed)
					FLAG=BITCNT(32)"
		::= { ppMxpmRmonDailyIntfcSDataEntry 23 }

	ppMxpmRmonDailyIntfcSRxUndersize OBJECT-TYPE
		SYNTAX		OCTET STRING (SIZE (4))
		ACCESS		read-only
		STATUS		mandatory
		DESCRIPTION	"ppMxpmRmonDailyIntfcSRxUndersize
					When PortName is dmrPort1(3) to DmrPort2(4), Not Used (0 fixed)
					FLAG=BITCNT(32)"
		::= { ppMxpmRmonDailyIntfcSDataEntry 24 }

	ppMxpmRmonWeeklyData OBJECT IDENTIFIER
		::= { ppMxPmonInfo 4 }

	ppMxpmRmonWeeklyIntfcMData OBJECT IDENTIFIER
		::= { ppMxpmRmonWeeklyData 1 }

	ppMxpmRmonWeeklyIntfcMInfoDataTable OBJECT-TYPE
		SYNTAX		SEQUENCE OF PpMxpmRmonWeeklyIntfcMInfoDataEntry
		ACCESS		not-accessible
		STATUS		mandatory
		DESCRIPTION	"ppMxpmRmonWeeklyIntfcMInfoDataTable
					TABSZ=8"
		::= { ppMxpmRmonWeeklyIntfcMData 1 }

	ppMxpmRmonWeeklyIntfcMInfoDataEntry OBJECT-TYPE
		SYNTAX		PpMxpmRmonWeeklyIntfcMInfoDataEntry
		ACCESS		not-accessible
		STATUS		mandatory
		DESCRIPTION	"ppMxpmRmonWeeklyIntfcMInfoDataEntry"
		INDEX		{
						ppMxpmRmonWeeklyIntfcMInfoPasoIndex,
						ppMxpmRmonWeeklyIntfcMInfoPortName
					}
		::= { ppMxpmRmonWeeklyIntfcMInfoDataTable 1 }

	PpMxpmRmonWeeklyIntfcMInfoDataEntry ::= SEQUENCE {
					  ppMxpmRmonWeeklyIntfcMInfoPasoIndex  IpAddress,
					  ppMxpmRmonWeeklyIntfcMInfoPortName   INTEGER,
					  ppMxpmRmonWeeklyIntfcMInfoStatus     INTEGER,
					  ppMxpmRmonWeeklyIntfcMInfoPortUsage  INTEGER
					}

	ppMxpmRmonWeeklyIntfcMInfoPasoIndex OBJECT-TYPE
		SYNTAX		IpAddress 
		ACCESS		read-only
		STATUS		mandatory
		DESCRIPTION	"(Not used) Pasolink IP Address Index"
		::= { ppMxpmRmonWeeklyIntfcMInfoDataEntry 1 }
		
	ppMxpmRmonWeeklyIntfcMInfoPortName OBJECT-TYPE
		SYNTAX		INTEGER {
					  linePort1(1),
					  linePort2(2),
					  linePort3(3),
					  linePort4(4),
					  dmrPort1(5),
					  dmrPort2(6),
					  dmrPort3(7),
					  dmrPort4(8)
					}
		ACCESS		read-only
		STATUS		mandatory
		DESCRIPTION	"(Not used) Rmon PORT INDEX(IntfcMInfo)
					1:LINE PORT1
					2:LINE PORT2
					3:LINE PORT3
					4:LINE PORT4
					5:DMR PORT1
					6:DMR PORT2
					7:DMR PORT3
					8:DMR PORT4"
		::= { ppMxpmRmonWeeklyIntfcMInfoDataEntry 2 }

	ppMxpmRmonWeeklyIntfcMInfoStatus OBJECT-TYPE
		SYNTAX		INTEGER ( 0..4 )
					
		ACCESS		read-only
		STATUS		mandatory
		DESCRIPTION	"(Not used) STATUS
					  not_obtain(0),
					  valid_not_maint(1),
					  valid_maint(2),
					  invalid_not_maint(3),
					  invalid_maint(4)"
		::= { ppMxpmRmonWeeklyIntfcMInfoDataEntry 3 }

	ppMxpmRmonWeeklyIntfcMInfoPortUsage OBJECT-TYPE
		SYNTAX		INTEGER ( 0..2 )
					
		ACCESS		read-only
		STATUS		mandatory
		DESCRIPTION	"(Not used) PORT USAGE
					  Invalid(0),
					  used(1),
					  not_used(2)
					"
		::= { ppMxpmRmonWeeklyIntfcMInfoDataEntry 4 }

	ppMxpmRmonWeeklyIntfcMDataTable OBJECT-TYPE
		SYNTAX		SEQUENCE OF PpMxpmRmonWeeklyIntfcMDataEntry
		ACCESS		not-accessible
		STATUS		mandatory
		DESCRIPTION	"ppMxpmRmonWeeklyIntfcMDataTable
					TABSZ=8"
		::= { ppMxpmRmonWeeklyIntfcMData 2 }

	ppMxpmRmonWeeklyIntfcMDataEntry OBJECT-TYPE
		SYNTAX		PpMxpmRmonWeeklyIntfcMDataEntry
		ACCESS		not-accessible
		STATUS		mandatory
		DESCRIPTION	"Each item of this table is represented as follows: 
					o OCTET STRING of each value is represented 5byte Interger( little endian ).
					o When a value is overflow, most significant bit is 1.
					"
		INDEX		{
						ppMxpmRmonWeeklyIntfcMPasoIndex,
						ppMxpmRmonWeeklyIntfcMPortName
					}
		::= { ppMxpmRmonWeeklyIntfcMDataTable 1 }

	PpMxpmRmonWeeklyIntfcMDataEntry ::= SEQUENCE {
					  ppMxpmRmonWeeklyIntfcMPasoIndex              IpAddress,
					  ppMxpmRmonWeeklyIntfcMPortName               INTEGER,
					  ppMxpmRmonWeeklyIntfcMRxUnicast              OCTET STRING,
					  ppMxpmRmonWeeklyIntfcMRxBroadcast            OCTET STRING,
					  ppMxpmRmonWeeklyIntfcMRxMulticast            OCTET STRING,
					  ppMxpmRmonWeeklyIntfcMRxPause                OCTET STRING,
					  ppMxpmRmonWeeklyIntfcMRxCrcError             OCTET STRING,
					  ppMxpmRmonWeeklyIntfcMRxFragments            OCTET STRING,
					  ppMxpmRmonWeeklyIntfcMRx64Octets             OCTET STRING,
					  ppMxpmRmonWeeklyIntfcMRx65to127Octets        OCTET STRING,
					  ppMxpmRmonWeeklyIntfcMRx128to255Octets       OCTET STRING,
					  ppMxpmRmonWeeklyIntfcMRx256to511Octets       OCTET STRING,
					  ppMxpmRmonWeeklyIntfcMRx512to1023Octets      OCTET STRING,
					  ppMxpmRmonWeeklyIntfcMRx1024to1536Octets     OCTET STRING,
					  ppMxpmRmonWeeklyIntfcMRx1537toMaxSizeOctets  OCTET STRING,
					  ppMxpmRmonWeeklyIntfcMRxJabbers              OCTET STRING,
					  ppMxpmRmonWeeklyIntfcMTxUnicast              OCTET STRING,
					  ppMxpmRmonWeeklyIntfcMTxBroadcast            OCTET STRING,
					  ppMxpmRmonWeeklyIntfcMTxMulticast            OCTET STRING,
					  ppMxpmRmonWeeklyIntfcMTxPause                OCTET STRING,
					  ppMxpmRmonWeeklyIntfcMTxTotalCollision       OCTET STRING,
					  ppMxpmRmonWeeklyIntfcMRxAlignmentError       OCTET STRING,
					  ppMxpmRmonWeeklyIntfcMRxSymbolError          OCTET STRING,
					  ppMxpmRmonWeeklyIntfcMRxUndersize            OCTET STRING
					}

	ppMxpmRmonWeeklyIntfcMPasoIndex OBJECT-TYPE
		SYNTAX		IpAddress 
		ACCESS		read-only
		STATUS		mandatory
		DESCRIPTION	"(Not used) Pasolink IP Address Index"
		::= { ppMxpmRmonWeeklyIntfcMDataEntry 1 }
		
	ppMxpmRmonWeeklyIntfcMPortName OBJECT-TYPE
		SYNTAX		INTEGER {
					  linePort1(1),
					  linePort2(2),
					  linePort3(3),
					  linePort4(4),
					  dmrPort1(5),
					  dmrPort2(6),
					  dmrPort3(7),
					  dmrPort4(8)
					}
		ACCESS		read-only
		STATUS		mandatory
		DESCRIPTION	"(Not used) Rmon PORT INDEX(IntfcM)
					1:LINE PORT1
					2:LINE PORT2
					3:LINE PORT3
					4:LINE PORT4
					5:DMR PORT1
					6:DMR PORT2
					7:DMR PORT3
					8:DMR PORT4"
		::= { ppMxpmRmonWeeklyIntfcMDataEntry 2 }

	ppMxpmRmonWeeklyIntfcMRxUnicast OBJECT-TYPE
		SYNTAX		OCTET STRING (SIZE (5))
		ACCESS		read-only
		STATUS		mandatory
		DESCRIPTION	"(Not used) ppMxpmRmonWeeklyIntfcMRxUnicast
					FLAG=BITCNT(40)"
		::= { ppMxpmRmonWeeklyIntfcMDataEntry 3 }

	ppMxpmRmonWeeklyIntfcMRxBroadcast OBJECT-TYPE
		SYNTAX		OCTET STRING (SIZE (5))
		ACCESS		read-only
		STATUS		mandatory
		DESCRIPTION	"(Not used) ppMxpmRmonWeeklyIntfcMRxBroadcast
					FLAG=BITCNT(40)"
		::= { ppMxpmRmonWeeklyIntfcMDataEntry 4 }

	ppMxpmRmonWeeklyIntfcMRxMulticast OBJECT-TYPE
		SYNTAX		OCTET STRING (SIZE (5))
		ACCESS		read-only
		STATUS		mandatory
		DESCRIPTION	"(Not used) ppMxpmRmonWeeklyIntfcMRxMulticast
					FLAG=BITCNT(40)"
		::= { ppMxpmRmonWeeklyIntfcMDataEntry 5 }

	ppMxpmRmonWeeklyIntfcMRxPause OBJECT-TYPE
		SYNTAX		OCTET STRING (SIZE (5))
		ACCESS		read-only
		STATUS		mandatory
		DESCRIPTION	"(Not used) ppMxpmRmonWeeklyIntfcMRxPause
					FLAG=BITCNT(40)"
		::= { ppMxpmRmonWeeklyIntfcMDataEntry 6 }

	ppMxpmRmonWeeklyIntfcMRxCrcError OBJECT-TYPE
		SYNTAX		OCTET STRING (SIZE (5))
		ACCESS		read-only
		STATUS		mandatory
		DESCRIPTION	"(Not used) ppMxpmRmonWeeklyIntfcMRxCrcError
					FLAG=BITCNT(40)"
		::= { ppMxpmRmonWeeklyIntfcMDataEntry 7 }

	ppMxpmRmonWeeklyIntfcMRxFragments OBJECT-TYPE
		SYNTAX		OCTET STRING (SIZE (5))
		ACCESS		read-only
		STATUS		mandatory
		DESCRIPTION	"(Not used) ppMxpmRmonWeeklyIntfsMRxFragments
					FLAG=BITCNT(40)"
		::= { ppMxpmRmonWeeklyIntfcMDataEntry 8 }

	ppMxpmRmonWeeklyIntfcMRx64Octets OBJECT-TYPE
		SYNTAX		OCTET STRING (SIZE (5))
		ACCESS		read-only
		STATUS		mandatory
		DESCRIPTION	"(Not used) ppMxpmRmonWeeklyIntfsMRx64Octets
					FLAG=BITCNT(40)"
		::= { ppMxpmRmonWeeklyIntfcMDataEntry 9 }

	ppMxpmRmonWeeklyIntfcMRx65to127Octets OBJECT-TYPE
		SYNTAX		OCTET STRING (SIZE (5))
		ACCESS		read-only
		STATUS		mandatory
		DESCRIPTION	"(Not used) ppMxpmRmonWeeklyIntfsMRx65to127Octets
					FLAG=BITCNT(40)"
		::= { ppMxpmRmonWeeklyIntfcMDataEntry 10 }

	ppMxpmRmonWeeklyIntfcMRx128to255Octets OBJECT-TYPE
		SYNTAX		OCTET STRING (SIZE (5))
		ACCESS		read-only
		STATUS		mandatory
		DESCRIPTION	"(Not used) ppMxpmRmonWeeklyIntfsMRx128to255Octets
					FLAG=BITCNT(40)"
		::= { ppMxpmRmonWeeklyIntfcMDataEntry 11 }

	ppMxpmRmonWeeklyIntfcMRx256to511Octets OBJECT-TYPE
		SYNTAX		OCTET STRING (SIZE (5))
		ACCESS		read-only
		STATUS		mandatory
		DESCRIPTION	"(Not used) ppMxpmRmonWeeklyIntfsMRx256to511Octets
					FLAG=BITCNT(40)"
		::= { ppMxpmRmonWeeklyIntfcMDataEntry 12 }

	ppMxpmRmonWeeklyIntfcMRx512to1023Octets OBJECT-TYPE
		SYNTAX		OCTET STRING (SIZE (5))
		ACCESS		read-only
		STATUS		mandatory
		DESCRIPTION	"(Not used) ppMxpmRmonWeeklyIntfsMRx512to1023Octets
					FLAG=BITCNT(40)"
		::= { ppMxpmRmonWeeklyIntfcMDataEntry 13 }

	ppMxpmRmonWeeklyIntfcMRx1024to1536Octets OBJECT-TYPE
		SYNTAX		OCTET STRING (SIZE (5))
		ACCESS		read-only
		STATUS		mandatory
		DESCRIPTION	"(Not used) ppMxpmRmonWeeklyIntfsMRx1024to1536Octets
					FLAG=BITCNT(40)"
		::= { ppMxpmRmonWeeklyIntfcMDataEntry 14 }

	ppMxpmRmonWeeklyIntfcMRx1537toMaxSizeOctets OBJECT-TYPE
		SYNTAX		OCTET STRING (SIZE (5))
		ACCESS		read-only
		STATUS		mandatory
		DESCRIPTION	"(Not used) ppMxpmRmonWeeklyIntfsMRx1537toMaxSizeOctets
					FLAG=BITCNT(40)"
		::= { ppMxpmRmonWeeklyIntfcMDataEntry 15 }

	ppMxpmRmonWeeklyIntfcMRxJabbers OBJECT-TYPE
		SYNTAX		OCTET STRING (SIZE (5))
		ACCESS		read-only
		STATUS		mandatory
		DESCRIPTION	"(Not used) ppMxpmRmonWeeklyIntfsMRxJabbers
					FLAG=BITCNT(40)"
		::= { ppMxpmRmonWeeklyIntfcMDataEntry 16 }

	ppMxpmRmonWeeklyIntfcMTxUnicast OBJECT-TYPE
		SYNTAX		OCTET STRING (SIZE (5))
		ACCESS		read-only
		STATUS		mandatory
		DESCRIPTION	"(Not used) ppMxpmRmonWeeklyIntfsMTxUnicast
					FLAG=BITCNT(40)"
		::= { ppMxpmRmonWeeklyIntfcMDataEntry 17 }

	ppMxpmRmonWeeklyIntfcMTxBroadcast OBJECT-TYPE
		SYNTAX		OCTET STRING (SIZE (5))
		ACCESS		read-only
		STATUS		mandatory
		DESCRIPTION	"(Not used)ppMxpmRmonWeeklyIntfsMTxBroadcast
					FLAG=BITCNT(40)"
		::= { ppMxpmRmonWeeklyIntfcMDataEntry 18 }

	ppMxpmRmonWeeklyIntfcMTxMulticast OBJECT-TYPE
		SYNTAX		OCTET STRING (SIZE (5))
		ACCESS		read-only
		STATUS		mandatory
		DESCRIPTION	"(Not used) ppMxpmRmonWeeklyIntfsMTxMulticast
					FLAG=BITCNT(40)"
		::= { ppMxpmRmonWeeklyIntfcMDataEntry 19 }

	ppMxpmRmonWeeklyIntfcMTxPause OBJECT-TYPE
		SYNTAX		OCTET STRING (SIZE (5))
		ACCESS		read-only
		STATUS		mandatory
		DESCRIPTION	"(Not used) ppMxpmRmonWeeklyIntfsMTxPause
					FLAG=BITCNT(40)"
		::= { ppMxpmRmonWeeklyIntfcMDataEntry 20 }

	ppMxpmRmonWeeklyIntfcMTxTotalCollision OBJECT-TYPE
		SYNTAX		OCTET STRING (SIZE (5))
		ACCESS		read-only
		STATUS		mandatory
		DESCRIPTION	"(Not used) ppMxpmRmonWeeklyIntfsMTxTotalCollision
					When PortName is dmrPort1(5) to DmrPort4(8), Not Used (0 fixed)
					FLAG=BITCNT(40)"
		::= { ppMxpmRmonWeeklyIntfcMDataEntry 21 }

	ppMxpmRmonWeeklyIntfcMRxAlignmentError OBJECT-TYPE
		SYNTAX		OCTET STRING (SIZE (5))
		ACCESS		read-only
		STATUS		mandatory
		DESCRIPTION	"(Not used) ppMxpmRmonWeeklyIntfsMRxAlignmentError
					When PortName is dmrPort1(5) to DmrPort4(8), Not Used (0 fixed)
					FLAG=BITCNT(40)"
		::= { ppMxpmRmonWeeklyIntfcMDataEntry 22 }

	ppMxpmRmonWeeklyIntfcMRxSymbolError OBJECT-TYPE
		SYNTAX		OCTET STRING (SIZE (5))
		ACCESS		read-only
		STATUS		mandatory
		DESCRIPTION	"(Not used) ppMxpmRmonWeeklyIntfsMRxSymbolError
					When PortName is dmrPort1(5) to DmrPort4(8), Not Used (0 fixed)
					FLAG=BITCNT(40)"
		::= { ppMxpmRmonWeeklyIntfcMDataEntry 23 }

	ppMxpmRmonWeeklyIntfcMRxUndersize OBJECT-TYPE
		SYNTAX		OCTET STRING (SIZE (5))
		ACCESS		read-only
		STATUS		mandatory
		DESCRIPTION	"(Not used) ppMxpmRmonWeeklyIntfsMRxUndersize
					When PortName is dmrPort1(5) to DmrPort4(8), Not Used (0 fixed)
					FLAG=BITCNT(40)"
		::= { ppMxpmRmonWeeklyIntfcMDataEntry 24 }

	ppMxpmRmonWeeklyIntfcSData OBJECT IDENTIFIER
		::= { ppMxpmRmonWeeklyData 2 }

	ppMxpmRmonWeeklyIntfcSInfoDataTable OBJECT-TYPE
		SYNTAX		SEQUENCE OF PpMxpmRmonWeeklyIntfcSInfoDataEntry
		ACCESS		not-accessible
		STATUS		mandatory
		DESCRIPTION	"ppMxpmRmonWeeklyIntfcSInfoDataTable
					TABSZ=4"
		::= { ppMxpmRmonWeeklyIntfcSData 1 }

	ppMxpmRmonWeeklyIntfcSInfoDataEntry OBJECT-TYPE
		SYNTAX		PpMxpmRmonWeeklyIntfcSInfoDataEntry
		ACCESS		not-accessible
		STATUS		mandatory
		DESCRIPTION	"ppMxpmRmonWeeklyIntfcSInfoDataEntry"
		INDEX		{
						ppMxpmRmonWeeklyIntfcSInfoPasoIndex,
						ppMxpmRmonWeeklyIntfcSInfoPortName
					}
		::= { ppMxpmRmonWeeklyIntfcSInfoDataTable 1 }

	PpMxpmRmonWeeklyIntfcSInfoDataEntry ::= SEQUENCE {
					  ppMxpmRmonWeeklyIntfcSInfoPasoIndex  IpAddress,
					  ppMxpmRmonWeeklyIntfcSInfoPortName   INTEGER,
					  ppMxpmRmonWeeklyIntfcSInfoStatus     INTEGER,
					  ppMxpmRmonWeeklyIntfcSInfoPortUsage  INTEGER
					}

	ppMxpmRmonWeeklyIntfcSInfoPasoIndex OBJECT-TYPE
		SYNTAX		IpAddress 
		ACCESS		read-only
		STATUS		mandatory
		DESCRIPTION	"Pasolink IP Address Index"
		::= { ppMxpmRmonWeeklyIntfcSInfoDataEntry 1 }
		
	ppMxpmRmonWeeklyIntfcSInfoPortName OBJECT-TYPE
		SYNTAX		INTEGER {
					  linePort1(1),
					  linePort2(2),
					  dmrPort1(3),
					  dmrPort2(4)
					}
		ACCESS		read-only
		STATUS		mandatory
		DESCRIPTION	"Rmon PORT INDEX(IntfcS)
					1:LINE PORT1
					2:LINE PORT2
					3:DMR PORT1
					4:DMR PORT2
					"
		::= { ppMxpmRmonWeeklyIntfcSInfoDataEntry 2 }

	ppMxpmRmonWeeklyIntfcSInfoStatus OBJECT-TYPE
		SYNTAX		INTEGER ( 0..4 )
					
		ACCESS		read-only
		STATUS		mandatory
		DESCRIPTION	" STATUS
					  not_obtain(0),
					  valid_not_maint(1),
					  valid_maint(2),
					  invalid_not_maint(3),
					  invalid_maint(4)"
		::= { ppMxpmRmonWeeklyIntfcSInfoDataEntry 3 }

	ppMxpmRmonWeeklyIntfcSInfoPortUsage OBJECT-TYPE
		SYNTAX		INTEGER ( 0..2 )
					
		ACCESS		read-only
		STATUS		mandatory
		DESCRIPTION	" PORT USAGE
					  Invalid(0),
					  used(1),
					  not_used(2)
					"
		::= { ppMxpmRmonWeeklyIntfcSInfoDataEntry 4 }

	ppMxpmRmonWeeklyIntfcSDataTable OBJECT-TYPE
		SYNTAX		SEQUENCE OF PpMxpmRmonWeeklyIntfcSDataEntry
		ACCESS		not-accessible
		STATUS		mandatory
		DESCRIPTION	"ppMxpmRmonWeeklyIntfcSDataTable
					TABSZ=4"
		::= { ppMxpmRmonWeeklyIntfcSData 2 }

	ppMxpmRmonWeeklyIntfcSDataEntry OBJECT-TYPE
		SYNTAX		PpMxpmRmonWeeklyIntfcSDataEntry
		ACCESS		not-accessible
		STATUS		mandatory
		DESCRIPTION	"Each item of this table is represented as follows: 
					o OCTET STRING of each value is represented 5byte Interger( little endian ).
					o When a value is overflow, most significant bit is 1.
					"
		INDEX		{
						ppMxpmRmonWeeklyIntfcSPasoIndex,
						ppMxpmRmonWeeklyIntfcSPortName
					}
		::= { ppMxpmRmonWeeklyIntfcSDataTable 1 }

	PpMxpmRmonWeeklyIntfcSDataEntry ::= SEQUENCE {
					  ppMxpmRmonWeeklyIntfcSPasoIndex              IpAddress,
					  ppMxpmRmonWeeklyIntfcSPortName               INTEGER,
					  ppMxpmRmonWeeklyIntfcSRxUnicast              OCTET STRING,
					  ppMxpmRmonWeeklyIntfcSRxBroadcast            OCTET STRING,
					  ppMxpmRmonWeeklyIntfcSRxMulticast            OCTET STRING,
					  ppMxpmRmonWeeklyIntfcSRxPause                OCTET STRING,
					  ppMxpmRmonWeeklyIntfcSRxCrcError             OCTET STRING,
					  ppMxpmRmonWeeklyIntfcSRxFragments            OCTET STRING,
					  ppMxpmRmonWeeklyIntfcSRx64Octets             OCTET STRING,
					  ppMxpmRmonWeeklyIntfcSRx65to127Octets        OCTET STRING,
					  ppMxpmRmonWeeklyIntfcSRx128to255Octets       OCTET STRING,
					  ppMxpmRmonWeeklyIntfcSRx256to511Octets       OCTET STRING,
					  ppMxpmRmonWeeklyIntfcSRx512to1023Octets      OCTET STRING,
					  ppMxpmRmonWeeklyIntfcSRx1024to1536Octets     OCTET STRING,
					  ppMxpmRmonWeeklyIntfcSRx1537toMaxSizeOctets  OCTET STRING,
					  ppMxpmRmonWeeklyIntfcSRxJabbers              OCTET STRING,
					  ppMxpmRmonWeeklyIntfcSTxUnicast              OCTET STRING,
					  ppMxpmRmonWeeklyIntfcSTxBroadcast            OCTET STRING,
					  ppMxpmRmonWeeklyIntfcSTxMulticast            OCTET STRING,
					  ppMxpmRmonWeeklyIntfcSTxPause                OCTET STRING,
					  ppMxpmRmonWeeklyIntfcSTxTotalCollision       OCTET STRING,
					  ppMxpmRmonWeeklyIntfcSRxAlignmentError       OCTET STRING,
					  ppMxpmRmonWeeklyIntfcSRxSymbolError          OCTET STRING,
					  ppMxpmRmonWeeklyIntfcSRxUndersize            OCTET STRING
					}

	ppMxpmRmonWeeklyIntfcSPasoIndex OBJECT-TYPE
		SYNTAX		IpAddress 
		ACCESS		read-only
		STATUS		mandatory
		DESCRIPTION	"Pasolink IP Address Index"
		::= { ppMxpmRmonWeeklyIntfcSDataEntry 1 }
		
	ppMxpmRmonWeeklyIntfcSPortName OBJECT-TYPE
		SYNTAX		INTEGER {
					  linePort1(1),
					  linePort2(2),
					  dmrPort1(3),
					  dmrPort2(4)
					}
		ACCESS		read-only
		STATUS		mandatory
		DESCRIPTION	"Rmon PORT INDEX(IntfcS)
					1:LINE PORT1
					2:LINE PORT2
					3:DMR PORT1
					4:DMR PORT2
					"
		::= { ppMxpmRmonWeeklyIntfcSDataEntry 2 }

	ppMxpmRmonWeeklyIntfcSRxUnicast OBJECT-TYPE
		SYNTAX		OCTET STRING (SIZE (5))
		ACCESS		read-only
		STATUS		mandatory
		DESCRIPTION	"ppMxpmRmonWeeklyIntfcSRxUnicast
					FLAG=BITCNT(40)"
		::= { ppMxpmRmonWeeklyIntfcSDataEntry 3 }

	ppMxpmRmonWeeklyIntfcSRxBroadcast OBJECT-TYPE
		SYNTAX		OCTET STRING (SIZE (5))
		ACCESS		read-only
		STATUS		mandatory
		DESCRIPTION	"ppMxpmRmonWeeklyIntfcSRxBroadcast
					FLAG=BITCNT(40)"
		::= { ppMxpmRmonWeeklyIntfcSDataEntry 4 }

	ppMxpmRmonWeeklyIntfcSRxMulticast OBJECT-TYPE
		SYNTAX		OCTET STRING (SIZE (5))
		ACCESS		read-only
		STATUS		mandatory
		DESCRIPTION	"ppMxpmRmonWeeklyIntfcSRxMulticast
					FLAG=BITCNT(40)"
		::= { ppMxpmRmonWeeklyIntfcSDataEntry 5 }

	ppMxpmRmonWeeklyIntfcSRxPause OBJECT-TYPE
		SYNTAX		OCTET STRING (SIZE (5))
		ACCESS		read-only
		STATUS		mandatory
		DESCRIPTION	"ppMxpmRmonWeeklyIntfcSRxPause
					FLAG=BITCNT(40)"
		::= { ppMxpmRmonWeeklyIntfcSDataEntry 6 }

	ppMxpmRmonWeeklyIntfcSRxCrcError OBJECT-TYPE
		SYNTAX		OCTET STRING (SIZE (5))
		ACCESS		read-only
		STATUS		mandatory
		DESCRIPTION	"ppMxpmRmonWeeklyIntfcSRxCrcError
					FLAG=BITCNT(40)"
		::= { ppMxpmRmonWeeklyIntfcSDataEntry 7 }

	ppMxpmRmonWeeklyIntfcSRxFragments OBJECT-TYPE
		SYNTAX		OCTET STRING (SIZE (5))
		ACCESS		read-only
		STATUS		mandatory
		DESCRIPTION	"ppMxpmRmonWeeklyIntfsMRxFragments
					FLAG=BITCNT(40)"
		::= { ppMxpmRmonWeeklyIntfcSDataEntry 8 }

	ppMxpmRmonWeeklyIntfcSRx64Octets OBJECT-TYPE
		SYNTAX		OCTET STRING (SIZE (5))
		ACCESS		read-only
		STATUS		mandatory
		DESCRIPTION	"ppMxpmRmonWeeklyIntfsMRx64Octets
					FLAG=BITCNT(40)"
		::= { ppMxpmRmonWeeklyIntfcSDataEntry 9 }

	ppMxpmRmonWeeklyIntfcSRx65to127Octets OBJECT-TYPE
		SYNTAX		OCTET STRING (SIZE (5))
		ACCESS		read-only
		STATUS		mandatory
		DESCRIPTION	"ppMxpmRmonWeeklyIntfsMRx65to127Octets
					FLAG=BITCNT(40)"
		::= { ppMxpmRmonWeeklyIntfcSDataEntry 10 }

	ppMxpmRmonWeeklyIntfcSRx128to255Octets OBJECT-TYPE
		SYNTAX		OCTET STRING (SIZE (5))
		ACCESS		read-only
		STATUS		mandatory
		DESCRIPTION	"ppMxpmRmonWeeklyIntfsMRx128to255Octets
					FLAG=BITCNT(40)"
		::= { ppMxpmRmonWeeklyIntfcSDataEntry 11 }

	ppMxpmRmonWeeklyIntfcSRx256to511Octets OBJECT-TYPE
		SYNTAX		OCTET STRING (SIZE (5))
		ACCESS		read-only
		STATUS		mandatory
		DESCRIPTION	"ppMxpmRmonWeeklyIntfsMRx256to511Octets
					FLAG=BITCNT(40)"
		::= { ppMxpmRmonWeeklyIntfcSDataEntry 12 }

	ppMxpmRmonWeeklyIntfcSRx512to1023Octets OBJECT-TYPE
		SYNTAX		OCTET STRING (SIZE (5))
		ACCESS		read-only
		STATUS		mandatory
		DESCRIPTION	"ppMxpmRmonWeeklyIntfsMRx512to1023Octets
					FLAG=BITCNT(40)"
		::= { ppMxpmRmonWeeklyIntfcSDataEntry 13 }

	ppMxpmRmonWeeklyIntfcSRx1024to1536Octets OBJECT-TYPE
		SYNTAX		OCTET STRING (SIZE (5))
		ACCESS		read-only
		STATUS		mandatory
		DESCRIPTION	"ppMxpmRmonWeeklyIntfsMRx1024to1536Octets
					FLAG=BITCNT(40)"
		::= { ppMxpmRmonWeeklyIntfcSDataEntry 14 }

	ppMxpmRmonWeeklyIntfcSRx1537toMaxSizeOctets OBJECT-TYPE
		SYNTAX		OCTET STRING (SIZE (5))
		ACCESS		read-only
		STATUS		mandatory
		DESCRIPTION	"ppMxpmRmonWeeklyIntfsMRx1537toMaxSizeOctets
					FLAG=BITCNT(40)"
		::= { ppMxpmRmonWeeklyIntfcSDataEntry 15 }

	ppMxpmRmonWeeklyIntfcSRxJabbers OBJECT-TYPE
		SYNTAX		OCTET STRING (SIZE (5))
		ACCESS		read-only
		STATUS		mandatory
		DESCRIPTION	"ppMxpmRmonWeeklyIntfsMRxJabbers
					FLAG=BITCNT(40)"
		::= { ppMxpmRmonWeeklyIntfcSDataEntry 16 }

	ppMxpmRmonWeeklyIntfcSTxUnicast OBJECT-TYPE
		SYNTAX		OCTET STRING (SIZE (5))
		ACCESS		read-only
		STATUS		mandatory
		DESCRIPTION	"ppMxpmRmonWeeklyIntfsMTxUnicast
					FLAG=BITCNT(40)"
		::= { ppMxpmRmonWeeklyIntfcSDataEntry 17 }

	ppMxpmRmonWeeklyIntfcSTxBroadcast OBJECT-TYPE
		SYNTAX		OCTET STRING (SIZE (5))
		ACCESS		read-only
		STATUS		mandatory
		DESCRIPTION	"ppMxpmRmonWeeklyIntfsMTxBroadcast
					FLAG=BITCNT(40)"
		::= { ppMxpmRmonWeeklyIntfcSDataEntry 18 }

	ppMxpmRmonWeeklyIntfcSTxMulticast OBJECT-TYPE
		SYNTAX		OCTET STRING (SIZE (5))
		ACCESS		read-only
		STATUS		mandatory
		DESCRIPTION	"ppMxpmRmonWeeklyIntfsMTxMulticast
					FLAG=BITCNT(40)"
		::= { ppMxpmRmonWeeklyIntfcSDataEntry 19 }

	ppMxpmRmonWeeklyIntfcSTxPause OBJECT-TYPE
		SYNTAX		OCTET STRING (SIZE (5))
		ACCESS		read-only
		STATUS		mandatory
		DESCRIPTION	"ppMxpmRmonWeeklyIntfsMTxPause
					FLAG=BITCNT(40)"
		::= { ppMxpmRmonWeeklyIntfcSDataEntry 20 }

	ppMxpmRmonWeeklyIntfcSTxTotalCollision OBJECT-TYPE
		SYNTAX		OCTET STRING (SIZE (5))
		ACCESS		read-only
		STATUS		mandatory
		DESCRIPTION	"ppMxpmRmonWeeklyIntfsMTxTotalCollision
					When PortName is dmrPort1(3) to DmrPort2(4), Not Used (0 fixed)
					FLAG=BITCNT(40)"
		::= { ppMxpmRmonWeeklyIntfcSDataEntry 21 }

	ppMxpmRmonWeeklyIntfcSRxAlignmentError OBJECT-TYPE
		SYNTAX		OCTET STRING (SIZE (5))
		ACCESS		read-only
		STATUS		mandatory
		DESCRIPTION	"ppMxpmRmonWeeklyIntfsMRxAlignmentError
					When PortName is dmrPort1(3) to DmrPort2(4), Not Used (0 fixed)
					FLAG=BITCNT(40)"
		::= { ppMxpmRmonWeeklyIntfcSDataEntry 22 }

	ppMxpmRmonWeeklyIntfcSRxSymbolError OBJECT-TYPE
		SYNTAX		OCTET STRING (SIZE (5))
		ACCESS		read-only
		STATUS		mandatory
		DESCRIPTION	"ppMxpmRmonWeeklyIntfsMRxSymbolError
					When PortName is dmrPort1(3) to DmrPort2(4), Not Used (0 fixed)
					FLAG=BITCNT(40)"
		::= { ppMxpmRmonWeeklyIntfcSDataEntry 23 }

	ppMxpmRmonWeeklyIntfcSRxUndersize OBJECT-TYPE
		SYNTAX		OCTET STRING (SIZE (5))
		ACCESS		read-only
		STATUS		mandatory
		DESCRIPTION	"ppMxpmRmonWeeklyIntfsMRxUndersize
					When PortName is dmrPort1(3) to DmrPort2(4), Not Used (0 fixed)
					FLAG=BITCNT(40)"
		::= { ppMxpmRmonWeeklyIntfcSDataEntry 24 }


-----------------------------------------------
-- ppMxAuxIOInfo Group Definitions
-----------------------------------------------

	ppMxAuxInputItemTable OBJECT-TYPE
		SYNTAX		SEQUENCE OF PpMxAuxInputItemEntry
		ACCESS		not-accessible
		STATUS		mandatory
		DESCRIPTION	"AUX. Input Table"
		::= { ppMxAuxIOInfo 1 }

	ppMxAuxInputItemEntry OBJECT-TYPE
		SYNTAX		PpMxAuxInputItemEntry
		ACCESS		not-accessible
		STATUS		mandatory
		DESCRIPTION	"AUX. Input Table Entry"
		INDEX		{
						ppMxAuxInputItemPasoIndex,
						ppMxAuxInputItemIndex
					}
		::= { ppMxAuxInputItemTable 1 }

	PpMxAuxInputItemEntry ::= SEQUENCE {
					  ppMxAuxInputItemPasoIndex  IpAddress,
					  ppMxAuxInputItemIndex      INTEGER,
					  ppMxAuxInputItemValue      DeactiveActive01Value
					}
					
	ppMxAuxInputItemPasoIndex OBJECT-TYPE
		SYNTAX		IpAddress 
		ACCESS		read-only
		STATUS		mandatory
		DESCRIPTION	"Pasolink IP Address Index"
		::= { ppMxAuxInputItemEntry 1 }
		
	ppMxAuxInputItemIndex OBJECT-TYPE
		SYNTAX		INTEGER {
					  hk-in1(1),
					  hk-in2(2),
					  hk-in3(3),
					  hk-in4(4),
					  hk-in5(5),
					  hk-in6(6)
					}
		ACCESS		read-only
		STATUS		mandatory
		DESCRIPTION	"AUX INPUT INDEX"
		::= { ppMxAuxInputItemEntry 2 }

	ppMxAuxInputItemValue OBJECT-TYPE
		SYNTAX		DeactiveActive01Value
		ACCESS		read-only
		STATUS		mandatory
		DESCRIPTION	"0:INVALID, 1:EVENT OFF-OPEN LOOP, 2:EVENT ON-CLOSE LOOP
					FLAG=TRAP|EVLOG
					LOGITEM='%s'
					LOGSTATUS='%s'
					LOGFLAG='LII_I_HK_NAME_IN|LII_S_HK_NAME_IN|LII_T_HK_NAME_IN'
					TRAP=statusTrapPpMxAuxInput"
		::= { ppMxAuxInputItemEntry 3 }

	ppMxAuxOutputItemTable OBJECT-TYPE
		SYNTAX		SEQUENCE OF PpMxAuxOutputItemEntry
		ACCESS		not-accessible
		STATUS		mandatory
		DESCRIPTION	"AUX. Output Table"
		::= { ppMxAuxIOInfo 2 }

	ppMxAuxOutputItemEntry OBJECT-TYPE
		SYNTAX		PpMxAuxOutputItemEntry
		ACCESS		not-accessible
		STATUS		mandatory
		DESCRIPTION	"AUX. Output Table Entry"
		INDEX		{
						ppMxAuxOutputItemPasoIndex,
						ppMxAuxOutputItemIndex
					}
		::= { ppMxAuxOutputItemTable 1 }

	PpMxAuxOutputItemEntry ::= SEQUENCE {
					  ppMxAuxOutputItemPasoIndex IpAddress,
					  ppMxAuxOutputItemIndex  INTEGER,
					  ppMxAuxOutputItemValue  DeactiveActive01Value
					}

	ppMxAuxOutputItemPasoIndex OBJECT-TYPE
		SYNTAX		IpAddress 
		ACCESS		read-only
		STATUS		mandatory
		DESCRIPTION	"Pasolink IP Address Index"
		::= { ppMxAuxOutputItemEntry 1 }
		
	ppMxAuxOutputItemIndex OBJECT-TYPE
		SYNTAX		INTEGER {
					  hk-out1(1),
					  hk-out2(2),
					  hk-out3(3),
					  hk-out4(4)
					}
		ACCESS		read-only
		STATUS		mandatory
		DESCRIPTION	"AUX. OUTPUT INDEX"
		::= { ppMxAuxOutputItemEntry 2 }

	ppMxAuxOutputItemValue OBJECT-TYPE
		SYNTAX		DeactiveActive01Value
		ACCESS		read-only
		STATUS		mandatory
		DESCRIPTION	"0:INVALID, 1:EVENT OFF-OPEN LOOP, 2:EVENT ON-CLOSE LOOP
					FLAG=TRAP|EVLOG
					LOGITEM='%s'
					LOGSTATUS='%s'
					LOGFLAG='LII_I_HK_NAME_OUT|LII_S_HK_NAME_OUT'
					TRAP=eventTrapPpMxAuxOutput"
		::= { ppMxAuxOutputItemEntry 3 }

-----------------------------------------------
-- ppMxAuxIOInfo Group Definitions
-----------------------------------------------

	ppMxGetMeteringInfoData OBJECT IDENTIFIER
 		::= { ppMxGetMeasurementData 1 }

	ppMxGetMeteringInfoDataTable OBJECT-TYPE
		SYNTAX		SEQUENCE OF PpMxGetMeteringInfoDataEntry
		ACCESS		not-accessible
		STATUS		mandatory
		DESCRIPTION	"Measurement Data Table"
		::= { ppMxGetMeteringInfoData 1 }
	
	ppMxGetMeteringInfoDataEntry OBJECT-TYPE
		SYNTAX		PpMxGetMeteringInfoDataEntry
		ACCESS		not-accessible
		STATUS		mandatory
		DESCRIPTION	"Measurement Table Entry"
		INDEX { ppMxgmiManagerIndex } 
		::= { ppMxGetMeteringInfoDataTable 1 }

	PpMxGetMeteringInfoDataEntry ::= SEQUENCE {
		ppMxgmiManagerIndex		IpAddress,
		ppMxgmiRequestID		INTEGER,
		ppMxgmiTargetPasolink		IpAddress,
		ppMxgmiDataStatus		INTEGER	
	}

	ppMxgmiManagerIndex OBJECT-TYPE
		SYNTAX		IpAddress
		ACCESS		read-only
		STATUS		mandatory
		DESCRIPTION	"Higher-level manager IpAddress"
		::= { ppMxGetMeteringInfoDataEntry 1 }

	ppMxgmiRequestID OBJECT-TYPE
		SYNTAX		INTEGER (1..9999)
		ACCESS		read-write
		STATUS		mandatory
		DESCRIPTION	"Request ID"
		::= { ppMxGetMeteringInfoDataEntry 2 }
		
	ppMxgmiTargetPasolink OBJECT-TYPE
		SYNTAX		IpAddress
		ACCESS		read-write
		STATUS		mandatory
		DESCRIPTION	"Target Pasolink IpAddress"
		::= { ppMxGetMeteringInfoDataEntry 3 }
	
	ppMxgmiDataStatus OBJECT-TYPE
		SYNTAX		INTEGER (0..3)
		ACCESS		read-only
		STATUS		mandatory
		DESCRIPTION	"Data Status
				invalid(0),
				ready(1),
				wait(2),
				fail(3)"
		::= { ppMxGetMeteringInfoDataEntry 4 }

-----------------------------------------------
-- End User MIB Object Definitions
-----------------------------------------------
END

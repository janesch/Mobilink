------------------------------------------------------------------------------
--
-- (c) Copyright 2001-2009 mBalance.
--
--  This MIB is proprietary to and embodies the confidential technology of
--  mBalance. Possession, use, duplication or dissemination of this MIB is
--  authorized only pursuant to a valid written license from mBalance.
--
------------------------------------------------------------------------------
--
-- File    : textpass-apc-mib.my
-- Release : R04.01
-- $Id: textpass-apc-mib.my,v 1.64 2010/04/16 07:53:22 tdouglas Exp $
-- $Revision: 1.64 $

--------------------------------------------------------------------------------


TEXTPASS-APC-MIB DEFINITIONS ::= BEGIN

    ----------------------------------------------------------------------------
    --                              I M P O R T S                             --
    ----------------------------------------------------------------------------

    IMPORTS
        IpAddress, Gauge, Counter
            FROM RFC1155-SMI
        TEXTUAL-CONVENTION
            FROM SNMPv2-TC
        textpass
            FROM MBALANCE-MIB
        deviceType, IntervalTime, TcpPort,
        Throughput, AdminState, NameString, E164Address, OperationalState,
        TypeOfNumber, NumberingPlanIdentification, Boolean, Weight, Priority,
        LogLevel
            FROM TEXTPASS-GEN-MIB
        OBJECT-TYPE
            FROM RFC-1212
        TRAP-TYPE
            FROM RFC-1215;

    ----------------------------------------------------------------------------
    --                                T Y P E S                               --
    ----------------------------------------------------------------------------

    ----------------------------------------------------------------------------
    --
    --  AddressString: see description below
    --
    ----------------------------------------------------------------------------

    AddressString ::= TEXTUAL-CONVENTION
        DISPLAY-HINT "20a"
        STATUS mandatory
        DESCRIPTION
            "A UTF-8 string specifying an address. If the consists of decimal
            digits only, it is analysed and converted into a short number or
            an internationally significant number. Otherwise, it is treated
            as an alphanumeric address."
        SYNTAX OCTET STRING (SIZE (0..20))

    ----------------------------------------------------------------------------
    --
    --  AliasingMode, Not yet implemented
    --
    ----------------------------------------------------------------------------

    AliasingMode ::=
        INTEGER {
            none(0)
        }

    ----------------------------------------------------------------------------
    --
    --  AmsQueueIndex defines the index for an AMS queue
    --
    ----------------------------------------------------------------------------
        
    AmsQueueIndex ::=
        INTEGER (0..1000)

    ----------------------------------------------------------------------------
    --
    --  ApplicationAddressFormat specifies how an address is encoded in an AO/SM 
    --  or AT/SM that results from an MO/SM.
    --  Possible encodings are:
    --  - transparent, address is taken from MO/SM without any modification
    --  - national, address from MO/SM is converted to national format
    --  - international, address from MO/SM is converted to international format
    --  - asSystemWideSetting, address is encoded according to a system-wide 
    --    setting
    --
    ----------------------------------------------------------------------------

    ApplicationAddressFormat ::=
        INTEGER {
            transparent(0),
            national(1),
            international(2),
            asSystemWideSetting(3)
        }

    ----------------------------------------------------------------------------
    --
    --  ApplicationCategoryBitString defines the associated Application
    --  categories. The relating bit string specifies which
    --  Application Categories apply. Each bit in the bit string
    --  relates to a specific Application Category. If the bit is 1, the
    --  Application Category applies. Otherwise, if the bit is 0, the
    --  Application Category does not apply. Up to 1000 Application
    --  Categories can be defined. As such, the bit string consists of 1000
    --  bits with the least significant bit indicating whether Application
    --  Category with SNMP index 1 applies and the most significant bit
    --  indicating whether Application Category with SNMP index 1000
    --  applies.
    --
    ----------------------------------------------------------------------------

    ApplicationCategoryBitString ::=
        OCTET STRING (SIZE (1000..1000))

    ----------------------------------------------------------------------------
    --
    --  ApplicationCategoryTableIndex defines the range for the index of the
    --  Application Categroy table.
    --
    ----------------------------------------------------------------------------

    ApplicationCategoryTableIndex ::=
        INTEGER(1..1000)

    ----------------------------------------------------------------------------
    --
    --  ApplicationGroupTableIndex defines the range for the index of the Application
    --  Group table.
    --
    ----------------------------------------------------------------------------

    ApplicationGroupTableIndex ::=
        INTEGER(1..1000)

    ----------------------------------------------------------------------------
    --
    --  Application protocol type.
    --
    ----------------------------------------------------------------------------

    ApplicationProtocol ::=
        INTEGER {
            smpp(1),
            ucp(2),
            cimd(3)
        }

    ----------------------------------------------------------------------------
    --
    --  ApplicationServiceClassTableIndex defines the range for the index of
    --  the applicationServiceClass table.
    --
    ----------------------------------------------------------------------------

    ApplicationServiceClassTableIndex ::=
        INTEGER(1..10)

    ----------------------------------------------------------------------------
    --
    --  ApplicationTableIndex defines the range for the index of the Application
    --  table.
    --
    ----------------------------------------------------------------------------

    ApplicationTableIndex ::=
        INTEGER(0..10000)

    ----------------------------------------------------------------------------
    --
    --  ApplicationTimer defines the limits for Application related timers.
    --
    ----------------------------------------------------------------------------

    ApplicationTimer ::=
        Gauge(1..3600)

    ----------------------------------------------------------------------------
    --
    --  TimeStamp specifies the time in seconds since 1970 (UNIX time).
    --
    ----------------------------------------------------------------------------

    TimeStamp ::= 
        Gauge

    ----------------------------------------------------------------------------
    --
    --  HighResTime specifies a duration in miliseconds.
    --
    ----------------------------------------------------------------------------

    HighResTime ::= 
        Gauge

    ----------------------------------------------------------------------------
    --
    --  ApplicationType defines how SM's from/to the Application are routed.
    --
    --  TextPass supports the following routing possibilities:
    --
    --  1) Route through SMSC (throughSmsc)
    --  2) Route directly using SMPP protocol (smpp)
    --  3) Route directly using UCP protocol (ucp)
    --  4) Route directly using CIMD protocol (ucp)
    --
    ----------------------------------------------------------------------------

    ApplicationType ::=
        INTEGER {
            throughSmsc(0),
            smpp(1),
            ucp(2),
            cimd(3)
        }

    ----------------------------------------------------------------------------
    --
    --  ChargeIndication defines how a message should be charged.
    --  
    --  The following is supported:
    --  - chargeOriginator: charge originating Application
    --  - chargeRecipient: charge destination mobile
    --  - billingOnBehalfOf: charge mobile that Application specified as 
    --    originator
    --
    ----------------------------------------------------------------------------

    ChargeIndication ::=
        INTEGER {
            chargeOriginator(0),
            chargeRecipient(1),
            billingOnBehalfOf(2)
        }

    ----------------------------------------------------------------------------
    --
    --  ChargingUnits a business logic driven price modification
    --
    ----------------------------------------------------------------------------
        
    ChargingUnits ::=
        INTEGER (0..65535)
                                                                                        
    ----------------------------------------------------------------------------
    --
    --  CharSet defines the character sets
    --
    ----------------------------------------------------------------------------

    CharSet ::=
        INTEGER {
            gsmDefaultAlphabet(0),
            ascii7Bit(1),
            ascii8Bit(2)
        }

    ----------------------------------------------------------------------------
    --
    --  CimdConnections defines the number of CIMD links between TextPass and an
    --  Application.
    --
    ----------------------------------------------------------------------------

    CimdConnections ::=
        Gauge(0..255)

    ----------------------------------------------------------------------------
    --
    --  CimdInsidePassword defines an internal encoded password for a CIMD Application.
    --
    --  Supplying a zero-length string for the encoded password results in
    --  TextPass to send an empty password.
    --
    ----------------------------------------------------------------------------

    CimdInsidePassword ::=
        OCTET STRING (SIZE (0..32))

    ----------------------------------------------------------------------------
    --
    --  CimdOutsidePassword defines an MD5 encoded password for a CIMD Application.
    --  Note that CIMD allows the password to have a length of up to 32
    --  characters. MD5 encoding leads to a string of 16 bytes.
    --
    --  Supplying a zero-length string for the encoded password results in
    --  TextPass to accept any password.
    --
    ----------------------------------------------------------------------------

    CimdOutsidePassword ::=
        OCTET STRING (SIZE (0..16))

    ----------------------------------------------------------------------------
    --
    --  CimdPriority defines the values that a CIMD Application is allowed to
    --  specify for the priority. Implementation is done using a bit string.
    --  Each bit in the bit string relates to a priority value. If the bit is 1,
    --  the relating priority value applies. Otherwise, if the bit is 0, the
    --  relating priority value does not apply. The range of values for the
    --  priority is 1-9. As such, the bit string consists of 9 bits with
    --  the least significant bit indicating whether priority 1 applies and the
    --  most significant bit indicating whether priority 9 applies.
    --
    --  Example:
    --
    --    Supplying the following bitstring should result in TextPass accepting
    --    priority 1 and 2 for the relating Application and rejecting priority
    --    3 till 9.
    --
    --    000000011
    --
    ----------------------------------------------------------------------------

    CimdPriority ::=
        OCTET STRING (SIZE (9..9))

    ----------------------------------------------------------------------------
    --
    --  CimdServiceDescriptionMask defines the values that a CIMD Application is
    --  allowed to specify for the service description. Implementation is done
    --  using a bit string. Each bit in the bit string relates to a service
    --  description value. If the bit is 1, the relating service description
    --  value applies. Otherwise, if the bit is 0, the relating service
    --  description value does not apply. The range of values for the service
    --  description is 0-99. As such, the bit string consists of 100 bits with
    --  the least significant bit indicating whether service description 0
    --  applies and the most significant bit indicating whether service
    --  description 99 applies.
    --
    --  Example:
    --
    --    Supplying the following bitstring should result in TextPass accepting
    --    service description 98 and 99 for the relating Application and rejecting
    --    service description 1 till 97.
    --
    --    1100000000000000000000000000000000000000000000000000000000000000000000
    --    000000000000000000000000000000
    --
    ----------------------------------------------------------------------------

    CimdServiceDescriptionMask ::=
        OCTET STRING (SIZE (100..100))

    ----------------------------------------------------------------------------
    --
    --  CimdTariffClassMask defines the values that a CIMD Application is allowed
    --  to specify for the tariff class. Implementation is done using a bit
    --  string. Each bit in the bit string relates to a tariff class value. If
    --  the bit is 1, the relating tariff class value applies. Otherwise, if the
    --  bit is 0, the relating tariff class value does not apply. The range of
    --  values for the tariff class  is 0-99. As such, the bit string consists of
    --  100 bits with the least significant bit indicating whether tariff class 0
    --  applies and the most significant bit indicating whether tariff class 99
    --  applies.
    --
    --  Example:
    --
    --    Supplying the following bitstring should result in TextPass accepting
    --    tariff class 98 and 99 for the relating Application and rejecting
    --    tariff class 1 till 97.
    --
    --    1100000000000000000000000000000000000000000000000000000000000000000000
    --    000000000000000000000000000000
    --
    ----------------------------------------------------------------------------

    CimdTariffClassMask ::=
        OCTET STRING (SIZE (100..100))

    ----------------------------------------------------------------------------
    --
    --  CimdUserIdentity defines the user identity for a CIMD Application.
    --
    ----------------------------------------------------------------------------

    CimdUserIdentity ::=
        OCTET STRING (SIZE (0..32))

    ----------------------------------------------------------------------------
    --
    --  CimdWindowSize defines the window size as used on a link between TextPass
    --  and an Application.
    --
    ----------------------------------------------------------------------------

    CimdWindowSize ::=
        Gauge(1..128)

    ----------------------------------------------------------------------------
    --
    --  CliType defines the type of calling line identificcation authentication.
    --  This is only used in case it is enabled using the authentication method.
    --  Cli checking is only supported by the Hub not the Router. The following
    --  cli types are supported:
    --
    --  0) None
    --  1) Ip, authentication is done on applicationOutsideCliIpAddress and
    --     applicationOutsideCliTcpPort.
    --  2) X25, authentication is done on applicationOutsideCliX121Address
    --  3) GPRS, authtentication is done on applicationOutsideCliGprsMsisdn
    --  4) List, specifices a list of CLI address. The index of this list 
    --           has to be specified in applicationOutsideCliListIndex.
    --
    ----------------------------------------------------------------------------

    CliType ::=
        INTEGER {
            none(0),
            ip(1),
            x25(2),         -- for future use
            gprs(3),        -- for future use
            list(4)
        }

    ----------------------------------------------------------------------------
    --
    --  CliSourceAddressListIndex defines the range for the index of the 
    --  CLI source address list table. This index is only used by the HUB.
    --  The CliSourceAddressList is defined in the testpass-hub-mib.my.
    --
    ----------------------------------------------------------------------------

    CliSourceAddressListIndex ::=
        INTEGER(1..10000)

    ----------------------------------------------------------------------------
    --
    --  ConsolidationString specifies a string to be used in the CDR
    --  ConsolidationField.
    --
    ----------------------------------------------------------------------------

    ConsolidationString ::= TEXTUAL-CONVENTION
        DISPLAY-HINT "15a"
        STATUS mandatory
        DESCRIPTION "Consolidation string to be used in CDRs"
        SYNTAX OCTET STRING (SIZE (0..15))

    ----------------------------------------------------------------------------
    --
    --  DialoutSessions defines the number of sessions which can be setup
    --  with a dialout listener.
    --
    ----------------------------------------------------------------------------

    DialoutSessions ::=
        Gauge(0..100)

    ----------------------------------------------------------------------------
    --
    --  DialoutType defines the type of dialout session is used by the
    --  Application. The following dialout types are supported:
    --
    --  1) None
    --  2) Ip, dialout is done using Tcp/Ip. The address should be filled in
    --     using applicationOutsideDialoutIpAddress and
    --     applicationOutsideDialoutTcpPort.
    --  3) X25, dialout is done using X25. The address should be filled in
    --     using applicationOutsideDialoutX121Address
    --
    ----------------------------------------------------------------------------

    DialoutType ::=
        INTEGER {
            none(0),
            ip(1),
            x25(2)      -- for future use
        }

    ----------------------------------------------------------------------------
    --
    --  E164AddressRange specifies a number range formatted as following:
    --
    --  a) an internationally encoded E164 address excluding the international
    --     prefix of at most 15 digits, followed by
    --  b) a dash (-), followed by
    --  c) an internationally encoded E164 address excluding the international
    --     prefix of at most 15 digits.
    --
    --  or:
    --
    --  a) an internationally encoded E164 address excluding the international
    --     prefix of at most 15 digits.
    --
    --  To clear a number range, overwrite it with a zero-length string.
    --
    ----------------------------------------------------------------------------

    E164AddressRange ::=
        OCTET STRING (SIZE (0..31))

    ----------------------------------------------------------------------------
    --
    --  Configurable Error Mapping table index.  This type is also used in the
    --  HUB MIB.  Because the HUB MIB already imports from this MIB, this type
    --  had to be moved here.  (Better would be to place it in a shared MIB.)
    --
    ----------------------------------------------------------------------------

    ErrorMapIndex ::=
        INTEGER(1..100)

    ----------------------------------------------------------------------------
    --
    --  Specifies the value for the PID within an FCDR field of type 
    --  AddressInformation.
    --  Value -1 is special. It indicates that the PID should be set on the 
    --  basis of the Application protocol:
    --    - 57 for UCP 
    --    - 59 for SMPP
    --    - 55 for CIMD
    --
    ----------------------------------------------------------------------------
    
    FcdrAddressPid ::=
        INTEGER (-1..127)
        
    ----------------------------------------------------------------------------
    --
    --  InsideAuthenticationMethod defines the methods which are used to
    --  authenticate to the Service Centres. Implementation is done using a bit
    --  string. Each bit in the bit string relates to an authentication method.
    --  In this way multiple methods can be applied.
    --
    --  The bit string consist of 1 bit with the following meaning:
    --   bit 0: password authentication
    --
    --  This setting is only valid for the Hub, the Router will not setup any
    --  sessions.
    --
    --  Example:
    --    In case the Service Centre want password authentication only then the
    --    supplied bit string should become: 1
    --
    ----------------------------------------------------------------------------

    InsideAuthenticationMethod ::=
        OCTET STRING (SIZE (1..1))

    ----------------------------------------------------------------------------
    --
    --  LongMessageHandling defines how an AO/SM whose payload is too long for a
    --  single MT/SM should be handled.
    --
    ----------------------------------------------------------------------------
    
    LongMessageHandling ::=
        INTEGER{
            allowSendingToMobileAsConcatenated(0),
            allowSendingToMobileUsingLongLastTags(1),
            reject(2),
            onlyAllowSendingToSmsc(3)
        }

    ----------------------------------------------------------------------------
    --
    --  NotificationAddresMode defines how the notification address, if
    --  specified, is processed when a notification is requested.
    --  The following values can be used:
    --
    --  1) Transparent, transparently pass the notification address
    --  2) Clear, clear the notification address forcing it to a session only
    --     notification.
    --  3) CommonIp, fill in the common IP address of the TextPassHub including
    --     the applicationInsideDialoutListenPort.
    --  4) OwnIp, fill in the own IP address of the TextPassHub including the
    --     applicationInsideDialoutListenPort.
    --
    ----------------------------------------------------------------------------

    NotificationAddressMode ::=
        INTEGER {
            transparent(0),
            clear(1),
            commonIp(2),
            ownIp(3)
        }

    ----------------------------------------------------------------------------
    --
    --  NotificationHandling defines how the notifications of an Application
    --  are handled.
    --  The following values can be used:
    --
    --  1) sameSessionPreferred, the notification will be send
    --     over the source session. Another session is used if the session 
    --     is no longer available or a specific notification address is
    --     requested which is different then the configured Application.
    --  2) sameSessionOnly, the notification will only be send over the source
    --     session. The message will be discarded if it is no longer available.
    --     Requests with a specific notification address will be forced over the
    --     source session as well, no dialout will commence.
    --  3) dialoutPreferred, notifications with a specific notification address
    --     will always be send using the given address even if the Application
    --     has the same dialout address. The behavior of sameSessionPreferred
    --     will be used if no or an unsupported notification address is
    --     requested or dialout is not allowed.
    --  4) dialoutOnly, notifications with a specific notification address
    --     will always be send using the given address even if the Application.
    --     When no dialout is allowed or possible, the notification is rejected.
    --  5) sameHostOnly, similar to sameSessionPreferred, however if the source
    --     session is not found, and sourceIpAddress is given in the 
    --     SendNotificationRequest, it will only choose application sessions 
    --     that are also originating from the same IP address as defined in the 
    --     sourceIpAddress.
    --     If dial-out is allowed and requested, the priority sequence on 
    --     selection of sessions becomes: 1)same session that submitted the
    --     message. 2) A dial-out outside session to the defined notification
    --     address. If none exists than the session selection handling 
    --     tries to start one.
    --
    ----------------------------------------------------------------------------

    NotificationHandling ::=
        INTEGER {
            sameSessionPreferred(0),
            sameSessionOnly(1),
            dialoutPreferred(2),
            dialoutOnly(3),
            sameHostOnly(4)
        }

    ----------------------------------------------------------------------------
    --
    --  NotificationType defines the types of notification which may be requested.
    --  Implementation is done using a bit string.
    --  Each bit in the bit string relates to a notification type. In this
    --  way multiple types can be applied.
    --
    --  The bit string consist of 3 bits with the following meanings:
    --   bit 2: buffered
    --   bit 1: not delivered
    --   bit 0: delivered
    --
    --  Example:
    --    In case the Application wants to allow both delivere and not delivered
    --    notifications then the supplied bit string should become: 110
    --
    ----------------------------------------------------------------------------

    NotificationType ::=
        OCTET STRING (SIZE (3..3))

    ----------------------------------------------------------------------------
    --
    --  NrSmscOnlySessions defines the number of SMSC only sessions which should
    --  be setup towards each SMSC.
    --
    ----------------------------------------------------------------------------

    NrSmscOnlySessions ::=
        Gauge (0..255)

    ----------------------------------------------------------------------------
    --
    --  OutsideAuthenticationMethod defines the methods which are used to
    --  authenticate the Application. Implementation is done using a bit string.
    --  Each bit in the bit string relates to an authentication method. In this
    --  way multiple methods can be applied.
    --
    --  The bit string consist of 2 or 3 bits (bit 2 may be left out)
    --     with the following meanings:
    --   bit 0: password authentication
    --   bit 1: calling line identification authentication
    --   bit 2: Use 'OR' combination in stead of the default 'AND' behavior 
    --          (default 0 == 'AND')
    --
    --  In case cli authentication is requested then CliType and the corresponding
    --  address information needs to be supplied as well.
    --
    --  This setting is only valid for the Hub, the Router will always use
    --  password authentication.
    --
    --  Example:
    --   1) In case the Application want password authentication only then the
    --      supplied bit string should become: 100
    --   2) In case the Application want either password or cli authentication
    --      then the supplied bit string should become: 111
    --
    ----------------------------------------------------------------------------

    OutsideAuthenticationMethod ::=
        OCTET STRING (SIZE (2..3))

    ----------------------------------------------------------------------------
    --
    --  Percentage
    --
    ----------------------------------------------------------------------------

    Percentage ::=
        Gauge(0..100)

    ----------------------------------------------------------------------------
    --
    --  ScNodeTableIndex defines the range for the index of the Service
    --  Centre node table.
    --
    ----------------------------------------------------------------------------

    ScNodeTableIndex ::=
        INTEGER(1..500)

    ----------------------------------------------------------------------------
    --
    --  ScTerminationPointTableIndex defines the range for the index of the Service
    --  Centre Termination Point table.
    --
    ----------------------------------------------------------------------------

    ScTerminationPointTableIndex ::=
        INTEGER(1..1000)

    ----------------------------------------------------------------------------
    --
    --  ServiceCenteTableIndex defines the range for the index of the Service
    --  centre table.
    --
    ----------------------------------------------------------------------------

    ServiceCentreTableIndex ::=
        INTEGER(1..250)

    ----------------------------------------------------------------------------
    --
    -- In the ServiceClass only a subset of the session models is allowed:
    --
    ----------------------------------------------------------------------------

    ServiceClassSessionModel ::=
        INTEGER {
            insideOnlyAllScs(0),
            outsideOnly(1),
            permDialoutAllScs(2),
            replicateAllScs(3),
            distributeAllScs(4),
            insideOnlyScList(5),
            permDialoutScList(6),
            replicateScList(7),
            distributeScList(8)
        }

    ----------------------------------------------------------------------------
    --
    --  ServiceClassTableIndex defines the range for the index of the service
    --  class table.
    --
    ----------------------------------------------------------------------------

    ServiceClassTableIndex ::=
        INTEGER(1..1000)

    ----------------------------------------------------------------------------
    --
    --  SessionModel defines what kind of sessions are setup by the Application
    --
    --  TextPass supports the following session models:
    --
    --  0, 5) InsideOnly, Inbound SMS Application sessions are not allowed. The HUB
    --        will act as an bridge between routers and ServiceCentres.
    --        Two flavours:
    --        0) InsideOnlyAllScs (uses all available ServiceCentres) and
    --        5) InsideOnlyScList (uses only the specified ServiceCentres).
    --
    --  1)    OutsideOnly, Inbound SMS Application sessions will only be setup to
    --        routers, no ServiceCentres will be addressable.
    --
    --  2, 6) PermDialout, The HUB will setup sessions to the ServiceCentre for receiving
    --        messages. Only when messages arive dialout sessions to the SMS
    --        Application are setup. The dialout session will be dropped when no
    --        activity is shown for a configurable amount of time, while the session
    --        to the ServiceCentre remains active.
    --        Two flavours:
    --        2) PermDialoutAllScs (uses all available ServiceCentres) and
    --        6) PermDialoutScList (uses only the specified ServiceCentres).
    --
    --  3, 7) Replicate, Inbound LA sessions are replicated to each ServiceCentre.
    --        If capacity is not enough then more will be setup.
    --        Two flavours:
    --        3) ReplicateAllScs (uses all available ServiceCentres) and
    --        7) ReplicateScList (uses only the specified ServiceCentres).
    --
    --  4, 8) Distribute, Inbound LA sessions are distributed to each ServiceCentre.
    --        If another LA sessions is connected and enough capacity is available
    --        then no more sessions are setup.
    --        Two flavours:
    --        4) DistributeAllScs (uses all available ServiceCentres) and
    --        8) DistributeScList (uses only the specified ServiceCentres).
    --
    --  9)    useServiceClassModel, may only be used by applications to indicate
    --        that the session will be taken from the used serviceClass.
    --
    ----------------------------------------------------------------------------

    SessionModel ::=
        INTEGER {
            insideOnlyAllScs(0),
            outsideOnly(1),
            permDialoutAllScs(2),
            replicateAllScs(3),
            distributeAllScs(4),
            insideOnlyScList(5),
            permDialoutScList(6),
            replicateScList(7),
            distributeScList(8),
            useServiceClassModel(9)
        }

    ----------------------------------------------------------------------------
    --
    --  SmppBindType defines the bind type to use for SMPP links between 
    --  TextPass and a Termination Point (insideOnly).
    --
    ----------------------------------------------------------------------------

    SmppBindType ::=
        INTEGER {
            bindRxTx(0),
            bindTrx(1)
        }
    ----------------------------------------------------------------------------
    --
    --  SmppBindVersion defines the bind version to use for SMPP links between 
    --  TextPass and a Termination Point (insideOnly).
    --
    ----------------------------------------------------------------------------

    SmppBindVersion ::=
        INTEGER {
            smpp33(0),
            smpp34(1)
        }

    ----------------------------------------------------------------------------
    --
    --  SmppConnections defines the number of SMPP links between TextPass and an
    --  Application.
    --
    ----------------------------------------------------------------------------

    SmppConnections ::=
        Gauge(0..255)

    ----------------------------------------------------------------------------
    --
    --  SmppError defines the errors as used in GSM
    --
    ----------------------------------------------------------------------------

    SmppError ::=
        INTEGER {
            unknownError(0)
        }

    ----------------------------------------------------------------------------
    --
    --  SmppInsidePassword defines an internal encoded password for an SMPP
    --  Application.
    --
    ----------------------------------------------------------------------------

    SmppInsidePassword ::=
        OCTET STRING (SIZE (0..8))

    ----------------------------------------------------------------------------
    --
    --  SmppOutsidePassword defines an MD5 encoded password for an SMPP Application.
    --
    --  For details, refer to SMPP specification which is available at
    --  http://smsforum.net/
    --
    ----------------------------------------------------------------------------

    SmppOutsidePassword ::=
        OCTET STRING (SIZE (0..16))

    ----------------------------------------------------------------------------
    --
    --  SmppRetErrCode defines the error range which can be returned in error
    --  message.
    --
    ----------------------------------------------------------------------------

    SmppRetErrCode ::=
        Gauge(0..1279)

    ----------------------------------------------------------------------------
    --
    --  SmppSystemId defines a system ID as defined in SMPP.
    --
    --  For details, refer to SMPP specification which is available at
    --  http://smsforum.net/
    --
    ----------------------------------------------------------------------------

    SmppSystemId ::= TEXTUAL-CONVENTION
        DISPLAY-HINT "15a"
        STATUS mandatory
        DESCRIPTION "SMPP system ID"
        SYNTAX OCTET STRING (SIZE (1..15))

    ----------------------------------------------------------------------------
    --
    --  SmppSystemType defines a system type as defined in SMPP.
    --
    --  For details, refer to SMPP specification which is available at
    --  http://smsforum.net/
    --
    ----------------------------------------------------------------------------

    SmppSystemType ::= TEXTUAL-CONVENTION
        DISPLAY-HINT "12a"
        STATUS mandatory
        DESCRIPTION "SMPP system type"
        SYNTAX OCTET STRING (SIZE (0..12))

    ----------------------------------------------------------------------------
    --
    --  SmppWindowSize defines the window size as used on a link between
    --  TextPass and an Application.
    --
    ----------------------------------------------------------------------------

    SmppWindowSize ::=
        Gauge(1..255)

    ----------------------------------------------------------------------------
    --
    --  TerminationPointConnections defines the number of connections setup
    --  towards a Termination Point.
    --
    ----------------------------------------------------------------------------

    TerminationPointConnections ::=
        Gauge(0..2000)

    ----------------------------------------------------------------------------
    --
    --  TrafficType defines the type of traffic which can be handled. The
    --  following values are allowed:
    --   0)  aoAt, both Ao and At messages are allowed
    --   1)  ao,    only Ao messages are allowed
    --   2)  at,    only At messages are allowed
    --
    ----------------------------------------------------------------------------

    TrafficType ::=
        INTEGER {
            aoAt(0),
            ao(1),
            at(2)
        }


    ----------------------------------------------------------------------------
    --
    --  UcpConnections defines the number of UCP links between TextPass and an
    --  Application.
    --
    ----------------------------------------------------------------------------

    UcpConnections ::=
        Gauge(0..255)

    ----------------------------------------------------------------------------
    --
    --  UcpInsidePassword defines an internal encoded password for a UCP Application.
    --
    ----------------------------------------------------------------------------

    UcpInsidePassword ::=
        OCTET STRING (SIZE (0..16))

    ----------------------------------------------------------------------------
    --
    --  UcpOutsidePassword defines an MD5 encoded password for a UCP Application.
    --
    ----------------------------------------------------------------------------

    UcpOutsidePassword ::=
        OCTET STRING (SIZE (0..16))

    ----------------------------------------------------------------------------
    --
    --  UcpWindowSize defines the window size as used on a link between TextPass
    --  and an Application.
    --
    ----------------------------------------------------------------------------

    UcpWindowSize ::=
        Gauge(1..100)

    ----------------------------------------------------------------------------
    --
    --  X121Address specifies a X121 number
    --
    ----------------------------------------------------------------------------

    X121Address ::=                                -- should contain digits only
        OCTET STRING(SIZE (0..16))

    ----------------------------------------------------------------------------
    -- Type used to specify which custom character set is used.
    -- value 0 must be used to specify that NO custom character set is used. 
    ----------------------------------------------------------------------------
    CustomCharacterSet ::=
        INTEGER(0..5)

    ---------------------------------------------------------------------------- 
    -- 
    --  DelayTime specifies the time range for an application's delay time. 
    -- 
    ---------------------------------------------------------------------------- 
    DelayTime ::= 
        Gauge(0..60)

    ----------------------------------------------------------------------------
    --                              O B J E C T S                             --
    ----------------------------------------------------------------------------

    apc OBJECT IDENTIFIER ::= { textpass 33 }

    -- Application table

    applicationTable OBJECT-TYPE
        SYNTAX  SEQUENCE OF ApplicationEntry
        ACCESS  not-accessible
        STATUS  mandatory
        DESCRIPTION
            "A table containing properties and counters for each Application."
        ::= { apc 11 }

    applicationEntry OBJECT-TYPE
        SYNTAX  ApplicationEntry
        ACCESS  not-accessible
        STATUS  mandatory

        DESCRIPTION
            "Table entry defining a single Application."
        INDEX   { applicationIndex }
        ::= { applicationTable 1 }

    ApplicationEntry ::=
        SEQUENCE {
            applicationIndex                      ApplicationTableIndex,
            applicationAdminState                 AdminState,
            applicationName                       NameString,
            applicationShortNumber                E164Address,
            applicationType                       ApplicationType,
            applicationSessionModel               SessionModel,
            applicationNrSmscOnlySessions         NrSmscOnlySessions,
            applicationLogLevel                   LogLevel,
            applicationApplicationGroupIndex      ApplicationGroupTableIndex,
            applicationApplicationCategoryBits    ApplicationCategoryBitString,
            applicationThroughputAoMaximum        Throughput,
            applicationThroughputAtMaximum        Throughput,
            applicationThroughputAoCommitted      Throughput,
            applicationThroughputAtCommitted      Throughput,
            applicationPreferredCharacterSet      CharSet,
            applicationOperationalState           OperationalState,
            applicationForwardErrorMapIndex       ErrorMapIndex,
            applicationReverseErrorMapIndex       ErrorMapIndex,
            applicationFcdrRecipAddressPidForAt   FcdrAddressPid,
            applicationFcdrOrigAddressPidForAo    FcdrAddressPid,
            applicationOutsideAuthenticationMethod OutsideAuthenticationMethod,
            applicationOutsideCliType             CliType,
            applicationOutsideCliIpAddress        IpAddress,
            applicationOutsideCliIpMask           IpAddress,
            applicationOutsideCliTcpPort          TcpPort,
            applicationOutsideCliX121Address      X121Address,
            applicationOutsideCliGprsMsisdn       E164Address,
            applicationOutsideDialoutType         DialoutType,
            applicationOutsideDialoutIpAddress    IpAddress,
            applicationOutsideDialoutTcpPort      TcpPort,
            applicationOutsideDialoutX121Address  X121Address,
            applicationOutsideMaxInactivityTime   ApplicationTimer,
            applicationOutsideMaxResponseTime     ApplicationTimer,
            applicationOutsideDialoutInactivityTime ApplicationTimer,
            applicationOutsideDialoutMaxSessions  DialoutSessions,
            applicationInsideDialoutListenPort    TcpPort,
            applicationInsideDialoutMaxSessions   DialoutSessions,
            applicationInsideAuthenticationMethod InsideAuthenticationMethod,
            applicationInsideOnlySmppBindVersion  SmppBindVersion,
            applicationInsideOnlySmppBindType     SmppBindType,
            applicationSmppSystemId               SmppSystemId,
            applicationSmppSystemType             SmppSystemType,
            applicationOutsideSmppPassword        SmppOutsidePassword,
            applicationOutsideSmppAddressRange    E164AddressRange,
            applicationOutsideSmppAddressRangeTon TypeOfNumber,
            applicationOutsideSmppAddressRangeNpi NumberingPlanIdentification,
            applicationOutsideSmppWindowSize      SmppWindowSize,
            applicationOutsideSmppMaxReceivers    SmppConnections,
            applicationOutsideSmppMaxTransmitters SmppConnections,
            applicationOutsideSmppMaxTransceivers SmppConnections,
            applicationOutsideDialoutSmppWindowSize SmppWindowSize,
            applicationOutsideDialoutSmppPassword   SmppInsidePassword,
            applicationOutsideCliListIndex        CliSourceAddressListIndex,
            applicationInsideSmppPassword         SmppInsidePassword,
            applicationInsideSmppWindowSize       SmppWindowSize,
            applicationOutsideUcpPassword         UcpOutsidePassword,
            applicationOutsideUcpWindowSize       UcpWindowSize,
            applicationOutsideUcpMaxSessions      UcpConnections,
            applicationOutsideDialoutUcpWindowSize UcpWindowSize,
            applicationInsideUcpPassword          UcpInsidePassword,
            applicationInsideUcpWindowSize        UcpWindowSize,
            applicationOutsideCimdUserIdentity    CimdUserIdentity,
            applicationOutsideCimdPassword        CimdOutsidePassword,
            applicationOutsideCimdWindowSize      CimdWindowSize,
            applicationOutsideCimdMaxSessions     CimdConnections,
            applicationOutsideCimdTariffClass     CimdTariffClassMask,
            applicationOutsideCimdServiceDescription CimdServiceDescriptionMask,
            applicationOutsideCimdPriority        CimdPriority,
            applicationOutsideDialoutCimdWindowSize CimdWindowSize,
            applicationInsideCimdPassword         CimdInsidePassword,
            applicationInsideCimdWindowSize       CimdWindowSize,
            applicationOutsideMinimumSessionsThreshold Percentage,
            applicationInsideMinimumSessionsThreshold  Percentage,
            applicationOutsideLifeCheckInterval   IntervalTime,
            applicationCharacterSet               CustomCharacterSet,            
            applicationAliasingMode               AliasingMode,
            applicationConsolidationField         ConsolidationString,
            applicationAllowNotification          Boolean,
            applicationNotificationAddressMode    NotificationAddressMode,
            applicationOptimisedMtDelivery        Boolean,
            applicationAoEnabled                  Boolean,
            applicationAtEnabled                  Boolean,
            applicationRespondAfterDelivery       Boolean,
            applicationRoutingPathAoMtEnabled     Boolean,
            applicationRoutingPathAoMtAoEnabled   Boolean,
            applicationGsmStatusReportInitiatedByApplication Boolean,
            applicationLongMessageHandling        LongMessageHandling,
            applicationNotificationHandling       NotificationHandling,
            applicationEnableAtRecipientStats     Boolean,
            applicationFormatOriginator           ApplicationAddressFormat,
            applicationFormatRecipient            ApplicationAddressFormat,
            applicationFormatMsc                  ApplicationAddressFormat,
            applicationFormatSmsc                 ApplicationAddressFormat,
            applicationInsideDialoutSessionsCounter DialoutSessions,
            applicationOutsideDialoutSessionsCounter DialoutSessions,
            applicationOutsideSmppReceiversCounter    SmppConnections,
            applicationOutsideSmppTransmittersCounter SmppConnections,
            applicationOutsideSmppTransceiversCounter SmppConnections,
            applicationInsideSmppReceiversCounter     SmppConnections,
            applicationInsideSmppTransmittersCounter  SmppConnections,
            applicationInsideSmppTransceiversCounter  SmppConnections,
            applicationOutsideUcpSessionsCounter  UcpConnections,
            applicationInsideUcpSessionsCounter   UcpConnections,
            applicationOutsideCimdSessionsCounter CimdConnections,
            applicationInsideCimdSessionsCounter  CimdConnections,
            applicationOutsideCapacityUsageAo     Percentage,
            applicationOutsideCapacityUsageAt     Percentage,
            applicationOutsideSessionsPending     Gauge,
            applicationInsideCapacityUsageAo      Percentage,
            applicationInsideCapacityUsageAt      Percentage,
            applicationInsideSessionsPending      Gauge,
            applicationMoTotalCounter             Counter,
            applicationMoSuccessfulCounter        Counter,
            applicationMoTimeoutCounter           Counter,
            applicationMoDroppedCounter           Counter,
            applicationMoDiscardWithNakCounter    Counter,
            applicationMoRejectedByTprCounter     Counter,
            applicationMoRejectedByAppCounter     Counter,
            applicationMoUnknownResultCounter     Counter,
            applicationMoSysFailErrorCounter      Counter,
            applicationMoDataMisErrorCounter      Counter,
            applicationMoUnexpDataValErrorCounter Counter,
            applicationMoFacNotSuppErrorCounter   Counter,
            applicationMoUnkScErrorCounter        Counter,
            applicationMoScCongErrorCounter       Counter,
            applicationMoInvSmeAddrErrorCounter   Counter,
            applicationMoSubNotScSubErrorCounter  Counter,
            applicationMoOtherErrorsCounter       Counter,
            applicationMoTcapAbortedCounter       Counter,
            applicationMoSccpAbortedCounter       Counter,
            applicationMtTotalCounter             Counter,
            applicationMtSuccessfulCounter        Counter,
            applicationMtTimeoutCounter           Counter,
            applicationMtAbsSubErrorCounter       Counter,
            applicationMtSysFailErrorCounter      Counter,
            applicationMtDataMisErrorCounter      Counter,
            applicationMtUnexpDataValErrorCounter Counter,
            applicationMtFacNotSuppErrorCounter   Counter,
            applicationMtUnidenSubErrorCounter    Counter,
            applicationMtIllSubErrorCounter       Counter,
            applicationMtIllEquipErrorCounter     Counter,
            applicationMtSubBusyForMtSmErrorCounter Counter,
            applicationMtInvSmeAddrErrorCounter   Counter,
            applicationMtEquipProtErrorCounter    Counter,
            applicationMtEquipNotSmEquipErrorCounter Counter,
            applicationMtMemCapExcErrorCounter    Counter,
            applicationMtOtherErrorsCounter       Counter,
            applicationMtTcapAbortedCounter       Counter,
            applicationMtSccpAbortedCounter       Counter,
            applicationMtFallbackToVersion2Counter Counter,
            applicationMtFallbackToVersion1Counter Counter,
            applicationMtAlternatePathUsedCounter Counter,
            applicationMtAlternatePathNotUsedCounter Counter,
            applicationSriSmTotalCounter          Counter,
            applicationSriSmSuccessCounter        Counter,
            applicationSriSmTimeoutCounter        Counter,
            applicationSriSmSysFailErrorCounter   Counter,
            applicationSriSmDataMisErrorCounter   Counter,
            applicationSriSmUnexpDataValErrorCounter Counter,
            applicationSriSmFacNotSuppErrorCounter Counter,
            applicationSriSmUnkSubErrorCounter    Counter,
            applicationSriSmAbsSubErrorCounter    Counter,
            applicationSriSmCallBarredErrorCounter Counter,
            applicationSriSmTeleServNotProvErrorCounter Counter,
            applicationSriSmOtherErrorsCounter    Counter,
            applicationSriSmTcapAbortedCounter    Counter,
            applicationSriSmSccpAbortedCounter    Counter,
            applicationSriSmFallbackToVersion2Counter Counter,
            applicationSriSmFallbackToVersion1Counter Counter,
            applicationRepStsTotalCounter         Counter,
            applicationRepStsSuccessCounter       Counter,
            applicationRepStsTimeoutCounter       Counter,
            applicationRepStsSysFailErrorCounter  Counter,
            applicationRepStsDataMisErrorCounter  Counter,
            applicationRepStsUnexpDataValErrorCounter Counter,
            applicationRepStsUnkSubErrorCounter   Counter,
            applicationRepStsMsgWaitListFullErrorCounter Counter,
            applicationRepStsOtherErrorsCounter   Counter,
            applicationRepStsTcapAbortedCounter   Counter,
            applicationRepStsSccpAbortedCounter   Counter,
            applicationRepStsFallbackToVersion2Counter Counter,
            applicationRepStsFallbackToVersion1Counter Counter,
            applicationCntInsideAoTotal           Counter,
            applicationCntInsideAoSuccess         Counter,
            applicationCntInsideAoSourceError     Counter,
            applicationCntInsideAoRoutingError    Counter,
            applicationCntInsideAoDestinationTemporaryError Counter,
            applicationCntInsideAoDestinationPermanentRecipientError Counter,
            applicationCntInsideAoDestinationPermanentMessageError Counter,
            applicationCntInsideAtTotal           Counter,
            applicationCntInsideAtSuccess         Counter,
            applicationCntInsideAtSourceError     Counter,
            applicationCntInsideAtRoutingError    Counter,
            applicationCntInsideAtDestinationTemporaryError Counter,
            applicationCntInsideAtDestinationPermanentRecipientError Counter,
            applicationCntInsideAtDestinationPermanentMessageError Counter,
            applicationCntOutsideAoTotal          Counter,
            applicationCntOutsideAoSuccess        Counter,
            applicationCntOutsideAoSourceError    Counter,
            applicationCntOutsideAoRoutingError   Counter,
            applicationCntOutsideAoDestinationTemporaryError Counter,
            applicationCntOutsideAoDestinationPermanentRecipientError Counter,
            applicationCntOutsideAoDestinationPermanentMessageError Counter,
            applicationCntOutsideAtTotal          Counter,
            applicationCntOutsideAtSuccess        Counter,
            applicationCntOutsideAtSourceError    Counter,
            applicationCntOutsideAtRoutingError   Counter,
            applicationCntOutsideAtDestinationTemporaryError Counter,
            applicationCntOutsideAtDestinationPermanentRecipientError Counter,
            applicationCntOutsideAtDestinationPermanentMessageError Counter,
            applicationCntAoMtSuccess             Counter,
            applicationCntAoMtFailure             Counter,
            applicationCntAoAoSuccess             Counter,
            applicationCntAoAoFailure             Counter,
            applicationCntAtAtSuccess             Counter,
            applicationCntAtAtFailure             Counter,
            applicationCntMoMoSuccess             Counter,
            applicationCntMoMoFailure             Counter,
            applicationCntMoAoSuccess             Counter,
            applicationCntMoAoFailure             Counter,
            applicationCntMoAtSuccess             Counter,
            applicationCntMoAtFailure             Counter,
            applicationCntMtMtSuccess             Counter,
            applicationCntMtMtFailure             Counter,
            applicationCntAoDiscard               Counter,
            applicationCntAtDiscard               Counter,
            applicationCntMoDiscard               Counter,
            applicationCntMtDiscard               Counter,
            applicationCntAoMtAoPrimarySuccess    Counter,
            applicationCntAoMtAoFallbackSuccess   Counter,
            applicationCntAoMtAoFallbackFailure   Counter,
            applicationCntAoMtAoPrimaryFailure    Counter,
            applicationCntAoMtAoFallbackNotAppliedDueToPermErrorOnPrimary Counter,
            applicationCntAoMtAoFallbackNotAppliedDueToUnavailability Counter,
            applicationCntAoMtToAmsSuccess        Counter,
            applicationCntAoMtToAmsFailure        Counter,
            applicationCntAoMtAmsSuccess          Counter,
            applicationCntAoMtAmsFailure          Counter,
            applicationCntMoMtToAmsSuccess        Counter,
            applicationCntMoMtToAmsFailure        Counter,
            applicationCntMoMtAmsPrimarySuccess   Counter,
            applicationCntMoMtAmsPrimaryFailure   Counter,
            applicationCntMoMtAmsFallbackSuccess  Counter,
            applicationCntMoMtAmsFallbackFailure  Counter,
            applicationCntMoMtAmsFallbackNotAppliedDueToPermErrorOnPrimary Counter,
            applicationCntMoMtAmsFallbackNotAppliedDueToUnavailability Counter,
            applicationCntMoAtToAmsSuccess        Counter,
            applicationCntMoAtToAmsFailure        Counter,
            applicationCntMoAtAmsPrimarySuccess   Counter,
            applicationCntMoAtAmsPrimaryFailure   Counter,
            applicationCntMoAtAmsFallbackSuccess  Counter,
            applicationCntMoAtAmsFallbackFailure  Counter,
            applicationCntMoAtAmsFallbackNotAppliedDueToPermErrorOnPrimary Counter,
            applicationCntMoAtAmsFallbackNotAppliedDueToUnavailability Counter,
            applicationCntMoMtMoPrimarySuccess    Counter,
            applicationCntMoMtMoPrimaryFailure    Counter,
            applicationCntMoMtMoFallbackSuccess   Counter,
            applicationCntMoMtMoFallbackFailure   Counter,
            applicationCntMoMtMoFallbackNotAppliedDueToPermErrorOnPrimary Counter,
            applicationCntMoMtMoFallbackNotAppliedDueToUnavailability Counter,
            applicationCntMoMtAtPrimarySuccess    Counter,
            applicationCntMoMtAtPrimaryFailure    Counter,
            applicationCntMoMtAtFallbackSuccess   Counter,
            applicationCntMoMtAtFallbackFailure   Counter,
            applicationCntMoMtAtFallbackNotAppliedDueToPermErrorOnPrimary Counter,
            applicationCntMoMtAtFallbackNotAppliedDueToUnavailability Counter,
            applicationCntMoMtAoPrimarySuccess    Counter,
            applicationCntMoMtAoPrimaryFailure    Counter,
            applicationCntMoMtAoFallbackSuccess   Counter,
            applicationCntMoMtAoFallbackFailure   Counter,
            applicationCntMoMtAoFallbackNotAppliedDueToPermErrorOnPrimary Counter,
            applicationCntMoMtAoFallbackNotAppliedDueToUnavailability Counter,
            applicationCntMoMtSuccess             Counter,
            applicationCntMoMtFailure             Counter,
            applicationCntAoAtSuccess             Counter,
            applicationCntAoAtFailure             Counter,
            applicationCntAoAtToAmsSuccess        Counter,
            applicationCntAoAtToAmsFailure        Counter,
            applicationCntAoAtAmsSuccess          Counter,
            applicationCntAoAtAmsFailure          Counter,
            applicationCntAoAoToAmsSuccess        Counter,
            applicationCntAoAoToAmsFailure        Counter,
            applicationCntAoAoAmsPrimarySuccess   Counter,
            applicationCntAoAoAmsPrimaryFailure   Counter,
            applicationCntAoAoAmsFallbackSuccess  Counter,
            applicationCntAoAoAmsFallbackFailure  Counter,
            applicationCntAoAoAmsFallbackNotAppliedDueToPermErrorOnPrimary Counter,
            applicationCntAoAoAmsFallbackNotAppliedDueToUnavailability Counter,
            applicationCntAtAtToAmsSuccess        Counter,
            applicationCntAtAtToAmsFailure        Counter,
            applicationCntAtAtAmsPrimarySuccess   Counter,
            applicationCntAtAtAmsPrimaryFailure   Counter,
            applicationCntAtAtAmsFallbackSuccess  Counter,
            applicationCntAtAtAmsFallbackFailure  Counter,
            applicationCntAtAtAmsFallbackNotAppliedDueToPermErrorOnPrimary Counter,
            applicationCntAtAtAmsFallbackNotAppliedDueToUnavailability Counter,
            applicationCntAtAoSuccess             Counter,
            applicationCntAtAoFailure             Counter,
            applicationCntAtAoToAmsSuccess        Counter,
            applicationCntAtAoToAmsFailure        Counter,
            applicationCntAtAoAmsPrimarySuccess   Counter,
            applicationCntAtAoAmsPrimaryFailure   Counter,
            applicationCntAtAoAmsFallbackSuccess  Counter,
            applicationCntAtAoAmsFallbackFailure  Counter,
            applicationCntAtAoAmsFallbackNotAppliedDueToPermErrorOnPrimary Counter,
            applicationCntAtAoAmsFallbackNotAppliedDueToUnavailability Counter,
            applicationCntAoThroughputLimitHit    Counter,
            applicationCntAtThroughputLimitHit    Counter,
            applicationCntAoMtFromAmsSuccess      Counter,
            applicationCntAoMtFromAmsTemporaryError Counter, 
            applicationCntAoMtFromAmsPermanentRecipientError Counter,
            applicationCntAoMtFromAmsPermanentMessageError Counter,
            applicationCntAoMtFromAmsExpired      Counter,
            applicationCntAoMtFromAmsDeleted      Counter,
            applicationCntAoMtFromAmsReplaced     Counter,
            applicationCntMoMtFromAmsSuccess      Counter,
            applicationCntMoMtFromAmsTemporaryError Counter, 
            applicationCntMoMtFromAmsPermanentRecipientError Counter,
            applicationCntMoMtFromAmsPermanentMessageError Counter,
            applicationCntMoMtFromAmsExpired      Counter,
            applicationCntMoMtFromAmsDeleted      Counter,
            applicationCntMoMtFromAmsReplaced     Counter,
            applicationCntAoAtFromAmsSuccess      Counter,
            applicationCntAoAtFromAmsTemporaryError Counter, 
            applicationCntAoAtFromAmsPermanentRecipientError Counter,
            applicationCntAoAtFromAmsPermanentMessageError Counter,
            applicationCntAoAtFromAmsExpired      Counter,
            applicationCntAoAtFromAmsDeleted      Counter,
            applicationCntAoAtFromAmsReplaced     Counter,
            applicationCntAoAoFromAmsSuccess      Counter,
            applicationCntAoAoFromAmsTemporaryError Counter,
            applicationCntAoAoFromAmsPermanentRecipientError Counter,
            applicationCntAoAoFromAmsPermanentMessageError Counter,
            applicationCntAoAoFromAmsExpired      Counter,
            applicationCntAoAoFromAmsDeleted      Counter,
            applicationCntAoAoFromAmsReplaced     Counter,
            applicationCntMoAtFromAmsSuccess      Counter,
            applicationCntMoAtFromAmsTemporaryError Counter, 
            applicationCntMoAtFromAmsPermanentRecipientError Counter,
            applicationCntMoAtFromAmsPermanentMessageError Counter,
            applicationCntMoAtFromAmsExpired      Counter,
            applicationCntMoAtFromAmsDeleted      Counter,
            applicationCntMoAtFromAmsReplaced     Counter,
            applicationCntAtAoFromAmsSuccess      Counter,
            applicationCntAtAoFromAmsTemporaryError Counter,
            applicationCntAtAoFromAmsPermanentRecipientError Counter,
            applicationCntAtAoFromAmsPermanentMessageError Counter,
            applicationCntAtAoFromAmsExpired      Counter,
            applicationCntAtAoFromAmsDeleted      Counter,
            applicationCntAtAoFromAmsReplaced     Counter,
            applicationCntLongAoMessagesProcessed Counter,
            applicationCntAoOriginatorListViolations Counter,
            applicationCntOutsideAoRejected       Counter,
            applicationCntInsideAtRejected        Counter,
            applicationCntAoUcp01Request          Counter,
            applicationCntAoUcp01Ack              Counter,
            applicationCntAoUcp01Nack             Counter,
            applicationCntAoUcp02Request          Counter,
            applicationCntAoUcp02Ack              Counter,
            applicationCntAoUcp02Nack             Counter,
            applicationCntAoUcp30Request          Counter,
            applicationCntAoUcp30Ack              Counter,
            applicationCntAoUcp30Nack             Counter,
            applicationCntAoUcp31Request          Counter,
            applicationCntAoUcp31Ack              Counter,
            applicationCntAoUcp31Nack             Counter,
            applicationCntAoUcp51Request          Counter,
            applicationCntAoUcp51Ack              Counter,
            applicationCntAoUcp51Nack             Counter,
            applicationCntAoUcp54Request          Counter,
            applicationCntAoUcp54Ack              Counter,
            applicationCntAoUcp54Nack             Counter,
            applicationCntAoUcp60Request          Counter,
            applicationCntAoUcp60Ack              Counter,
            applicationCntAoUcp60Nack             Counter,
            applicationCntAoUcpOtherRequest       Counter,
            applicationCntAoUcpOtherAck           Counter,
            applicationCntAoUcpOtherNack          Counter,
            applicationCntAtUcp52Request          Counter,
            applicationCntAtUcp52Ack              Counter,
            applicationCntAtUcp52Nack             Counter,
            applicationCntAtUcp53Request          Counter,
            applicationCntAtUcp53Ack              Counter,
            applicationCntAtUcp53Nack             Counter,
            applicationCntAtUcpOtherRequest       Counter,
            applicationCntAtUcpOtherAck           Counter,
            applicationCntAtUcpOtherNack          Counter,
            applicationCntAtUcp01Request          Counter,
            applicationCntAtUcp01Ack              Counter,
            applicationCntAtUcp01Nack             Counter,
            applicationCntAoUcp55Request          Counter,
            applicationCntAoUcp55Ack              Counter,
            applicationCntAoUcp55Nack             Counter,
            applicationCntAoUcp56Request          Counter,
            applicationCntAoUcp56Ack              Counter,
            applicationCntAoUcp56Nack             Counter,
            applicationCntAtUcp57Request          Counter,
            applicationCntAtUcp57Ack              Counter,
            applicationCntAtUcp57Nack             Counter,
            applicationCntAtUcp58Request          Counter,
            applicationCntAtUcp58Ack              Counter,
            applicationCntAtUcp58Nack             Counter,
            applicationCntAoSmppSubmitSmRequest   Counter,
            applicationCntAoSmppSubmitSmAck       Counter,
            applicationCntAoSmppSubmitSmNack      Counter,
            applicationCntAoSmppDataSmRequest     Counter,
            applicationCntAoSmppDataSmAck         Counter,
            applicationCntAoSmppDataSmNack        Counter,
            applicationCntAoSmppBindRxRequest     Counter,
            applicationCntAoSmppBindRxAck         Counter,
            applicationCntAoSmppBindRxNack        Counter,
            applicationCntAoSmppBindTxRequest     Counter,
            applicationCntAoSmppBindTxAck         Counter,
            applicationCntAoSmppBindTxNack        Counter,
            applicationCntAoSmppBindTrxRequest    Counter,
            applicationCntAoSmppBindTrxAck        Counter,
            applicationCntAoSmppBindTrxNack       Counter,
            applicationCntAoSmppUnbindRequest     Counter,
            applicationCntAoSmppUnbindAck         Counter,
            applicationCntAoSmppUnbindNack        Counter,
            applicationCntAoSmppQuerySmRequest    Counter,
            applicationCntAoSmppQuerySmAck        Counter,
            applicationCntAoSmppQuerySmNack       Counter,
            applicationCntAoSmppCancelSmRequest   Counter,
            applicationCntAoSmppCancelSmAck       Counter,
            applicationCntAoSmppCancelSmNack      Counter,
            applicationCntAoSmppReplaceSmRequest  Counter,
            applicationCntAoSmppReplaceSmAck      Counter,
            applicationCntAoSmppReplaceSmNack     Counter,
            applicationCntAoSmppEnquireLinkRequest  Counter,
            applicationCntAoSmppEnquireLinkAck    Counter,
            applicationCntAoSmppEnquireLinkNack   Counter,
            applicationCntAoSmppGenericNack       Counter,
            applicationCntAoSmppOtherRequest      Counter,
            applicationCntAoSmppOtherAck          Counter,
            applicationCntAoSmppOtherNack         Counter,
            applicationCntAtSmppDeliverSmRequest  Counter,
            applicationCntAtSmppDeliverSmAck      Counter,
            applicationCntAtSmppDeliverSmNack     Counter,
            applicationCntAtSmppDataSmRequest     Counter,
            applicationCntAtSmppDataSmAck         Counter,
            applicationCntAtSmppDataSmNack        Counter,
            applicationCntAtSmppGenericNack       Counter,
            applicationCntAtSmppOtherRequest      Counter,
            applicationCntAtSmppOtherAck          Counter,
            applicationCntAtSmppOtherNack         Counter,
            applicationCntAoCimdLoginRequest      Counter,
            applicationCntAoCimdLoginAck          Counter,
            applicationCntAoCimdLoginNack         Counter,
            applicationCntAoCimdLogoutRequest     Counter,
            applicationCntAoCimdLogoutAck         Counter,
            applicationCntAoCimdLogoutNack        Counter,
            applicationCntAoCimdSubmitRequest     Counter,
            applicationCntAoCimdSubmitAck         Counter,
            applicationCntAoCimdSubmitNack        Counter,
            applicationCntAoCimdEnquireRequest    Counter,
            applicationCntAoCimdEnquireAck        Counter,
            applicationCntAoCimdEnquireNack       Counter,
            applicationCntAoCimdOtherRequest      Counter,
            applicationCntAoCimdOtherAck          Counter,
            applicationCntAoCimdOtherNack         Counter,
            applicationCntAtCimdDeliverRequest    Counter,
            applicationCntAtCimdDeliverAck        Counter,
            applicationCntAtCimdDeliverNack       Counter,
            applicationCntAtCimdDeliverStatusRequest    Counter,
            applicationCntAtCimdDeliverStatusAck  Counter,
            applicationCntAtCimdDeliverStatusNack Counter,
            applicationCntAtCimdAliveRequest      Counter,
            applicationCntAtCimdAliveAck          Counter,
            applicationCntAtCimdAliveNack         Counter,
            applicationCntAtCimdOtherRequest      Counter,
            applicationCntAtCimdOtherAck          Counter,
            applicationCntAtCimdOtherNack         Counter,
            applicationOriginatorReplacementEnabled Boolean,
            applicationOriginatorReplacementAddress AddressString,
            applicationAmsQueueForDialoutNotifications AmsQueueIndex,
            applicationTcpKeepAlive                 Boolean,
            applicationOriginatorChargingUnitsValid Boolean,
            applicationRecipientChargingUnitsValid Boolean,
            applicationOriginatorChargingUnits    ChargingUnits,
            applicationRecipientChargingUnits     ChargingUnits,
            applicationAoDelayTime                  DelayTime,
            applicationAoCurrentDelayed             Gauge
        }

    applicationIndex OBJECT-TYPE
        SYNTAX  ApplicationTableIndex
        ACCESS  not-accessible

        STATUS  mandatory
        DESCRIPTION
            "Index of entry in Application table."
        ::= { applicationEntry 1 }

    applicationAdminState OBJECT-TYPE
        SYNTAX  AdminState
        ACCESS  read-write
        STATUS  mandatory
        DESCRIPTION
            "Administrative state of the Application.

            Transition from 'inactive' state to 'active' state is only
            possible when:
            1) short number and name have been supplied;
            2) short number and name are not already in use by another
               Application (already checked when being set);
            3) system ID and address range have been supplied (only applicable
               for SMPP applications);
            4) all required parameters belonging to cli type filled in;
            5) if authentication method involves cli then cli type may not be
               none;
            6) all required parameters belonging to dialout type filled in;
            7) if dialout listen port then dialout type may not be none and
               the listen port may not be in use by another Application or
               outside listener;
            8) if a serviceClass list is specified then the serviceClass(es)
               needs to be configured and has to exist;
            9) if a session model 'insideOnlyScList' or 'insideOnlyAllScs' is
               configured, at least one serviceClass needs to be configured
               in the serviceClass list;
            10) appl Group configured needs to be configured and has to exist.
            11) if a serviceCentre list is specified then the session model
                has to be an *ScList type.
            12) If CLI authentication is enabled and cli type is 'list' 
                then specified CLI source address list must exists 
                and be activated.
            13) If CLI authentication is used without a ORed password 
                then the configured CLI addresses should not be used 
                by other active CLI applications.
            14) If CLI authentication is used with ORed password 
                then configured CLI addresses should not be used 
                by other active CLI applications without ORed password.

            Transition from 'active' state to 'inactive' state is always
            possible but will result in:
            1) The router will not match rules referring to 'inactive'
               applications; Open sessions from the Application towards the
               router will be closed.
            2) The hub will graceful shutdown all open sessions towards and
               from this Application.

            Transition from to 'destroy' is only possible if:
            1) none of the 'active' rule records is referring to the
               Application with a condition of type APPLICATION.

            For details, refer to the comment on the AdminState type."
        ::= { applicationEntry 2 }

    applicationName OBJECT-TYPE
        SYNTAX  NameString
        ACCESS  read-write
        STATUS  mandatory
        DESCRIPTION
            "Name of Application. The name has to be unique when it is set."
        ::= { applicationEntry 3 }

    applicationShortNumber OBJECT-TYPE
        SYNTAX  E164Address
        ACCESS  read-write
        STATUS  mandatory
        DESCRIPTION
            "Short number assigned to Application. Normally consisting of four
            digits. The maximum number of digits is defined by
            smsPropMaxLengthForShortNumber.
            Can only be changed if the adminState is inactive.
            The short number has to be unique when it is set."
        ::= { applicationEntry 4 }

    applicationType OBJECT-TYPE
        SYNTAX  ApplicationType
        ACCESS  read-write
        STATUS  mandatory
        DESCRIPTION
            "Interface type describing how TextPass interacts with the
            Application.
            Can only be changed if the adminState is inactive.
            For details, refer to the comment on the ApplicationType type."
        ::= { applicationEntry 5 }

    applicationSessionModel OBJECT-TYPE
        SYNTAX  SessionModel
        ACCESS  read-write
        STATUS  mandatory
        DESCRIPTION
            "Session Model describing how the sessions of the Application
            should be handled. If set to something different then
            'useServiceClassModel' then this setting will overule the
            configured setting of the associated Service Class.
            For details, refer to the comment on the SessionModel type.
            Default is 'useServiceClassModel'."
        ::= { applicationEntry 6 }

    applicationNrSmscOnlySessions OBJECT-TYPE
        SYNTAX  NrSmscOnlySessions
        ACCESS  read-write
        STATUS  mandatory
        DESCRIPTION
            "The number of sessions which are setup per HUB towards each
            SMSC in case the SessionModel is InsideOnlyAllScs,
            InsideOnlyScList, PermDialoutAllScs or PermDialoutScList.
            Default is 1."
        ::= { applicationEntry 7 }

    applicationLogLevel OBJECT-TYPE
        SYNTAX  LogLevel
        ACCESS  read-write
        STATUS  mandatory
        DESCRIPTION
            "Defines the loglevel for this specific Application.
            When an event occurs for this Application then it is logged if
            the level of the event is higher or equal to the configured one.
            Message are logged to the system log. 
            See also genPropAppLogEventCount and genPropAppLogEventInterval
            for more information.
            The default value is 'warning'. Application event logging can be
            disabled by setting this property to 'off'."
        ::= { applicationEntry 8 }

    applicationApplicationGroupIndex OBJECT-TYPE    
        SYNTAX  ApplicationGroupTableIndex
        ACCESS  read-write
        STATUS  mandatory
        DESCRIPTION
            "Index of entry in table containing Application Groups. This
            index identifies one specific Application Group. An Application
            Group needs to be configured."
        ::= { applicationEntry 9 }

    applicationApplicationCategoryBits OBJECT-TYPE
        SYNTAX  ApplicationCategoryBitString
        ACCESS  read-write
        STATUS  mandatory
        DESCRIPTION
            "Bit string containing a bit for each Application Category. Each
            bit which is set to 1 associates that Application Category to the
            Application.

            For details, refer to the comment on the
            ApplicationCategoryBitString type."
        ::= { applicationEntry 10 }

    applicationThroughputAoMaximum OBJECT-TYPE
        SYNTAX  Throughput
        ACCESS  read-write
        STATUS  mandatory
        DESCRIPTION
            "Maximum throughput from the Application towards the TP system
            in terms of SM's per second."
        ::= { applicationEntry 11 }

    applicationThroughputAtMaximum OBJECT-TYPE
        SYNTAX  Throughput
        ACCESS  read-write
        STATUS  mandatory
        DESCRIPTION
            "Maximum throughput from the TP system towards the Application
            in terms of SM's per second."
        ::= { applicationEntry 12 }

    applicationThroughputAoCommitted OBJECT-TYPE
        SYNTAX  Throughput
        ACCESS  read-write
        STATUS  mandatory
        DESCRIPTION
            "Committed throughput from the Application towards the TP system
            in terms of SM's per second."
        ::= { applicationEntry 13 }

    applicationThroughputAtCommitted OBJECT-TYPE
        SYNTAX  Throughput
        ACCESS  read-write
        STATUS  mandatory
        DESCRIPTION
            "Committed throughput from the TP system towards the Application
            in terms of SM's per second."
        ::= { applicationEntry 14 }

    applicationPreferredCharacterSet OBJECT-TYPE
        SYNTAX  CharSet
        ACCESS  read-write
        STATUS  mandatory
        DESCRIPTION
            "Preferred character set for the SM's that are sent towards the
            Application."
        ::= { applicationEntry 15 }

    applicationOperationalState OBJECT-TYPE
        SYNTAX  OperationalState
        ACCESS  read-only
        STATUS  mandatory
        DESCRIPTION
            "The operational state of the Application entity."
        ::= { applicationEntry 16 }

    applicationForwardErrorMapIndex OBJECT-TYPE
        SYNTAX  ErrorMapIndex
        ACCESS  read-write
        STATUS  mandatory
        DESCRIPTION
            "Index of the forward error mapping table to be used."
        ::= { applicationEntry 17 }

    applicationReverseErrorMapIndex OBJECT-TYPE
        SYNTAX  ErrorMapIndex
        ACCESS  read-write
        STATUS  mandatory
        DESCRIPTION
            "Index of the reverse error mapping table to be used."
        ::= { applicationEntry 18 }

    applicationFcdrRecipAddressPidForAt OBJECT-TYPE
        SYNTAX  FcdrAddressPid
        ACCESS  read-write
        STATUS  mandatory
        DESCRIPTION
            "Specifier for the value of the following fields:
            - RecipAddress->Pid field of FCDR's CallDetailRecord
            - orglRecipAddress->Pid field of FCDR's NotificationRecord
            Only applicable when the CDR pertains to a message that is
            delivered to the Application (i.e. only for AT messages).
            Default value is -1, which implies that the PID value in the 
            CDR depends on the Application protocol."
        ::= { applicationEntry 19 }

    applicationFcdrOrigAddressPidForAo OBJECT-TYPE
        SYNTAX  FcdrAddressPid
        ACCESS  read-write
        STATUS  mandatory
        DESCRIPTION
            "Specifier for the value of the following fields:
            - OrigAddress->Pid field of FCDR's CallDetailRecord
            - NotifAddress->Pid field of FCDR's CallDetailRecord
            - orglOrigAddress->Pid field of FCDR's NotificationRecord
            - orglNotifAddress->Pid field of FCDR's CallDetailRecord
            Only applicable when the CDR pertains to a message that is
            submitted by the Application (i.e. only for AO messages).
            Default value is -1, which implies that the PID value in the 
            CDR depends on the Application protocol."
        ::= { applicationEntry 20 }

    applicationOutsideAuthenticationMethod OBJECT-TYPE
        SYNTAX  OutsideAuthenticationMethod
        ACCESS  read-write
        STATUS  mandatory
        DESCRIPTION
            "The authentication method to be used by this Application.
            Possible settings are:
             - Password authentication
             - CLI authentication
            When both are selected, both need to match (AND). Select
            the OR box to use password OR CLI authentication.
            #For details, refer to the comment on the
            OutsideAuthenticationMethod type.#"
        ::= { applicationEntry 21 }

    applicationOutsideCliType OBJECT-TYPE
        SYNTAX  CliType
        ACCESS  read-write
        STATUS  mandatory
        DESCRIPTION
            "The type of cli identification which should be used by this
            Application. Only applicable if cli authentication is enabled
            by the authentication method.
            For details, refer to the comment on the CliType type."
        ::= { applicationEntry 22 }

    applicationOutsideCliIpAddress OBJECT-TYPE
        SYNTAX  IpAddress
        ACCESS  read-write
        STATUS  mandatory
        DESCRIPTION
            "The IP Address used in case the CliType is set to IP."
        ::= { applicationEntry 23 }

    applicationOutsideCliTcpPort OBJECT-TYPE
        SYNTAX  TcpPort
        ACCESS  read-write
        STATUS  mandatory
        DESCRIPTION
            "The TCP Port used in case the CliType is set to IP.
            May be set to zero to accept any port."
        ::= { applicationEntry 24 }

    applicationOutsideCliX121Address OBJECT-TYPE
        SYNTAX  X121Address
        ACCESS  read-write
        STATUS  mandatory
        DESCRIPTION
            "The X121 Address used in case the CliType is set to X25."
        ::= { applicationEntry 25 }

    applicationOutsideCliGprsMsisdn OBJECT-TYPE
        SYNTAX  E164Address
        ACCESS  read-write
        STATUS  mandatory
        DESCRIPTION
            "The GPRS MSISDN Address used in case the CliType is set to GPRS."
        ::= { applicationEntry 26 }

    applicationOutsideDialoutType OBJECT-TYPE
        SYNTAX  DialoutType
        ACCESS  read-write
        STATUS  mandatory
        DESCRIPTION
            "The type of dialout connection which should be used in case a
            dialout request is received on the dialout listen port or
            permanent dialout.
            For details, refer to the comment on the DialoutType type."
        ::= { applicationEntry 27 }

    applicationOutsideDialoutIpAddress OBJECT-TYPE
        SYNTAX  IpAddress
        ACCESS  read-write
        STATUS  mandatory
        DESCRIPTION
            "The IP Address to be used for the dialout connection in case
            the DialoutType is set to IP."
        ::= { applicationEntry 28 }

    applicationOutsideDialoutTcpPort OBJECT-TYPE
        SYNTAX  TcpPort
        ACCESS  read-write
        STATUS  mandatory
        DESCRIPTION
            "The TCP Port to be used for the dialout connection in case
            the DialoutType is set to IP."
        ::= { applicationEntry 29 }

    applicationOutsideDialoutX121Address OBJECT-TYPE
        SYNTAX  X121Address
        ACCESS  read-write
        STATUS  mandatory
        DESCRIPTION
            "The X121 Address to be used for the dialout connection in case
            the DialoutTYpe is set to X25."
        ::= { applicationEntry 30 }

    applicationOutsideMaxInactivityTime OBJECT-TYPE
        SYNTAX  ApplicationTimer
        ACCESS  read-write
        STATUS  mandatory
        DESCRIPTION
            "Maximum time span, expressed in seconds, that a link to an
            Application is idle before TextPass disconnects it.
            The default is 60 seconds."
        ::= { applicationEntry 31 }

    applicationOutsideMaxResponseTime OBJECT-TYPE
        SYNTAX  ApplicationTimer
        ACCESS  read-write
        STATUS  mandatory
        DESCRIPTION
            "Maximum time span, expressed in seconds, that TextPass waits for
            a response from an Application before it considers the relating
            request as timed out. The default is 5 seconds."
        ::= { applicationEntry 32 }

    applicationOutsideDialoutInactivityTime OBJECT-TYPE
        SYNTAX  ApplicationTimer
        ACCESS  read-write
        STATUS  mandatory
        DESCRIPTION
            "Maximum time span, expressed in seconds, that a outside dial-out
            link to an Application is idle before TextPass disconnects it.
            The default is 60 seconds."
        ::= { applicationEntry 33 }

    applicationOutsideDialoutMaxSessions OBJECT-TYPE
        SYNTAX  DialoutSessions
        ACCESS  read-write
        STATUS  mandatory
        DESCRIPTION
            "Maximum number of dialout sessions between TextPass and the
            Application. Only applicable if TextPass and the Application
            interface through dialout sessions."
        ::= { applicationEntry 34 }

    applicationOutsideCliIpMask OBJECT-TYPE
        SYNTAX  IpAddress
        ACCESS  read-write
        STATUS  mandatory
        DESCRIPTION
            "The IP mask used for matching the IP address in case the
            CliType is set to IP.
            Default is '255.255.255.255', to provide an exact match."
        ::= { applicationEntry 35 }

        
    applicationInsideDialoutListenPort OBJECT-TYPE
        SYNTAX  TcpPort
        ACCESS  read-write
        STATUS  mandatory
        DESCRIPTION
            "The listen port for an dialout Application. Any connection setup
            (by the SMSC) towards this port will result in a dialout session.
            The OutsideDialoutType and corresponding address information has
            to be configured as wel."
        ::= { applicationEntry 36 }

    applicationInsideDialoutMaxSessions OBJECT-TYPE
        SYNTAX  DialoutSessions
        ACCESS  read-write
        STATUS  mandatory
        DESCRIPTION
            "Maximum number of dialout sessions between SMSC and the
            TextPass. Only applicable if TextPass and the Application
            interface through dialout sessions."
        ::= { applicationEntry 37 }

    applicationInsideAuthenticationMethod OBJECT-TYPE
        SYNTAX  InsideAuthenticationMethod
        ACCESS  read-write
        STATUS  mandatory
        DESCRIPTION
            "The authentication method to be used by the Service Centre.  For
            details, refer to the comment on the InsideAuthenticationMethod
            type."
        ::= { applicationEntry 38 }

    applicationInsideOnlySmppBindVersion OBJECT-TYPE
        SYNTAX  SmppBindVersion
        ACCESS  read-write
        STATUS  mandatory
        DESCRIPTION
            "The definition of the bind behavior for SMPP insideOnly sessions.
            Using version smpp33 will have the effect that both receiver and
            transmitter sessions are setup for insideOnly sessions. Using 
            version smpp34 will setup transceiver sessions. The default
            value is smpp34."
        ::= { applicationEntry 39 }

    applicationInsideOnlySmppBindType OBJECT-TYPE
        SYNTAX  SmppBindType
        ACCESS  read-write
        STATUS  mandatory
        DESCRIPTION
            "Defines whether a transceiver session or separate receiver and
            transmitter sessions are set up, for SMPP v3.4 insideOnly
            sessions.
            Only applies to insideOnly sessionModel and only for SMPP v3.4
            Applications.
            Default is 'bindTrx'."
        ::= { applicationEntry 40 }

    applicationSmppSystemId OBJECT-TYPE
        SYNTAX  SmppSystemId
        ACCESS  read-write
        STATUS  mandatory
        DESCRIPTION
            "System ID of the Application. Only applicable if TextPass and the
            Application interface through SMPP."
        ::= { applicationEntry 41 }

    applicationSmppSystemType OBJECT-TYPE
        SYNTAX  SmppSystemType
        ACCESS  read-write
        STATUS  mandatory
        DESCRIPTION
            "System type of the Application. Only applicable if TextPass and
            the Application interface through SMPP."
        ::= { applicationEntry 42 }

    applicationOutsideSmppPassword OBJECT-TYPE
        SYNTAX  SmppOutsidePassword
        ACCESS  read-write
        STATUS  mandatory
        DESCRIPTION
            "Password of the Application. Only applicable if TextPass and the
            Application interface through SMPP. If a zero-length string is
            supplied, TextPass does not authenticate the Application when a
            link is being established."
        ::= { applicationEntry 43 }

    applicationOutsideSmppAddressRange OBJECT-TYPE
        SYNTAX  E164AddressRange
        ACCESS  read-write
        STATUS  mandatory
        DESCRIPTION
            "Address range that the Application may use for the originator in
            the SM's towards the mobile network. Only applicable if TextPass
            and the Application interface through SMPP."
        ::= { applicationEntry 44 }


    applicationOutsideSmppAddressRangeTon OBJECT-TYPE
        SYNTAX  TypeOfNumber
        ACCESS  read-write
        STATUS  mandatory
        DESCRIPTION
            "Type-of-number of the address range that the Application may use
            for the originator in the SM's towards the mobile network. Only
            applicable if TextPass and the Application interface through
            SMPP."
        ::= { applicationEntry 45 }

    applicationOutsideSmppAddressRangeNpi OBJECT-TYPE
        SYNTAX  NumberingPlanIdentification
        ACCESS  read-write
        STATUS  mandatory
        DESCRIPTION
            "Numbering-plan-identification of the address range that the
            Application may use for the originator in the SM's towards the
            mobile network. Only applicable if TextPass and the Application
            interface through SMPP."
        ::= { applicationEntry 46 }

    applicationOutsideSmppWindowSize OBJECT-TYPE
        SYNTAX  SmppWindowSize
        ACCESS  read-write
        STATUS  mandatory
        DESCRIPTION
            "Window size used on the links between TextPass and the
            Application.  Only applicable if TextPass and the Application
            interface through SMPP. The default is 255."
        ::= { applicationEntry 47 }

    applicationOutsideSmppMaxReceivers OBJECT-TYPE
        SYNTAX  SmppConnections
        ACCESS  read-write
        STATUS  mandatory
        DESCRIPTION
            "Maximum number of receiver links between TextPass and the
            Application. Only applicable if TextPass and the Application
            interface through SMPP. The default is 255."
        ::= { applicationEntry 48 }

    applicationOutsideSmppMaxTransmitters OBJECT-TYPE
        SYNTAX  SmppConnections
        ACCESS  read-write
        STATUS  mandatory
        DESCRIPTION
            "Maximum number of transmitter links between TextPass and the
            Application. Only applicable if TextPass and the Application
            interface through SMPP. The default is 255."
        ::= { applicationEntry 49 }

    applicationOutsideSmppMaxTransceivers OBJECT-TYPE
        SYNTAX  SmppConnections
        ACCESS  read-write
        STATUS  mandatory
        DESCRIPTION
            "Maximum number of transceiver links between TextPass and the
            Application. Only applicable if TextPass and the Application
            interface through SMPP. The default is 255."
        ::= { applicationEntry 50 }

    applicationOutsideDialoutSmppWindowSize OBJECT-TYPE
        SYNTAX  SmppWindowSize
        ACCESS  read-write
        STATUS  mandatory
        DESCRIPTION
            "Window size used on the links between TextPass and the
            Application.  Only applicable if TextPass and the Application
            interface through dialout sessions and they interface through
            SMPP. The default is 1."
        ::= { applicationEntry 51 }

    applicationOutsideDialoutSmppPassword OBJECT-TYPE
        SYNTAX  SmppInsidePassword
        ACCESS  read-write
        STATUS  mandatory
        DESCRIPTION
            "Password of the Application used for the outside dialout sessions 
             towards the dialout applications. Only applicable if TextPass 
             and the Application interface through SMPP and dialout
             is allowed."
        ::= { applicationEntry 52 }

    applicationOutsideCliListIndex OBJECT-TYPE
        SYNTAX  CliSourceAddressListIndex
        ACCESS  read-write
        STATUS  mandatory
        DESCRIPTION
            "Specifies the index of the CliSourceAddressListTable 
             (CLI source address list table). This index is used when 
             the CliType is set to 'list' and CLI athentication is enabled. 
             The used index must refer to an existing and active 
             CLI source address list. The CliSourceAddressListTable and 
             related CliSourceAddressesTable are defined in the 
             testpass-hub-mib.my."
        ::= { applicationEntry 53 }
            
    applicationInsideSmppPassword OBJECT-TYPE
        SYNTAX  SmppInsidePassword
        ACCESS  read-write
        STATUS  mandatory
        DESCRIPTION
            "Password of the Application used for the sessions towards the
            Service Centres. Only applicable if TextPass and the service
            centres interface through SMPP."
        ::= { applicationEntry 56 }

    applicationInsideSmppWindowSize OBJECT-TYPE
        SYNTAX  SmppWindowSize
        ACCESS  read-write
        STATUS  mandatory
        DESCRIPTION
            "Window size used on the links between TextPass and the service
            centres.  Only applicable if TextPass and the Service Centres
            interface through SMPP. The default is 255."
        ::= { applicationEntry 57 }

    
    applicationOutsideUcpPassword OBJECT-TYPE
        SYNTAX  UcpOutsidePassword
        ACCESS  read-write
        STATUS  mandatory
        DESCRIPTION
            "Password of the Application. Only applicable if TextPass and the
            Application interface through UCP.  If a zero-length string is
            supplied, TextPass does not authenticate the Application when a
            session is being established."
        ::= { applicationEntry 61 }

    applicationOutsideUcpWindowSize OBJECT-TYPE
        SYNTAX  UcpWindowSize
        ACCESS  read-write
        STATUS  mandatory
        DESCRIPTION
            "Window size used on the links between TextPass and the
            Application.  Only applicable if TextPass and the Application
            interface through UCP. The default is 100."
        ::= { applicationEntry 62 }

    applicationOutsideUcpMaxSessions OBJECT-TYPE
        SYNTAX  UcpConnections
        ACCESS  read-write
        STATUS  mandatory
        DESCRIPTION
            "Maximum number of links between TextPass and the
            Application. Only applicable if TextPass and the Application
            interface through UCP. The default is 255."
        ::= { applicationEntry 63 }

    applicationOutsideDialoutUcpWindowSize OBJECT-TYPE
        SYNTAX  UcpWindowSize
        ACCESS  read-write
        STATUS  mandatory
        DESCRIPTION
            "Window size used on the links between TextPass and the
            Application.  Only applicable if TextPass and the Application
            interface through dialout sessions and they interface through
            UCP. The default is 1."
        ::= { applicationEntry 64 }

    applicationInsideUcpPassword OBJECT-TYPE
        SYNTAX  UcpInsidePassword
        ACCESS  read-write
        STATUS  mandatory
        DESCRIPTION
            "Password of the Application used for the sessions towards the
            Service Centres. Only applicable if TextPass and the service
            centres interface through UCP."
        ::= { applicationEntry 66 }

    applicationInsideUcpWindowSize OBJECT-TYPE
        SYNTAX  UcpWindowSize
        ACCESS  read-write
        STATUS  mandatory
        DESCRIPTION
            "Window size used on the links between TextPass and the service
            centres.  Only applicable if TextPass and the Service Centres
            interface through UCP. The default is 100."
        ::= { applicationEntry 67 }

    applicationOutsideCimdUserIdentity OBJECT-TYPE
        SYNTAX  CimdUserIdentity
        ACCESS  read-write
        STATUS  mandatory
        DESCRIPTION
            "User identity of the Application. Only applicable if TextPass
            and the Application interface through CIMD."
        ::= { applicationEntry 71 }

    applicationOutsideCimdPassword OBJECT-TYPE
        SYNTAX  CimdOutsidePassword
        ACCESS  read-write
        STATUS  mandatory
        DESCRIPTION
            "Password of the Application. Only applicable if TextPass and the
            Application interface through CIMD. If a zero-length string is
            supplied, TextPass does not authenticate the Application when a
            link is being established."
        ::= { applicationEntry 72 }

    applicationOutsideCimdWindowSize OBJECT-TYPE
        SYNTAX  CimdWindowSize
        ACCESS  read-write
        STATUS  mandatory
        DESCRIPTION
            "Window size used on the links between TextPass and the
            Application.  Only applicable if TextPass and the Application
            interface through CIMD. The default is 128."
        ::= { applicationEntry 73 }

    applicationOutsideCimdMaxSessions OBJECT-TYPE
        SYNTAX  CimdConnections
        ACCESS  read-write
        STATUS  mandatory
        DESCRIPTION
            "Maximum number of links between TextPass and the
            Application. Only applicable if TextPass and the Application
            interface through CIMD. The default is 255."
        ::= { applicationEntry 74 }

    applicationOutsideCimdTariffClass OBJECT-TYPE
        SYNTAX  CimdTariffClassMask
        ACCESS  read-write
        STATUS  mandatory
        DESCRIPTION
            "Bit string indicating which tariff classes an Application is
            allowed to use. Only applicable if TextPass and the Application
            interface through CIMD."
        ::= { applicationEntry 75 }

    applicationOutsideCimdServiceDescription OBJECT-TYPE
        SYNTAX  CimdServiceDescriptionMask
        ACCESS  read-write
        STATUS  mandatory
        DESCRIPTION
            "Bit string indicating which service descriptions an Application
            is allowed to use. Only applicable if TextPass and the
            Application interface through CIMD."
        ::= { applicationEntry 76 }

    applicationOutsideCimdPriority OBJECT-TYPE
        SYNTAX  CimdPriority
        ACCESS  read-write
        STATUS  mandatory
        DESCRIPTION
            "Bit string indicating which priorities an Application is allowed
            to use. Only applicable if TextPass and the Application interface
            through CIMD."
        ::= { applicationEntry 77 }

    applicationOutsideDialoutCimdWindowSize OBJECT-TYPE
        SYNTAX  CimdWindowSize
        ACCESS  read-write
        STATUS  mandatory
        DESCRIPTION
            "Window size used on the links between TextPass and the
            Application.  Only applicable if TextPass and the Application
            interface through dialout sessions and if they interface through
            Cimd. The default is 1."
        ::= { applicationEntry 78 }

    applicationInsideCimdPassword OBJECT-TYPE
        SYNTAX  CimdInsidePassword
        ACCESS  read-write
        STATUS  mandatory
        DESCRIPTION
            "Password of the Application used for the sessions towards the
            Service Centres. Only applicable if TextPass and the service
            centres interface through CIMD."
        ::= { applicationEntry 81 }

    applicationInsideCimdWindowSize OBJECT-TYPE
        SYNTAX  CimdWindowSize
        ACCESS  read-write
        STATUS  mandatory
        DESCRIPTION
            "Window size used on the links between TextPass and the service
            centres.  Only applicable if TextPass and the Service Centres
            interface through CIMD."
        ::= { applicationEntry 82 }


    applicationOutsideMinimumSessionsThreshold OBJECT-TYPE
        SYNTAX  Percentage
        ACCESS  read-write
        STATUS  mandatory
        DESCRIPTION
            "This percentage specifies the minimum number of outside sessions;
             an alarm is set (SNMP trap) when the number of outside sessions
             drops below this level. The OutsideMinimumSessionsThreshold 
             is set as a percentage of the maximum number of outside sessions. 
             This maximum number of outside sessions is configurable 
             per protocol, which means that when the maximum number of outside
             sessions (e.g. applicationOutsideUcpMaxSessions) is 
             set at 50 and the OutsideMinimumSessionsThreshold percentage is
             set to 10 the absolute minimum number of outside session will
             be 5. When the number of outside sessions drops below this value
             an alarm is set by means of a SNMP trap. When the number of 
             outside sessions is no longer below this minimum the 
             pending alarm Will be cleared by means of a SNMP trap. 
             The HUB shall use different traps for every available 
             session type (InsideUcp, OutSideCimd, etc).
             The following traps are related to this threshold setting:
             -UCP:
                applicationOutsideUcpMinimumSessionsNotReached
                applicationOutsideUcpMinimumSessionsReached
             -CIMD
                applicationOutsideCimdMinimumSessionsNotReached
                applicationOutsideCimdMinimumSessionsReached
             -SMPP, separated traps for RX, TX and TRX session
                applicationOutsideSmppRxMinimumSessionsNotReached
                applicationOutsideSmppRxMinimumSessionsReached
                applicationOutsideSmppTxMinimumSessionsNotReached
                applicationOutsideSmppTxMinimumSessionsReached
                applicationOutsideSmppTrxMinimumSessionsNotReached
                applicationOutsideSmppTrxMinimumSessionsReached
             This mechanism can be disabled by setting the 
             OutsideMinimumSessionsThreshold percentage to 0.  
             The MinimumSessionsThreshold can be changed when the
             Application admin state is INACTIVE or ACTIVE.
             The default value for MinimumSessionsThreshold is 0,
             which means that no minimum number of outside 
             sessions trap are sent."
        ::= { applicationEntry 83 }


    applicationInsideMinimumSessionsThreshold OBJECT-TYPE
        SYNTAX  Percentage
        ACCESS  read-write
        STATUS  mandatory
        DESCRIPTION
            "This percentage specifies the minimum number of inside sessions;
             an alarm is set (SNMP trap) when the number of inside sessions
             drops below this level. The MinimumSessionsThreshold is set as
             a percentage of the maximum number of inside session. The 
             property applicationNrSmscOnlySessions is used to determine
             the maximum number of inside sessions.
             This means that when the maximum number of inside sessions
             (applicationNrSmscOnlySessions) is set at 50 
             and the InsideMinimumSessionsThreshold percentage is set
             to 10 the absolute minimum number of inside session will be 5.
             When the number of inside session drops below this value an
             alarm is set by means of a SNMP trap. When the number of
             inside sessions is no longer below this minimum value this
             alarm is cleared by means of a SNMP trap. The HUB shall use
             different traps for every available session type 
             (InsideUcp, OutSideCimd, etc).
             -UCP-:
                applicationInsideUcpMinimumSessionsNotReached
                applicationInsideUcpMinimumSessionsReached
             -CIMD-:
                applicationInsideCimdMinimumSessionsNotReached
                applicationInsideCimdMinimumSessionsReached
             -SMPP-, separated traps for RX, TX and TRX session
                applicationInsideSmppRxMinimumSessionsNotReached
                applicationInsideSmppRxMinimumSessionsReached
                applicationInsideSmppTxMinimumSessionsNotReached
                applicationInsideSmppTxMinimumSessionsReached
                applicationInsideSmppTrxMinimumSessionsNotReached
                applicationInsideSmppTrxMinimumSessionsReached
             This mechanism can be disabled by setting the 
             InsideMinimumSessionsThreshold percentage to 0. 
             This property can be changed when the Application 
             admin state is INACTIVE or ACTIVE. The default value for 
             InsideMinimumSessionsThreshold is 0, which means that
             no minimum number of inside sessions alarm traps are sent."

        ::= { applicationEntry 84 }

    applicationOutsideLifeCheckInterval OBJECT-TYPE
        SYNTAX  IntervalTime
        ACCESS  read-write
        STATUS  mandatory
        DESCRIPTION
            "This value specifies the time interval of life check 
             messages send to the application. The outside life check 
             functionality is only supported for the SMPP protocol, 
             implemented with the enquire_link PDU. The outside life check 
             functionality can be disabled by setting the 
             applicationOutsideLifeCheckInterval at 0. Setting the value of 
             the applicationOutsideLifeCheckInterval greater than the 
             OutsideMaxInactivityTime - OutsideMaxResponseTime, 
             will result in the HUB using the internally the 
             OutsideMaxInactivityTime - OutsideMaxResponseTime as
             life check interval. In this case when 
             OutsideMaxInactivityTime - OutsideMaxResponseTime is negative 
             or zero, a life check interval equal to the 
             OutsideMaxInactivityTime is used. 
             Default value for applicationOutsideLifeCheckInterval is 0."
        ::= { applicationEntry 85 }

    applicationCharacterSet OBJECT-TYPE
        SYNTAX  CustomCharacterSet
        ACCESS  read-write
        STATUS  mandatory
        DESCRIPTION
            "Specifies which custom character set is used. 
             Default is 0 (No custom character set used)."
        ::= { applicationEntry 86 }

    
    applicationFormatOriginator OBJECT-TYPE
        SYNTAX  ApplicationAddressFormat
        ACCESS  read-write
        STATUS  mandatory
        DESCRIPTION
            "Indicator specifying how the originator should be specified in
            an AO/SM or AT/SM that results from an MO/SM. When the value is
            equal to 'asSystemWideSetting', the format as specified by
            smsPropFormatAtOriginator is taken. Default is
            'asSystemWideSetting'."
        ::= { applicationEntry 88 }

    applicationFormatRecipient OBJECT-TYPE
        SYNTAX  ApplicationAddressFormat
        ACCESS  read-write
        STATUS  mandatory
        DESCRIPTION
            "Indicator specifying how the recipient should be specified in an
            AO/SM or AT/SM that results from an MO/SM. When the value is
            equal to 'asSystemWideSetting', the format as specified by
            smsPropFormatAtRecipient is taken. Default is
            'asSystemWideSetting'."
        ::= { applicationEntry 89 }

    applicationFormatMsc OBJECT-TYPE
        SYNTAX  ApplicationAddressFormat
        ACCESS  read-write
        STATUS  mandatory
        DESCRIPTION
            "Indicator specifying how the MSC should be specified in an AO/SM
            or AT/SM that results from an MO/SM. When the value is equal to
            'asSystemWideSetting', the format as specified by
            smsPropFormatAtMsc is taken. Default is 'asSystemWideSetting'."
        ::= { applicationEntry 90 }

    applicationFormatSmsc OBJECT-TYPE
        SYNTAX  ApplicationAddressFormat
        ACCESS  read-write
        STATUS  mandatory
        DESCRIPTION
            "Indicator specifying how the SMSC should be specified in an
            AO/SM or AT/SM that results from an MO/SM. When the value is
            equal to 'asSystemWideSetting', the format as specified by
            smsPropFormatAtSmsc is taken. Default is 'asSystemWideSetting'."
        ::= { applicationEntry 91 }

    applicationAliasingMode OBJECT-TYPE
        SYNTAX  AliasingMode
        ACCESS  read-write
        STATUS  mandatory
        DESCRIPTION
            "The aliasing mode to be used by this Application.

            For details, refer to the comment on the AliasingMode type."
        ::= { applicationEntry 92 }

    applicationConsolidationField OBJECT-TYPE
        SYNTAX  ConsolidationString
        ACCESS  read-write
        STATUS  mandatory
        DESCRIPTION
            "The value to be used in the ConsolidationField in the CDRs.
            The range of sensible values depends on the desired CDR format.
            By default, this field is set to the empty string ''."
        ::= { applicationEntry 93 }

    applicationAllowNotification OBJECT-TYPE
        SYNTAX  Boolean
        ACCESS  read-write
        STATUS  mandatory
        DESCRIPTION
            "Flag indicating whether or not delivery notifications are allowed
            for AO-MT (if requested). The message will be rejected if the 
            Application request a notification when it is not allowed."
        ::= { applicationEntry 94 }

    applicationNotificationAddressMode OBJECT-TYPE
        SYNTAX  NotificationAddressMode
        ACCESS  read-write
        STATUS  mandatory
        DESCRIPTION
            "The notification address mode to be used by this Application in
            case a notification is requested.

            For details, refer to the comment on the NotificationAddressMode
            type."
        ::= { applicationEntry 95 }

    applicationOptimisedMtDelivery OBJECT-TYPE
        SYNTAX  Boolean
        ACCESS  read-write
        STATUS  mandatory
        DESCRIPTION
            "Flag indicating whether or not HLR indications (AbsentSubscriber
            / MemoryCapacityExceeded) should be considered when performing a
            AO-MT delivery attempt."
        ::= { applicationEntry 96 }

    applicationAoEnabled OBJECT-TYPE
        SYNTAX  Boolean
        ACCESS  read-write
        STATUS  mandatory
        DESCRIPTION
            "Flag indicating whether or not AO traffic is enabled for this
            Application. The default is TRUE."
        ::= { applicationEntry 97 }

    applicationAtEnabled OBJECT-TYPE
        SYNTAX  Boolean
        ACCESS  read-write
        STATUS  mandatory
        DESCRIPTION
            "Flag indicating whether or not AT traffic is enabled for this
            Application. The default is TRUE."
        ::= { applicationEntry 98 }

    applicationRespondAfterDelivery OBJECT-TYPE
        SYNTAX  Boolean
        ACCESS  read-write
        STATUS  mandatory
        DESCRIPTION
            "Flag indicating when TextPass generates a response of an AO/SM.
            If the flag is set, TextPass generates a response after delivery
            of the AO/SM to the MS. The response then reflects the delivery
            result: An ACK indicates successful delivery, whilst a NAK with
            error code 'subscriber hang-up' for UCP or error code 'delivery
            failure' for SMPP indicates that delivery of the AO/SM towards
            the MS failed. A NAK with another error code implies that the SM
            is rejected in the validation phase (eg. due to invalid syntax,
            license violation, etc.).
            If the flag is not set, which is the default, the response will be
            generated after the validation phase, but before TextPass starts
            the delivery of the AO/SM towards the MS."
        ::= { applicationEntry 99 }

    applicationRoutingPathAoMtEnabled OBJECT-TYPE
        SYNTAX  Boolean
        ACCESS  read-write
        STATUS  mandatory
        DESCRIPTION
            "Flag indicating whether or not this Application can send
            AO-MT SMs (singleShot delivery attempts)."
        ::= { applicationEntry 100 }


    applicationRoutingPathAoMtAoEnabled OBJECT-TYPE
        SYNTAX  Boolean
        ACCESS  read-write
        STATUS  mandatory
        DESCRIPTION
            "Flag indicating whether or not this Application can send
            AO-MT-AO SMs (first delivery attempt by TextPass, fallback
            to SMSC). If this flag is set, the TextPass always generates
            a response after delivery of the AO/SM, regardless of the
            setting of the Respond-After-Delivery attribute."
        ::= { applicationEntry 101 }

    applicationGsmStatusReportInitiatedByApplication OBJECT-TYPE
        SYNTAX  Boolean
        ACCESS  read-write
        STATUS  mandatory
        DESCRIPTION
            "Flag indicating whether or not the Application itself is
            responsible for generating GSM status reports for MO/SM's
            that are routed to the Application. Normally, TextPass will
            generate GSM status reports as soon as the Application sends
            a response to ACK/NAK a previously delivered MO/AT SM. When
            this flag is set, the TextPass won't do this. It is then up
            to the Application to initiate GSM status reports. This is
            useful when the Application is not the temination-point of
            the Application, but just an intermediate point with a
            store-and-forward functionality. When this flag is set,
            information required to generate a GSM status report is
            passed to the Application using proprietary extensions on
            the Application protocol. Initiating a GSM status report by
            an Application is also implemented by proprietary extensions
            on the Application protocol.
            At this point, the proprietary extensions have only been
            defined and implemented for SMPP. Attempts to set this flag
            for a UCP or CIMD Application are rejected."
        ::= { applicationEntry 102 }
        
    applicationLongMessageHandling OBJECT-TYPE
        SYNTAX  LongMessageHandling
        ACCESS  read-write
        STATUS  mandatory
        DESCRIPTION
            "Indicator specifying how AO/SM-s whose payload is too long for a
            single MT/SM should be handled.
            Default is 'allowSendingToMobileAsConcatenated'."
        ::= { applicationEntry 103 }

    applicationNotificationHandling OBJECT-TYPE
        SYNTAX  NotificationHandling
        ACCESS  read-write
        STATUS  mandatory
        DESCRIPTION
            "Indicator specifying how applications notifications should
            be handled. See NotificationHandling for more information. The
            default is 'sessionPreferred'."
        ::= { applicationEntry 104 }

    applicationEnableAtRecipientStats OBJECT-TYPE
        SYNTAX  Boolean
        ACCESS  read-write
        STATUS  mandatory
        DESCRIPTION
            "Indicator specifying the AT recipient statistics shall be
            recorded for this Application. The AT recipient statistics
            are held in the appAtRecipientCountryStatsTable and
            appAtRecipientMobNetworkStatsTable tables per country and
            mobile network respectivaly. They are only available
            on the router. By default, this parameter is set to 'false'."
        ::= { applicationEntry 105 }

    applicationInsideDialoutSessionsCounter OBJECT-TYPE
        SYNTAX  DialoutSessions
        ACCESS  read-only
        STATUS  mandatory
        DESCRIPTION
            "Number of dialout sessions currently established between SMSC
            and TextPass. Only applicable if TextPass and the Application
            interface through dialout sessions."
        ::= { applicationEntry 106 }

    applicationOutsideDialoutSessionsCounter OBJECT-TYPE
        SYNTAX  DialoutSessions
        ACCESS  read-only
        STATUS  mandatory
        DESCRIPTION
            "Number of dialout sessions currently established between TextPass
            and Application. Only applicable if TextPass and the Application
            interface through dialout sessions."
        ::= { applicationEntry 107 }

    applicationOutsideSmppReceiversCounter OBJECT-TYPE
        SYNTAX  SmppConnections
        ACCESS  read-only
        STATUS  mandatory
        DESCRIPTION
            "Number of receiver links currently established between TextPass
            and the Application. Only applicable if TextPass and the
            Application interface through SMPP."
        ::= { applicationEntry 111 }

    applicationOutsideSmppTransmittersCounter OBJECT-TYPE
        SYNTAX  SmppConnections
        ACCESS  read-only
        STATUS  mandatory
        DESCRIPTION
            "Number of transmitter links currently established between
            TextPass and the Application. Only applicable if TextPass and the
            Application interface through SMPP."
        ::= { applicationEntry 112 }

    applicationOutsideSmppTransceiversCounter OBJECT-TYPE
        SYNTAX  SmppConnections
        ACCESS  read-only
        STATUS  mandatory
        DESCRIPTION
            "Number of transceiver links currently established between
            TextPass and the Application. Only applicable if TextPass and the
            Application interface through SMPP."
        ::= { applicationEntry 113 }

    applicationInsideSmppReceiversCounter OBJECT-TYPE
        SYNTAX  SmppConnections
        ACCESS  read-only
        STATUS  mandatory
        DESCRIPTION
            "Number of receiver links currently established between TextPass
            and the Service Centres. Only applicable if TextPass and the
            Service Centres interface through SMPP."
        ::= { applicationEntry 116 }

    applicationInsideSmppTransmittersCounter OBJECT-TYPE
        SYNTAX  SmppConnections
        ACCESS  read-only
        STATUS  mandatory
        DESCRIPTION
            "Number of transmitter links currently established between
            TextPass and the Service Centres. Only applicable if TextPass and
            the Service Centres interface through SMPP."
        ::= { applicationEntry 117 }

    applicationInsideSmppTransceiversCounter OBJECT-TYPE
        SYNTAX  SmppConnections
        ACCESS  read-only
        STATUS  mandatory
        DESCRIPTION
            "Number of transceiver links currently established between
            TextPass and the Service Centres. Only applicable if TextPass and
            the Service Centres interface through SMPP."
        ::= { applicationEntry 118 }

    applicationOutsideUcpSessionsCounter OBJECT-TYPE
        SYNTAX  UcpConnections
        ACCESS  read-only
        STATUS  mandatory
        DESCRIPTION
            "Number of UCP sessions currently established between TextPass and
            the Application. Only applicable if TextPass and the Application
            interface through UCP."
        ::= { applicationEntry 121 }

    applicationInsideUcpSessionsCounter OBJECT-TYPE
        SYNTAX  UcpConnections
        ACCESS  read-only
        STATUS  mandatory
        DESCRIPTION
            "Number of UCP sessions currently established between TextPass and
            the Service Centres. Only applicable if TextPass and the service
            centres interface through UCP."
        ::= { applicationEntry 126 }

    applicationOutsideCimdSessionsCounter OBJECT-TYPE
        SYNTAX  CimdConnections
        ACCESS  read-only
        STATUS  mandatory
        DESCRIPTION
            "Number of CIMD sessions currently established between TextPass
            and the Application. Only applicable if TextPass and the
            Application interface through CIMD."
        ::= { applicationEntry 131 }

    applicationInsideCimdSessionsCounter OBJECT-TYPE
        SYNTAX  CimdConnections
        ACCESS  read-only
        STATUS  mandatory
        DESCRIPTION
            "Number of CIMD sessions currently established between TextPass
            and the Service Centres. Only applicable if TextPass and the
            Service Centres interface through CIMD."
        ::= { applicationEntry 136 }

    applicationOutsideCapacityUsageAo OBJECT-TYPE
        SYNTAX  Percentage
        ACCESS  read-only
        STATUS  mandatory
        DESCRIPTION
            "Rate between actual number of pending submit transactions from
            the Application and the maximum number possible."
        ::= { applicationEntry 141 }

    applicationOutsideCapacityUsageAt OBJECT-TYPE
        SYNTAX  Percentage
        ACCESS  read-only
        STATUS  mandatory
        DESCRIPTION
            "Rate between actual number of pending delivery transactions
            towards the Application and the maximum number possible."
        ::= { applicationEntry 142 }

    applicationOutsideSessionsPending OBJECT-TYPE
        SYNTAX  Gauge
        ACCESS  read-only
        STATUS  mandatory
        DESCRIPTION
            "Number of new sessions currently being setup from the outside.
            This are sessions on which we received a login request but are
            not yet acknowledged (HUB busy with verification steps)."
        ::= { applicationEntry 143 }

    applicationInsideCapacityUsageAo OBJECT-TYPE
        SYNTAX  Percentage
        ACCESS  read-only
        STATUS  mandatory
        DESCRIPTION
            "Rate between actual number of pending submit transactions from
            the Service Centres and the maximum number possible."
        ::= { applicationEntry 146 }

    applicationInsideCapacityUsageAt OBJECT-TYPE
        SYNTAX  Percentage
        ACCESS  read-only
        STATUS  mandatory
        DESCRIPTION
            "Rate between actual number of pending delivery transactions
            towards the Service Centres and the maximum number possible."
        ::= { applicationEntry 147 }

    applicationInsideSessionsPending OBJECT-TYPE
        SYNTAX  Gauge
        ACCESS  read-only
        STATUS  mandatory
        DESCRIPTION
            "Number of new sessions currently being setup from the inside.
            This are sessions which are setup but no acknowlegment is
            recieved yet from the scTerminationPoint."
        ::= { applicationEntry 148 }

    applicationMoTotalCounter OBJECT-TYPE
        SYNTAX  Counter
        ACCESS  read-write
        STATUS  mandatory
        DESCRIPTION
            "Counter specifying the total number of times an MO/SM was
            received."
        ::= { applicationEntry 151 }

    applicationMoSuccessfulCounter OBJECT-TYPE
        SYNTAX  Counter
        ACCESS  read-write
        STATUS  mandatory
        DESCRIPTION
            "Counter specifying the number of times an MO/SM was successfully
             routed to its destination. The following events result in
             incrementing of this counter:
             - receiving a MO/SM matching a rule with action equal to
               discardWithAck
             - receiving an ACK from an Application as result of an MO/SM
               being routed to the Application
             - receiving an ACK from an SMSC as result of an MO/SM being
               routed to the SMSC."
        ::= { applicationEntry 152 }

    applicationMoTimeoutCounter OBJECT-TYPE
        SYNTAX  Counter
        ACCESS  read-write
        STATUS  mandatory
        DESCRIPTION
            "Counter specifying the number of times that routing an MO/SM to
            its destination resulted in a timeout. The following events
            result in incrementing of this counter:
             - not receiving a response from an Application on an MO/SM
               being routed to the Application within the maximum response
               time
             - receiving an ACK from an SMSC as result of an MO/SM being
               routed to an SMSC within the maximum response time."
        ::= { applicationEntry 153 }

    applicationMoDroppedCounter OBJECT-TYPE
        SYNTAX  Counter
        ACCESS  read-write
        STATUS  mandatory
        DESCRIPTION
            "Counter specifying the number of times that an MO/SM has not
            been routed to its destination due to decimation (this is only
            applicable when routing to an Application)."
        ::= { applicationEntry 154 }

    applicationMoDiscardWithNakCounter OBJECT-TYPE
        SYNTAX  Counter
        ACCESS  read-write
        STATUS  mandatory
        DESCRIPTION
            "Counter specifying the number of times that TPR has rejected an
            MO/SM as result of a routing rule with action equal to
            discardWithNak or because none of the routing rules match."
        ::= { applicationEntry 155 }

    applicationMoRejectedByTprCounter OBJECT-TYPE
        SYNTAX  Counter
        ACCESS  read-write
        STATUS  mandatory
        DESCRIPTION
            "Counter specifying the number of times that TPR has rejected an
            MO/SM as result of incorrect syntax of the MO/SM."
        ::= { applicationEntry 156 }

    applicationMoRejectedByAppCounter OBJECT-TYPE
        SYNTAX  Counter
        ACCESS  read-write
        STATUS  mandatory
        DESCRIPTION
            "Counter specifying the number of times that routing to an
            Application resulted in the Application rejecting the MO/SM by
            sending a NAK."
        ::= { applicationEntry 157 }

    applicationMoUnknownResultCounter OBJECT-TYPE
        SYNTAX  Counter
        ACCESS  read-write
        STATUS  mandatory
        DESCRIPTION
            "Counter specifying the number of times that the result of routing
            an MO/SM to its destination could not be retrieved (this is only
            applicable when using optimal routing towards an SMSC)."
        ::= { applicationEntry 158 }

    applicationMoSysFailErrorCounter OBJECT-TYPE
        SYNTAX  Counter
        ACCESS  read-write
        STATUS  mandatory
        DESCRIPTION
            "Counter specifying the number of times that routing to an SMSC
            resulted in the SMSC rejecting the MO/SM with a System-Failure
            error on MAP level."
        ::= { applicationEntry 159 }

    applicationMoDataMisErrorCounter OBJECT-TYPE
        SYNTAX  Counter
        ACCESS  read-write
        STATUS  mandatory
        DESCRIPTION
            "Counter specifying the number of times that routing to an SMSC
            resulted in the SMSC rejecting the MO/SM with a Data-Missing
            error on MAP level."
        ::= { applicationEntry 160 }

    applicationMoUnexpDataValErrorCounter OBJECT-TYPE
        SYNTAX  Counter
        ACCESS  read-write
        STATUS  mandatory
        DESCRIPTION
            "Counter specifying the number of times that routing to an SMSC
            resulted in the SMSC rejecting the MO/SM with a Unexpected-Data-
            Value error on MAP level."
        ::= { applicationEntry 161 }

    applicationMoFacNotSuppErrorCounter OBJECT-TYPE
        SYNTAX  Counter
        ACCESS  read-write
        STATUS  mandatory
        DESCRIPTION
            "Counter specifying the number of times that routing to an SMSC
            resulted in the SMSC rejecting the MO/SM with a Facility-Not-
            Supported error on MAP level."
        ::= { applicationEntry 162 }

    applicationMoUnkScErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Unknown-
            Service-Centre."
        ::= { applicationEntry 163 }

    applicationMoScCongErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to SC-
            Congestion."
        ::= { applicationEntry 164 }

    applicationMoInvSmeAddrErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to Invalid-
            SME-Address."
        ::= { applicationEntry 165 }

    applicationMoSubNotScSubErrorCounter OBJECT-TYPE
        SYNTAX  Counter
        ACCESS  read-write
        STATUS  mandatory
        DESCRIPTION
            "Counter specifying the number of times that routing to an SMSC
            resulted in the SMSC rejecting the MO/SM with a SM-Delivery-
            Failure error on MAP level with failure cause equal to
            Subscriber-Not-SC-Subscriber."
        ::= { applicationEntry 166 }

    applicationMoOtherErrorsCounter OBJECT-TYPE
        SYNTAX  Counter
        ACCESS  read-write
        STATUS  mandatory
        DESCRIPTION
            "Counter specifying the number of times that routing to an SMSC
            resulted in the SMSC rejecting the MO/SM with another MAP error
            (or possibly a failure cause) than specified for the
            other MO counters."
        ::= { applicationEntry 167 }

    applicationMoTcapAbortedCounter OBJECT-TYPE
        SYNTAX  Counter
        ACCESS  read-write
        STATUS  mandatory
        DESCRIPTION
            "Counter specifying the number of times that routing to an SMSC
            resulted in the SMSC rejecting the MO/SM by sending a TC-ABORT
            on TCAP level."
        ::= { applicationEntry 168 }

    applicationMoSccpAbortedCounter OBJECT-TYPE
        SYNTAX  Counter
        ACCESS  read-write
        STATUS  mandatory
        DESCRIPTION
            "Counter specifying the number of times that routing to an SMSC
            resulted in the SMSC rejecting the MO/SM by sending a UDTS on
            SCCP level."
        ::= { applicationEntry 169 }

    applicationMtTotalCounter OBJECT-TYPE
        SYNTAX  Counter
        ACCESS  read-write
        STATUS  mandatory
        DESCRIPTION
            "Counter specifying the total number of times an MT/SM was issued
            by the TPR. This counter is incremented whenever:
            - the TPR issues a MT/SM on behalf of an Application that is
              directly connected to the TPR
            - the TPR receives all MT/SM's from an SMSC and directs the MT/SM
              to its destination."
        ::= { applicationEntry 170 }

    applicationMtSuccessfulCounter OBJECT-TYPE
        SYNTAX  Counter
        ACCESS  read-write
        STATUS  mandatory
        DESCRIPTION
            "Counter specifying the number of times an MT/SM was successfully
            delivered."
        ::= { applicationEntry 171 }

    applicationMtTimeoutCounter OBJECT-TYPE
        SYNTAX  Counter
        ACCESS  read-write
        STATUS  mandatory
        DESCRIPTION
            "Counter specifying the number of times that delivering an MT/SM
            resulted in a timeout."
        ::= { applicationEntry 172 }

    applicationMtAbsSubErrorCounter OBJECT-TYPE
        SYNTAX  Counter
        ACCESS  read-write
        STATUS  mandatory
        DESCRIPTION
            "Counter specifying the number of times that delivering an MT/SM
            resulted in an Absent-Subscriber error."
        ::= { applicationEntry 173 }

    applicationMtSysFailErrorCounter OBJECT-TYPE
        SYNTAX  Counter
        ACCESS  read-write
        STATUS  mandatory
        DESCRIPTION
            "Counter specifying the number of times that delivering an MT/SM
            resulted in an System-Failure error."
        ::= { applicationEntry 174 }

    applicationMtDataMisErrorCounter OBJECT-TYPE
        SYNTAX  Counter
        ACCESS  read-write
        STATUS  mandatory
        DESCRIPTION
            "Counter specifying the number of times that delivering an MT/SM
            resulted in an Data-Missing error."
        ::= { applicationEntry 175 }

    applicationMtUnexpDataValErrorCounter OBJECT-TYPE
        SYNTAX  Counter
        ACCESS  read-write
        STATUS  mandatory
        DESCRIPTION
            "Counter specifying the number of times that delivering an MT/SM
            resulted in an Unexpected-Data-Value error."
        ::= { applicationEntry 176 }

    applicationMtFacNotSuppErrorCounter OBJECT-TYPE
        SYNTAX  Counter
        ACCESS  read-write
        STATUS  mandatory
        DESCRIPTION
            "Counter specifying the number of times that delivering an MT/SM
            resulted in an Facility-Not-Supported error."
        ::= { applicationEntry 177 }

    applicationMtUnidenSubErrorCounter OBJECT-TYPE
        SYNTAX  Counter
        ACCESS  read-write
        STATUS  mandatory
        DESCRIPTION
            "Counter specifying the number of times that delivering an MT/SM
            resulted in an Unidentified-Subscriber error."
        ::= { applicationEntry 178 }

    applicationMtIllSubErrorCounter OBJECT-TYPE
        SYNTAX  Counter
        ACCESS  read-write
        STATUS  mandatory
        DESCRIPTION
            "Counter specifying the number of times that delivering an MT/SM
            resulted in an Illegal-Subscriber error."
        ::= { applicationEntry 179 }

    applicationMtIllEquipErrorCounter OBJECT-TYPE
        SYNTAX  Counter
        ACCESS  read-write
        STATUS  mandatory
        DESCRIPTION
            "Counter specifying the number of times that delivering an MT/SM
            resulted in an Illegal-Equipment error."
        ::= { applicationEntry 180 }

    applicationMtSubBusyForMtSmErrorCounter OBJECT-TYPE
        SYNTAX  Counter
        ACCESS  read-write
        STATUS  mandatory
        DESCRIPTION
            "Counter specifying the number of times that delivering an MT/SM
            resulted in an Subscriber-Busy-For-MT-SMS error."
        ::= { applicationEntry 181 }

    applicationMtInvSmeAddrErrorCounter OBJECT-TYPE
        SYNTAX  Counter
        ACCESS  read-write
        STATUS  mandatory
        DESCRIPTION
            "Counter specifying the number of times that delivering an MT/SM
            resulted in a SM-Delivery-Failure error with failure cause equal
            to Invalid-SME-Address."
        ::= { applicationEntry 182 }

    applicationMtEquipProtErrorCounter OBJECT-TYPE
        SYNTAX  Counter
        ACCESS  read-write
        STATUS  mandatory
        DESCRIPTION
            "Counter specifying the number of times that delivering an MT/SM
            resulted in a SM-Delivery-Failure error with failure cause equal
            to Equipment-Protocol-Error."
        ::= { applicationEntry 183 }

    applicationMtEquipNotSmEquipErrorCounter OBJECT-TYPE
        SYNTAX  Counter
        ACCESS  read-write
        STATUS  mandatory
        DESCRIPTION
            "Counter specifying the number of times that delivering an MT/SM
            resulted in a SM-Delivery-Failure error with failure cause equal
            to Equipment-Not-SM-equipped."
        ::= { applicationEntry 184 }

    applicationMtMemCapExcErrorCounter OBJECT-TYPE
        SYNTAX  Counter
        ACCESS  read-write
        STATUS  mandatory
        DESCRIPTION
            "Counter specifying the number of times that delivering an MT/SM
            resulted in a SM-Delivery-Failure error with failure cause equal
            to Memory-Capacity-Exceeded."
        ::= { applicationEntry 185 }

    applicationMtOtherErrorsCounter OBJECT-TYPE
        SYNTAX  Counter
        ACCESS  read-write
        STATUS  mandatory
        DESCRIPTION
            "Counter specifying the number of times that delivering an MT/SM
            resulted in another MAP error (or possibly a failure cause) than
            specified for the other MT counters."
        ::= { applicationEntry 186 }

    applicationMtTcapAbortedCounter OBJECT-TYPE
        SYNTAX  Counter
        ACCESS  read-write
        STATUS  mandatory
        DESCRIPTION
            "Counter specifying the number of times that delivering an MT/SM
            resulted in the MSC/SGSN rejecting the MT/SM by sending a TC-ABORT
            on TCAP level."
        ::= { applicationEntry 187 }

    applicationMtSccpAbortedCounter OBJECT-TYPE
        SYNTAX  Counter
        ACCESS  read-write
        STATUS  mandatory
        DESCRIPTION
            "Counter specifying the number of times that delivering an MT/SM
            resulted in the MSC/SGSN rejecting the MT/SM by sending a UDTS on
            SCCP level."
        ::= { applicationEntry 188 }

    applicationMtFallbackToVersion2Counter OBJECT-TYPE
        SYNTAX  Counter
        ACCESS  read-write
        STATUS  mandatory
        DESCRIPTION
            "Counter specifying the number of times that delivering an MT/SM
            resulted in the MSC/SGSN requesting to fallback to MAP version 2."
        ::= { applicationEntry 189 }

    applicationMtFallbackToVersion1Counter OBJECT-TYPE
        SYNTAX  Counter
        ACCESS  read-write
        STATUS  mandatory
        DESCRIPTION
            "Counter specifying the number of times that delivering an MT/SM
            resulted in the MSC/SGSN requesting to fallback to MAP version 1."
        ::= { applicationEntry 190 }

    applicationMtAlternatePathUsedCounter OBJECT-TYPE
        SYNTAX  Counter
        ACCESS  read-write
        STATUS  mandatory
        DESCRIPTION
            "Counter specifying the number of times that for delivering an
            MT/SM both paths (through MSC and through SGSN) were available
            and that delivery on the primary path failed (and the alternate
            path was thus used)."
        ::= { applicationEntry 191 }

    applicationMtAlternatePathNotUsedCounter OBJECT-TYPE
        SYNTAX  Counter
        ACCESS  read-write
        STATUS  mandatory
        DESCRIPTION
            "Counter specifying the number of times that for delivering an
            MT/SM both paths (through MSC and through SGSN) were available
            and that delivery on the primary path succeeded (and the
            alternate path was thus not used)."
        ::= { applicationEntry 192 }

    applicationSriSmTotalCounter OBJECT-TYPE
        SYNTAX  Counter
        ACCESS  read-write
        STATUS  mandatory
        DESCRIPTION
            "Counter specifying the total number of times a Send-Routing-Info-
            For-SM operation was issued
            by the TPR. This counter is incremented whenever:
            - the TPR issues a Send-Routing-Info-For-SM operation as part of
              the delivery of a MT/SM that was sent by an Application that is
              directly connected to the TPR
            - the TPR receives all Send-Routing-Info-For-SM operations from
              an SMSC and directs the opeation to its destination."
        ::= { applicationEntry 193 }

    applicationSriSmSuccessCounter OBJECT-TYPE
        SYNTAX  Counter
        ACCESS  read-write
        STATUS  mandatory
        DESCRIPTION
            "Counter specifying the number of times a Send-Routing-Info-For-
            SM operation was successfully issued."
        ::= { applicationEntry 194 }

    applicationSriSmTimeoutCounter OBJECT-TYPE
        SYNTAX  Counter
        ACCESS  read-write
        STATUS  mandatory
        DESCRIPTION
            "Counter specifying the number of times that issueing a
            Send-Routing- Info-For-SM operation resulted in a timeout."
        ::= { applicationEntry 195 }

    applicationSriSmSysFailErrorCounter OBJECT-TYPE
        SYNTAX  Counter
        ACCESS  read-write
        STATUS  mandatory
        DESCRIPTION
            "Counter specifying the number of times that issueing a
            Send-Routing- Info-For-SM operation resulted in a System-Failure
            error."
        ::= { applicationEntry 196 }

    applicationSriSmDataMisErrorCounter OBJECT-TYPE
        SYNTAX  Counter
        ACCESS  read-write
        STATUS  mandatory
        DESCRIPTION
            "Counter specifying the number of times that issueing a
            Send-Routing- Info-For-SM operation resulted in a Data-Missing
            error."
        ::= { applicationEntry 197 }

    applicationSriSmUnexpDataValErrorCounter OBJECT-TYPE
        SYNTAX  Counter
        ACCESS  read-write
        STATUS  mandatory
        DESCRIPTION
            "Counter specifying the number of times that issueing a
            Send-Routing- Info-For-SM operation resulted in a
            Unexpected-Data-Value error."
        ::= { applicationEntry 198 }

    applicationSriSmFacNotSuppErrorCounter OBJECT-TYPE
        SYNTAX  Counter
        ACCESS  read-write
        STATUS  mandatory
        DESCRIPTION
            "Counter specifying the number of times that issueing a
            Send-Routing- Info-For-SM operation resulted in a
            Facility-Not-Supported error."
        ::= { applicationEntry 199 }

    applicationSriSmUnkSubErrorCounter OBJECT-TYPE
        SYNTAX  Counter
        ACCESS  read-write
        STATUS  mandatory
        DESCRIPTION
            "Counter specifying the number of times that issueing a
            Send-Routing- Info-For-SM operation resulted in a
            Unknown-Subscriber error."
        ::= { applicationEntry 200 }

    applicationSriSmAbsSubErrorCounter OBJECT-TYPE
        SYNTAX  Counter
        ACCESS  read-write
        STATUS  mandatory
        DESCRIPTION
            "Counter specifying the number of times that issueing a
            Send-Routing- Info-For-SM operation resulted in a
            Absent-Subscriber error."
        ::= { applicationEntry 201 }

    applicationSriSmCallBarredErrorCounter OBJECT-TYPE
        SYNTAX  Counter
        ACCESS  read-write
        STATUS  mandatory
        DESCRIPTION
            "Counter specifying the number of times that issueing a
            Send-Routing- Info-For-SM operation resulted in a Call-Barred
            error."
        ::= { applicationEntry 202 }

    applicationSriSmTeleServNotProvErrorCounter OBJECT-TYPE
        SYNTAX  Counter
        ACCESS  read-write
        STATUS  mandatory
        DESCRIPTION
            "Counter specifying the number of times that issueing a
            Send-Routing- Info-For-SM operation resulted in a
            Teleservice-Not-Provisioned error."
        ::= { applicationEntry 203 }

    applicationSriSmOtherErrorsCounter OBJECT-TYPE
        SYNTAX  Counter
        ACCESS  read-write
        STATUS  mandatory
        DESCRIPTION
            "Counter specifying the number of times that issueing a
            Send-Routing- Info-For-SM operation resulted in another error
            than specified for the other Send-Routing-Info-For-SM counters."
        ::= { applicationEntry 204 }

    applicationSriSmTcapAbortedCounter OBJECT-TYPE
        SYNTAX  Counter
        ACCESS  read-write
        STATUS  mandatory
        DESCRIPTION
            "Counter specifying the number of times that issueing a
            Send-Routing- Info-For-SM operation resulted in the HLR rejecting
            the operation by sending a TC-ABORT on TCAP level."
        ::= { applicationEntry 205 }

    applicationSriSmSccpAbortedCounter OBJECT-TYPE
        SYNTAX  Counter
        ACCESS  read-write
        STATUS  mandatory
        DESCRIPTION
            "Counter specifying the number of times that issueing a
            Send-Routing- Info-For-SM operation resulted in the HLR rejecting
            the operation by sending a UDTS on SCCP level."
        ::= { applicationEntry 206 }

    applicationSriSmFallbackToVersion2Counter OBJECT-TYPE
        SYNTAX  Counter
        ACCESS  read-write
        STATUS  mandatory
        DESCRIPTION
            "Counter specifying the number of times that issueing a
            Send-Routing- Info-For-SM operation resulted in the HLR
            requesting to fallback to MAP version 2."
        ::= { applicationEntry 207 }

    applicationSriSmFallbackToVersion1Counter OBJECT-TYPE
        SYNTAX  Counter
        ACCESS  read-write
        STATUS  mandatory
        DESCRIPTION
            "Counter specifying the number of times that issueing a
            Send-Routing- Info-For-SM operation resulted in the HLR
            requesting to fallback to MAP version 1."
        ::= { applicationEntry 208 }

    applicationRepStsTotalCounter OBJECT-TYPE
        SYNTAX  Counter
        ACCESS  read-write
        STATUS  mandatory
        DESCRIPTION
            "Counter specifying the total number of times a Report-SM-
            Delivery-Status operation was issued
            by the TPR. This counter is incremented whenever:
            - the TPR issues a Report-SM-Delivery-Status operation as part of
              the delivery of a MT/SM that was sent by an Application that is
              directly connected to the TPR
            - the TPR receives all Report-SM-Delivery-Status operations from
              an SMSC and directs the opeation to its destination."
        ::= { applicationEntry 209 }

    applicationRepStsSuccessCounter OBJECT-TYPE
        SYNTAX  Counter
        ACCESS  read-write
        STATUS  mandatory
        DESCRIPTION
            "Counter specifying the number of times a Report-SM-Delivery-
            Status operation was successfully issued."
        ::= { applicationEntry 210 }

    applicationRepStsTimeoutCounter OBJECT-TYPE
        SYNTAX  Counter
        ACCESS  read-write
        STATUS  mandatory
        DESCRIPTION
            "Counter specifying the number of times that issueing a
            Report-SM- Delivery-Status operation resulted in a timeout."
        ::= { applicationEntry 211 }

    applicationRepStsSysFailErrorCounter OBJECT-TYPE
        SYNTAX  Counter
        ACCESS  read-write
        STATUS  mandatory
        DESCRIPTION
            "Counter specifying the number of times that issueing a Report-SM-
            Delivery-Status operation resulted in a System-Failure error."
        ::= { applicationEntry 212 }

    applicationRepStsDataMisErrorCounter OBJECT-TYPE
        SYNTAX  Counter
        ACCESS  read-write
        STATUS  mandatory
        DESCRIPTION
            "Counter specifying the number of times that issueing a Report-SM-
            Delivery-Status operation resulted in a Data-Missing error."
        ::= { applicationEntry 213 }

    applicationRepStsUnexpDataValErrorCounter OBJECT-TYPE
        SYNTAX  Counter
        ACCESS  read-write
        STATUS  mandatory
        DESCRIPTION
            "Counter specifying the number of times that issueing a Report-SM-
            Delivery-Status operation resulted in a Unexpected-Data-Value
            error."
        ::= { applicationEntry 214 }

    applicationRepStsUnkSubErrorCounter OBJECT-TYPE
        SYNTAX  Counter
        ACCESS  read-write
        STATUS  mandatory
        DESCRIPTION
           "Counter specifying the number of times that issueing a Report-SM-
            Delivery-Status operation resulted in an Unknown-Subscriber
            error."
        ::= { applicationEntry 215 }

    applicationRepStsMsgWaitListFullErrorCounter OBJECT-TYPE
        SYNTAX  Counter
        ACCESS  read-write
        STATUS  mandatory
        DESCRIPTION
           "Counter specifying the number of times that issueing a Report-SM-
            Delivery-Status operation resulted in a Message-Waiting-List-Full
            error."
        ::= { applicationEntry 216 }

    applicationRepStsOtherErrorsCounter OBJECT-TYPE
        SYNTAX  Counter
        ACCESS  read-write
        STATUS  mandatory
        DESCRIPTION
            "Counter specifying the number of times that issueing a
            Report-SM- Delivery-Status operation resulted in in another error
            than specified for the other Report-SM-Delivery-Status counters."
        ::= { applicationEntry 217 }

    applicationRepStsTcapAbortedCounter OBJECT-TYPE
        SYNTAX  Counter
        ACCESS  read-write
        STATUS  mandatory
        DESCRIPTION
            "Counter specifying the number of times that issueing a Report-SM-
            Delivery-Status operation resulted in the HLR rejecting the
            operation by sending a TC-ABORT on TCAP level."
        ::= { applicationEntry 218 }

    applicationRepStsSccpAbortedCounter OBJECT-TYPE
        SYNTAX  Counter
        ACCESS  read-write
        STATUS  mandatory
        DESCRIPTION
            "Counter specifying the number of times that issueing a Report-SM-
            Delivery-Status operation resulted in the HLR rejecting the
            operation by sending a UDTS on SCCP level."
        ::= { applicationEntry 219 }

    applicationRepStsFallbackToVersion2Counter OBJECT-TYPE
        SYNTAX  Counter
        ACCESS  read-write
        STATUS  mandatory
        DESCRIPTION
            "Counter specifying the number of times that issueing a Report-SM-
            Delivery-Status operation resulted in the HLR requesting to
            fallback to MAP version 2."
        ::= { applicationEntry 220 }

    applicationRepStsFallbackToVersion1Counter OBJECT-TYPE
        SYNTAX  Counter
        ACCESS  read-write
        STATUS  mandatory
        DESCRIPTION
            "Counter specifying the number of times that issueing a Report-SM-
            Delivery-Status operation resulted in the HLR requesting to
            fallback to MAP version 1."
        ::= { applicationEntry 221 }

    applicationCntInsideAoTotal OBJECT-TYPE
        SYNTAX  Counter
        ACCESS  read-write
        STATUS  mandatory
        DESCRIPTION
            "Counter specifying the total number of times an AO/SM was
            sent towards a Service Centre."
        ::= { applicationEntry 231 }

    applicationCntInsideAoSuccess OBJECT-TYPE
        SYNTAX  Counter
        ACCESS  read-write
        STATUS  mandatory
        DESCRIPTION
            "Counter specifying the number of times an AO/SM was
            successfully routed to its destination."
        ::= { applicationEntry 232 }

    applicationCntInsideAoSourceError OBJECT-TYPE
        SYNTAX  Counter
        ACCESS  read-write
        STATUS  mandatory
        DESCRIPTION
            "Counter specifying the number of times an AO/SM towards
             a Service Centre resulted in a source error
             (like a syntax error). The error mapping
             table is used to identify a source error. With a correct
             error mapping table it is not possible that this counter
             increases."
        ::= { applicationEntry 233 }

    applicationCntInsideAoRoutingError OBJECT-TYPE
        SYNTAX  Counter
        ACCESS  read-write
        STATUS  mandatory
        DESCRIPTION
            "Counter specifying the number of times an AO/SM towards
            a Service Centre resulted in a routing error. The error
            mapping table is used to identify a routing error."
        ::= { applicationEntry 234 }

    applicationCntInsideAoDestinationTemporaryError OBJECT-TYPE
        SYNTAX  Counter
        ACCESS  read-write
        STATUS  mandatory
        DESCRIPTION
            "Counter specifying the number of times an AO/SM towards
            a Service Centre resulted in a temporary error. The error
            mapping table is used to identify a temporary error."
        ::= { applicationEntry 235 }

    applicationCntInsideAoDestinationPermanentRecipientError OBJECT-TYPE
        SYNTAX  Counter
        ACCESS  read-write
        STATUS  mandatory
        DESCRIPTION
            "Counter specifying the number of times an AO/SM towards
            a Service Centre resulted in a permanent recipient error. 
            The error mapping table is used to identify a permanent 
            recipient error."
        ::= { applicationEntry 236 }

    applicationCntInsideAoDestinationPermanentMessageError OBJECT-TYPE
        SYNTAX  Counter
        ACCESS  read-write
        STATUS  mandatory
        DESCRIPTION
            "Counter specifying the number of times an AO/SM towards
            a Service Centre resulted in a permanent message error. The 
            error mapping table is used to identify a permanent message 
            error."
        ::= { applicationEntry 237 }

    applicationCntInsideAtTotal OBJECT-TYPE
        SYNTAX  Counter
        ACCESS  read-write
        STATUS  mandatory
        DESCRIPTION
            "Counter specifying the total number of times an AT/SM was
            received from a Service Centre."
        ::= { applicationEntry 238 }

    applicationCntInsideAtSuccess OBJECT-TYPE
        SYNTAX  Counter
        ACCESS  read-write
        STATUS  mandatory
        DESCRIPTION
            "Counter specifying the number of times an AT/SM was
            successfully routed to its destination."
        ::= { applicationEntry 239 }

    applicationCntInsideAtSourceError OBJECT-TYPE
        SYNTAX  Counter
        ACCESS  read-write
        STATUS  mandatory
        DESCRIPTION
            "Counter specifying the number of times an AT/SM from
             a Service Centre resulted in a source error
             (like a syntax error). The error mapping
             table is used to identify a source error."
        ::= { applicationEntry 240 }

    applicationCntInsideAtRoutingError OBJECT-TYPE
        SYNTAX  Counter
        ACCESS  read-write
        STATUS  mandatory
        DESCRIPTION
            "Counter specifying the number of times an AT/SM from
            a Service Centre resulted in a routing error. The error
            mapping table is used to identify a routing error."
        ::= { applicationEntry 241 }

    applicationCntInsideAtDestinationTemporaryError OBJECT-TYPE
        SYNTAX  Counter
        ACCESS  read-write
        STATUS  mandatory
        DESCRIPTION
            "Counter specifying the number of times an AT/SM from
            a Service Centre resulted in a temporary error. The error
            mapping table is used to identify a temporary error."
        ::= { applicationEntry 242 }

    applicationCntInsideAtDestinationPermanentRecipientError OBJECT-TYPE
        SYNTAX  Counter
        ACCESS  read-write
        STATUS  mandatory
        DESCRIPTION
            "Counter specifying the number of times an AT/SM from
            a Service Centre resulted in a permanent recipient error. 
            The error mapping table is used to identify a permanent 
            recipient error."
        ::= { applicationEntry 243 }

    applicationCntInsideAtDestinationPermanentMessageError OBJECT-TYPE
        SYNTAX  Counter
        ACCESS  read-write
        STATUS  mandatory
        DESCRIPTION
            "Counter specifying the number of times an AT/SM from
            a Service Centre resulted in a permanent message error. The 
            error mapping table is used to identify a permanent message 
            error."
        ::= { applicationEntry 244 }

    applicationCntOutsideAoTotal OBJECT-TYPE
        SYNTAX  Counter
        ACCESS  read-write
        STATUS  mandatory
        DESCRIPTION
            "Counter specifying the total number of times an AO/SM was
            received from an Application."
        ::= { applicationEntry 245 }

    applicationCntOutsideAoSuccess OBJECT-TYPE
        SYNTAX  Counter
        ACCESS  read-write
        STATUS  mandatory
        DESCRIPTION
            "Counter specifying the number of times an AO/SM was
            successfully routed to its destination."
        ::= { applicationEntry 246 }

    applicationCntOutsideAoSourceError OBJECT-TYPE
        SYNTAX  Counter
        ACCESS  read-write
        STATUS  mandatory
        DESCRIPTION
            "Counter specifying the number of times an AO/SM from
             an Application resulted in a source error
             (like a syntax error). The error mapping
             table is used to identify a source error."
        ::= { applicationEntry 247 }

    applicationCntOutsideAoRoutingError OBJECT-TYPE
        SYNTAX  Counter
        ACCESS  read-write
        STATUS  mandatory
        DESCRIPTION
            "Counter specifying the number of times an AO/SM from
            an Application resulted in a routing error. The error
            mapping table is used to identify a routing error."
        ::= { applicationEntry 248 }

    applicationCntOutsideAoDestinationTemporaryError OBJECT-TYPE
        SYNTAX  Counter
        ACCESS  read-write
        STATUS  mandatory
        DESCRIPTION
            "Counter specifying the number of times an AO/SM from
            an Application resulted in a temporary error. The error
            mapping table is used to identify a temporary error."
        ::= { applicationEntry 249 }

    applicationCntOutsideAoDestinationPermanentRecipientError OBJECT-TYPE
        SYNTAX  Counter
        ACCESS  read-write
        STATUS  mandatory
        DESCRIPTION
             "Counter specifying the number of times an AO/SM from
            an Application resulted in a permanent recipient error. 
            The error mapping table is used to identify a permanent 
            recipient error."
        ::= { applicationEntry 250 }

    applicationCntOutsideAoDestinationPermanentMessageError OBJECT-TYPE
        SYNTAX  Counter
        ACCESS  read-write
        STATUS  mandatory
        DESCRIPTION
            "Counter specifying the number of times an AO/SM from
            an Application resulted in a permanent message error. 
            The error mapping table is used to identify a permanent 
            message error."
        ::= { applicationEntry 251 }

    applicationCntOutsideAtTotal OBJECT-TYPE
        SYNTAX  Counter
        ACCESS  read-write
        STATUS  mandatory
        DESCRIPTION
            "Counter specifying the total number of times an AT/SM was
            sent towards an Application."
        ::= { applicationEntry 252 }

    applicationCntOutsideAtSuccess OBJECT-TYPE
        SYNTAX  Counter
        ACCESS  read-write
        STATUS  mandatory
        DESCRIPTION
            "Counter specifying the number of times an AT/SM was
            successfully routed to its destination."
        ::= { applicationEntry 253 }

    applicationCntOutsideAtSourceError OBJECT-TYPE
        SYNTAX  Counter
        ACCESS  read-write
        STATUS  mandatory
        DESCRIPTION
            "Counter specifying the number of times an AT/SM towards
             an Application resulted in a source error
             (like a syntax error). The error mapping
             table is used to identify a source error. With a correct
             error mapping table it is not possible that this counter
             increases."
        ::= { applicationEntry 254 }

    applicationCntOutsideAtRoutingError OBJECT-TYPE
        SYNTAX  Counter
        ACCESS  read-write
        STATUS  mandatory
        DESCRIPTION
            "Counter specifying the number of times an AT/SM towards
            an Application resulted in a routing error. The error
            mapping table is used to identify a routing error."
        ::= { applicationEntry 255 }

    applicationCntOutsideAtDestinationTemporaryError OBJECT-TYPE
        SYNTAX  Counter
        ACCESS  read-write
        STATUS  mandatory
        DESCRIPTION
            "Counter specifying the number of times an AT/SM towards
            an Application resulted in a temporary error. The error
            mapping table is used to identify a temporary error."
        ::= { applicationEntry 256 }

    applicationCntOutsideAtDestinationPermanentRecipientError OBJECT-TYPE
        SYNTAX  Counter
        ACCESS  read-write
        STATUS  mandatory
        DESCRIPTION
            "Counter specifying the number of times an AT/SM towards
            an Application resulted in a permanent recipient error. 
            The error mapping table is used to identify a permanent 
            recipient error."
        ::= { applicationEntry 257 }

    applicationCntOutsideAtDestinationPermanentMessageError OBJECT-TYPE
        SYNTAX  Counter
        ACCESS  read-write
        STATUS  mandatory
        DESCRIPTION
            "Counter specifying the number of times an AT/SM towards
            an Application resulted in a permanent message error. The 
            error mapping table is used to identify a permanent message 
            error."
        ::= { applicationEntry 258 }

    applicationCntAoMtSuccess OBJECT-TYPE
        SYNTAX  Counter
        ACCESS  read-write
        STATUS  mandatory
        DESCRIPTION
            "Counter specifying the number of times an AO->MT routed
            message was succesfully delivered as MT/SM."
        ::= { applicationEntry 300 }

    applicationCntAoMtFailure OBJECT-TYPE
        SYNTAX  Counter
        ACCESS  read-write
        STATUS  mandatory
        DESCRIPTION
            "Counter specifying the number of times an AO->MT routed
            message failed to be delivered as MT/SM."
        ::= { applicationEntry 301 }

    applicationCntAoAoSuccess OBJECT-TYPE
        SYNTAX  Counter
        ACCESS  read-write
        STATUS  mandatory
        DESCRIPTION
            "Counter specifying the number of times an AO->AO routed message
            was succesfully submitted as AO/SM."
        ::= { applicationEntry 302 }

    applicationCntAoAoFailure OBJECT-TYPE
        SYNTAX  Counter
        ACCESS  read-write
        STATUS  mandatory
        DESCRIPTION
            "Counter specifying the number of times an AO->AO routed message
            failed to be submitted as AO/SM."
        ::= { applicationEntry 303 }

    applicationCntAtAtSuccess OBJECT-TYPE
        SYNTAX  Counter
        ACCESS  read-write
        STATUS  mandatory
        DESCRIPTION
            "Counter specifying the number of times an AT->AT routed message
            was succesfully delivered as AT/SM."
        ::= { applicationEntry 304 }

    applicationCntAtAtFailure OBJECT-TYPE
        SYNTAX  Counter
        ACCESS  read-write
        STATUS  mandatory
        DESCRIPTION
            "Counter specifying the number of times an AT->AT routed message
            failed to be delivered as AT/SM."
        ::= { applicationEntry 305 }

    applicationCntMoMoSuccess OBJECT-TYPE
        SYNTAX  Counter
        ACCESS  read-write
        STATUS  mandatory
        DESCRIPTION
            "Counter specifying the number of times an MO->MO routed message
            was succesfully submitted as MO/SM."
        ::= { applicationEntry 306 }

    applicationCntMoMoFailure OBJECT-TYPE
        SYNTAX  Counter
        ACCESS  read-write
        STATUS  mandatory
        DESCRIPTION
            "Counter specifying the number of times an MO->MO routed message
            failed to be submitted as MO/SM."
        ::= { applicationEntry 307 }

    applicationCntMoAoSuccess OBJECT-TYPE
        SYNTAX  Counter
        ACCESS  read-write
        STATUS  mandatory
        DESCRIPTION
            "Counter specifying the number of times an MO->AO routed message
            was succesfully submitted as AO/SM."
        ::= { applicationEntry 308 }

    applicationCntMoAoFailure OBJECT-TYPE
        SYNTAX  Counter
        ACCESS  read-write
        STATUS  mandatory
        DESCRIPTION
            "Counter specifying the number of times an MO->AO routed message
            failed to be submitted as AO/SM."
        ::= { applicationEntry 309 }

    applicationCntMoAtSuccess OBJECT-TYPE
        SYNTAX  Counter
        ACCESS  read-write
        STATUS  mandatory
        DESCRIPTION
            "Counter specifying the number of times an MO->AT routed message
            was succesfully delivered as AT/SM."
        ::= { applicationEntry 310 }

    applicationCntMoAtFailure OBJECT-TYPE
        SYNTAX  Counter
        ACCESS  read-write
        STATUS  mandatory
        DESCRIPTION
            "Counter specifying the number of times an MO->AT routed message
            failed to be delivered as AT/SM."
        ::= { applicationEntry 311 }

    applicationCntMtMtSuccess OBJECT-TYPE
        SYNTAX  Counter
        ACCESS  read-write
        STATUS  mandatory
        DESCRIPTION
            "Counter specifying the number of times an MT->MT routed message
            was succesfully delivered as MT/SM."
        ::= { applicationEntry 312 }

    applicationCntMtMtFailure OBJECT-TYPE
        SYNTAX  Counter
        ACCESS  read-write
        STATUS  mandatory
        DESCRIPTION
            "Counter specifying the number of times an MT->MT  routed message
            failed to be delivered as MT/SM."
        ::= { applicationEntry 313 }

    applicationCntAoDiscard OBJECT-TYPE
        SYNTAX  Counter
        ACCESS  read-write
        STATUS  mandatory
        DESCRIPTION
            "Counter specifying the number of times an AO/SM
            was discarded because of a rule."
        ::= { applicationEntry 314 }

    applicationCntAtDiscard OBJECT-TYPE
        SYNTAX  Counter
        ACCESS  read-write
        STATUS  mandatory
        DESCRIPTION
            "Counter specifying the number of times an AT/SM
            was discarded because of a rule."
        ::= { applicationEntry 315 }

    applicationCntMoDiscard OBJECT-TYPE
        SYNTAX  Counter
        ACCESS  read-write
        STATUS  mandatory
        DESCRIPTION
            "Counter specifying the number of times an MO/SM
            was discarded because of a rule."
        ::= { applicationEntry 316 }

    applicationCntMtDiscard OBJECT-TYPE
        SYNTAX  Counter
        ACCESS  read-write
        STATUS  mandatory
        DESCRIPTION
            "Counter specifying the number of times an MT/SM
            was discarded because of a rule."
        ::= { applicationEntry 317 }

    applicationCntAoMtAoPrimarySuccess OBJECT-TYPE
        SYNTAX  Counter
        ACCESS  read-write
        STATUS  mandatory
        DESCRIPTION
            "Counter specifying the number of times an AO->MT->AO routed
            message was succesfully delivered as MT/SM."
        ::= { applicationEntry 318 }

    applicationCntAoMtAoFallbackSuccess OBJECT-TYPE
        SYNTAX  Counter
        ACCESS  read-write
        STATUS  mandatory
        DESCRIPTION
            "Counter specifying the number of times an AO->MT->AO routed
            message was succesfully submitted as AO/SM after a failed first
            delivery attempt as MT/SM."
        ::= { applicationEntry 319 }

    applicationCntAoMtAoFallbackFailure OBJECT-TYPE
        SYNTAX  Counter
        ACCESS  read-write
        STATUS  mandatory
        DESCRIPTION
            "Counter specifying the number of times an AO->MT->AO routed
            message failed to be submitted as AO/SM after a failed first
            delivery attempt as MT/SM."
        ::= { applicationEntry 320 }
     
    applicationCntAoMtAoPrimaryFailure OBJECT-TYPE
        SYNTAX  Counter
        ACCESS  read-write
        STATUS  mandatory
        DESCRIPTION
            "Counter specifying the number of times an AO->MT->AO routed
            message failed to be delivered as MT/SM."
        ::= { applicationEntry 321 }

    applicationCntAoMtAoFallbackNotAppliedDueToPermErrorOnPrimary OBJECT-TYPE
        SYNTAX  Counter
        ACCESS  read-write
        STATUS  mandatory
        DESCRIPTION
            "Counter specifying the number of times an AO->MT->AO routed
            message was not attempted to be submitted as AO/SM because
            the first delivery attempt as MT/SM resulted in an error
            classified as 'permanent'."
        ::= { applicationEntry 322 }

    applicationCntAoMtAoFallbackNotAppliedDueToUnavailability OBJECT-TYPE
        SYNTAX  Counter
        ACCESS  read-write
        STATUS  mandatory
        DESCRIPTION
            "Counter specifying the number of times an AO->MT->AO routed
            message was not attempted to be submitted as AO/SM after a
            failed first delivery attempt as MT/SM, because the service
            centre was unavailable."
        ::= { applicationEntry 323 }

    applicationCntAoMtToAmsSuccess OBJECT-TYPE
        SYNTAX  Counter
        ACCESS  read-write
        STATUS  mandatory
        DESCRIPTION
            "Counter specifying the number of times an AO->AMS(as MT) routed
            message was successfully stored in the AMS."
        ::= { applicationEntry 324 }

    applicationCntAoMtToAmsFailure OBJECT-TYPE
        SYNTAX  Counter
        ACCESS  read-write
        STATUS  mandatory
        DESCRIPTION
            "Counter specifying the number of times an AO->AMS(as MT) routed
            message failed to be stored in the AMS."
        ::= { applicationEntry 325 }

    applicationCntAoMtAmsSuccess OBJECT-TYPE
        SYNTAX  Counter
        ACCESS  read-write
        STATUS  mandatory
        DESCRIPTION
            "Counter specifying the number of times an AO->MT->AMS routed
            message was accepted by the AMS for direct delivery as MT/SM."
        ::= { applicationEntry 326 }

    applicationCntAoMtAmsFailure OBJECT-TYPE
        SYNTAX  Counter
        ACCESS  read-write
        STATUS  mandatory
        DESCRIPTION
            "Counter specifying the number of times an AO->MT->AMS routed
            message failed to be submitted to the AMS for direct delivery
            as MT/SM."
        ::= { applicationEntry 327 }

    applicationCntMoMtToAmsSuccess OBJECT-TYPE
        SYNTAX  Counter
        ACCESS  read-write
        STATUS  mandatory
        DESCRIPTION
            "Counter specifying the number of times an MO->AMS(as MT)
            routed message was successfully stored in the AMS."
        ::= { applicationEntry 332 }

    applicationCntMoMtToAmsFailure OBJECT-TYPE
        SYNTAX  Counter
        ACCESS  read-write
        STATUS  mandatory
        DESCRIPTION
            "Counter specifying the number of times an MO->AMS(as MT)
            routed message failed to be stored in AMS."
        ::= { applicationEntry 333 }

    applicationCntMoMtAmsPrimarySuccess OBJECT-TYPE
        SYNTAX  Counter
        ACCESS  read-write
        STATUS  mandatory
        DESCRIPTION
            "Counter specifying the number of times an MO->MT->AMS(as MT)
            routed message was successfully delivered as MT/SM."
        ::= { applicationEntry 334 }

    applicationCntMoMtAmsPrimaryFailure OBJECT-TYPE
        SYNTAX  Counter
        ACCESS  read-write
        STATUS  mandatory
        DESCRIPTION
            "Counter specifying the number of times an MO->MT->AMS(as MT)
            routed message failed to be delivered as MT/SM."
        ::= { applicationEntry 335 }

    applicationCntMoMtAmsFallbackSuccess OBJECT-TYPE
        SYNTAX  Counter
        ACCESS  read-write
        STATUS  mandatory
        DESCRIPTION
            "Counter specifying the number of times an MO->MT->AMS
            routed message was successfully stored in the AMS after a first
            delivery attempt failed."
        ::= { applicationEntry 336 }

    applicationCntMoMtAmsFallbackFailure OBJECT-TYPE
        SYNTAX  Counter
        ACCESS  read-write
        STATUS  mandatory
        DESCRIPTION
            "Counter specifying the number of times an MO->MT->AMS
            routed message could not be stored in the AMS after a first
            delivery attempt failed."
        ::= { applicationEntry 337 }

    applicationCntMoMtAmsFallbackNotAppliedDueToPermErrorOnPrimary OBJECT-TYPE
        SYNTAX  Counter
        ACCESS  read-write
        STATUS  mandatory
        DESCRIPTION
            "Counter specifying the number of times an MO->MT->AMS
            routed message was not attempted to be stored in the AMS because
            the first delivery attempt as MT/SM resulted in an error
            classified as 'permanent'."
        ::= { applicationEntry 338 }

    applicationCntMoMtAmsFallbackNotAppliedDueToUnavailability OBJECT-TYPE
        SYNTAX  Counter
        ACCESS  read-write
        STATUS  mandatory
        DESCRIPTION
            "Counter specifying the number of times an MO->MT->AMS
            routed message was not attempted to be stored in the AMS after
            a failed first delivery attempt as MT/SM, because the AMS was
            not available."
        ::= { applicationEntry 339 }

    applicationCntMoAtToAmsSuccess OBJECT-TYPE
        SYNTAX  Counter
        ACCESS  read-write
        STATUS  mandatory
        DESCRIPTION
            "Counter specifying the number of times an MO->AMS(as AT)
            routed message was successfully stored in the AMS."
        ::= { applicationEntry 340 }

    applicationCntMoAtToAmsFailure OBJECT-TYPE
        SYNTAX  Counter
        ACCESS  read-write
        STATUS  mandatory
        DESCRIPTION
            "Counter specifying the number of times an MO->AMS(as AT)
            routed message failed to be stored in the AMS."
        ::= { applicationEntry 341 }

    applicationCntMoAtAmsPrimarySuccess OBJECT-TYPE
        SYNTAX  Counter
        ACCESS  read-write
        STATUS  mandatory
        DESCRIPTION
            "Counter specifying the number of times an MO->AT->AMS
            routed message was successfully delivered as AT/SM."
        ::= { applicationEntry 342 }

    applicationCntMoAtAmsPrimaryFailure OBJECT-TYPE
        SYNTAX  Counter
        ACCESS  read-write
        STATUS  mandatory
        DESCRIPTION
            "Counter specifying the number of times an MO->AT->AMS
            routed message failed to be delivered as AT/SM."
        ::= { applicationEntry 343 }

    applicationCntMoAtAmsFallbackSuccess OBJECT-TYPE
        SYNTAX  Counter
        ACCESS  read-write
        STATUS  mandatory
        DESCRIPTION
            "Counter specifying the number of times an MO->AT->AMS
            routed message was successfully stored in the AMS after the
            first delivery attempt as AT/SM failed."
        ::= { applicationEntry 344 }

    applicationCntMoAtAmsFallbackFailure OBJECT-TYPE
        SYNTAX  Counter
        ACCESS  read-write
        STATUS  mandatory
        DESCRIPTION
            "Counter specifying the number of times an MO->AT->AMS routed
            message failed to be stored in the AMS after the first delivery
            attempt as AT/SM failed."
        ::= { applicationEntry 345 }

    applicationCntMoAtAmsFallbackNotAppliedDueToPermErrorOnPrimary OBJECT-TYPE
        SYNTAX  Counter
        ACCESS  read-write
        STATUS  mandatory
        DESCRIPTION
            "Counter specifying the number of times an MO->AT->AMS routed
            message was not attempted to be stored in the AMS because the
            first delivery attempt as AT/SM resulted in an error
            classified as 'permanent'."
        ::= { applicationEntry 346 }

    applicationCntMoAtAmsFallbackNotAppliedDueToUnavailability OBJECT-TYPE
        SYNTAX  Counter
        ACCESS  read-write
        STATUS  mandatory
        DESCRIPTION
            "Counter specifying the number of times an MO->AT->AMS routed
            message was not stored in the AMS after a failed first delivery
            attempt as AT/SM, because the AMS was unavailable."
        ::= { applicationEntry 347 }

    applicationCntMoMtMoPrimarySuccess OBJECT-TYPE
        SYNTAX  Counter
        ACCESS  read-write
        STATUS  mandatory
        DESCRIPTION
            "Counter specifying the number of times an MO->MT->MO routed
            message was succesfully delivered as MT/SM."
        ::= { applicationEntry 348 }

    applicationCntMoMtMoPrimaryFailure OBJECT-TYPE
        SYNTAX  Counter
        ACCESS  read-write
        STATUS  mandatory
        DESCRIPTION
            "Counter specifying the number of times an MO->MT->MO routed
            message failed to be delivered as MT/SM."
        ::= { applicationEntry 349 }

    applicationCntMoMtMoFallbackSuccess OBJECT-TYPE
        SYNTAX  Counter
        ACCESS  read-write
        STATUS  mandatory
        DESCRIPTION
            "Counter specifying the number of times an MO->MT->MO routed
            message was succesfully submitted as MO/SM after a failed
            first delivery attempt."
        ::= { applicationEntry 350 }

    applicationCntMoMtMoFallbackFailure OBJECT-TYPE
        SYNTAX  Counter
        ACCESS  read-write
        STATUS  mandatory
        DESCRIPTION
            "Counter specifying the number of times an MO->MT->MO routed
            message failed to be submitted as MO/SM after a failed first
            delivery attempt as MT/SM."
        ::= { applicationEntry 351 }

    applicationCntMoMtMoFallbackNotAppliedDueToPermErrorOnPrimary OBJECT-TYPE
        SYNTAX  Counter
        ACCESS  read-write
        STATUS  mandatory
        DESCRIPTION
            "Counter specifying the number of times an MO->MT->MO routed
            message was not attempted to be submitted as MO/SM because the
            first delivery attempt as MT/SM failed with an error classified
            as 'permanent'."
        ::= { applicationEntry 352 }

    applicationCntMoMtMoFallbackNotAppliedDueToUnavailability OBJECT-TYPE
        SYNTAX  Counter
        ACCESS  read-write
        STATUS  mandatory
        DESCRIPTION
            "Counter specifying the number of times an MO->MT->MO routed
            message was not attempted to be subbmitted as MO/SM after a
            failed first delivery attempt as MT/SM, because the SMSC was
            unavailable."
        ::= { applicationEntry 353 }

    applicationCntMoMtAtPrimarySuccess OBJECT-TYPE
        SYNTAX  Counter
        ACCESS  read-write
        STATUS  mandatory
        DESCRIPTION
            "Counter specifying the number of times an MO->MT->AT routed
            message was succesfully delivered as MT/SM."
        ::= { applicationEntry 354 }

    applicationCntMoMtAtPrimaryFailure OBJECT-TYPE
        SYNTAX  Counter
        ACCESS  read-write
        STATUS  mandatory
        DESCRIPTION
            "Counter specifying the number of times an MO->MT->AT routed
            message failed to be delivered as MT/SM."
        ::= { applicationEntry 355 }

    applicationCntMoMtAtFallbackSuccess OBJECT-TYPE
        SYNTAX  Counter
        ACCESS  read-write
        STATUS  mandatory
        DESCRIPTION
            "Counter specifying the number of times an MO->MT->AT routed
            message was succesfully delivered as AT/SM after a failed
            first delivery attempt as MT/SM."
        ::= { applicationEntry 356 }

    applicationCntMoMtAtFallbackFailure OBJECT-TYPE
        SYNTAX  Counter
        ACCESS  read-write
        STATUS  mandatory
        DESCRIPTION
            "Counter specifying the number of times an MO->MT->AT routed
            message failed to be delivered as AT/SM after a failed
            first delivery attempt as MT/SM."
        ::= { applicationEntry 357 }

    applicationCntMoMtAtFallbackNotAppliedDueToPermErrorOnPrimary OBJECT-TYPE
        SYNTAX  Counter
        ACCESS  read-write
        STATUS  mandatory
        DESCRIPTION
            "Counter specifying the number of times an MO->MT->AT routed
            message was not attempted to be delivered as AT/SM because
            the first delivery attempt as MT/SM failed with an error
            classified as 'permanent'."
        ::= { applicationEntry 358 }

    applicationCntMoMtAtFallbackNotAppliedDueToUnavailability OBJECT-TYPE
        SYNTAX  Counter
        ACCESS  read-write
        STATUS  mandatory
        DESCRIPTION
            "Counter specifying the number of times an MO->MT->AT routed
            message was not attempted to be delivered as AT/SM after a
            failed first delivery attempt as MT/SM, because the target
            Application was unavailable."
        ::= { applicationEntry 359 }

    applicationCntMoMtAoPrimarySuccess OBJECT-TYPE
        SYNTAX  Counter
        ACCESS  read-write
        STATUS  mandatory
        DESCRIPTION
            "Counter specifying the number of times an MO->MT->AO routed
            message was succesfully delivered as MT/SM."
        ::= { applicationEntry 360 }

    applicationCntMoMtAoPrimaryFailure OBJECT-TYPE
        SYNTAX  Counter
        ACCESS  read-write
        STATUS  mandatory
        DESCRIPTION
            "Counter specifying the number of times an MO->MT->AO routed
            message failed to be delivered as MT/SM."
        ::= { applicationEntry 361 }

    applicationCntMoMtAoFallbackSuccess OBJECT-TYPE
        SYNTAX  Counter
        ACCESS  read-write
        STATUS  mandatory
        DESCRIPTION
            "Counter specifying the number of times an MO->MT->AO routed
            message was succesfully submitted as AO/SM after a failed first
            delivery attempt as MT/SM."
        ::= { applicationEntry 362 }

    applicationCntMoMtAoFallbackFailure OBJECT-TYPE
        SYNTAX  Counter
        ACCESS  read-write
        STATUS  mandatory
        DESCRIPTION
            "Counter specifying the number of times an MO->MT->AO routed
            message failed to be submitted as AO/SM after a failed first
            delivery attempt as MT/SM."
        ::= { applicationEntry 363 }

    applicationCntMoMtAoFallbackNotAppliedDueToPermErrorOnPrimary OBJECT-TYPE
        SYNTAX  Counter
        ACCESS  read-write
        STATUS  mandatory
        DESCRIPTION
            "Counter specifying the number of times an MO->MT->AO routed
            message was not attemptd to be submitted as AO/SM because the
            first delivery attempt an MT/SM failed with an error classified
            as 'permanent'."
        ::= { applicationEntry 364 }

    applicationCntMoMtAoFallbackNotAppliedDueToUnavailability OBJECT-TYPE
        SYNTAX  Counter
        ACCESS  read-write
        STATUS  mandatory
        DESCRIPTION
            "Counter specifying the number of times an MO->MT->AO routed
            message was not attempted to be submitted as AO/SM after a
            failed first delivery attempt as MT/SM, because the service
            centre was unavailable."
        ::= { applicationEntry 365 }

    applicationCntMoMtSuccess OBJECT-TYPE
        SYNTAX  Counter
        ACCESS  read-write
        STATUS  mandatory
        DESCRIPTION
            "Counter specifying the number of times an MO->MT routed message
            was succesfully delivered as MT/SM."
        ::= { applicationEntry 366 }

    applicationCntMoMtFailure OBJECT-TYPE
        SYNTAX  Counter
        ACCESS  read-write
        STATUS  mandatory
        DESCRIPTION
            "Counter specifying the number of times an MO->MT routed message
            failed to be delivered as MT/SM."
        ::= { applicationEntry 367 }

    applicationCntAoAtSuccess OBJECT-TYPE
        SYNTAX  Counter
        ACCESS  read-write
        STATUS  mandatory
        DESCRIPTION
            "Counter specifying the number of times an AO->AT routed message
            was succesfully delivered as AT/SM."
        ::= { applicationEntry 368 }

    applicationCntAoAtFailure OBJECT-TYPE
        SYNTAX  Counter
        ACCESS  read-write
        STATUS  mandatory
        DESCRIPTION
            "Counter specifying the number of times an AO->AT routed message
            failed to be delivered as AT/SM."
        ::= { applicationEntry 369 }

    applicationCntAoAtToAmsSuccess OBJECT-TYPE
        SYNTAX  Counter
        ACCESS  read-write
        STATUS  mandatory
        DESCRIPTION
            "Counter specifying the number of times an AO->AMS(as AT) routed
            message was successfully stored in the AMS."
        ::= { applicationEntry 370 }

    applicationCntAoAtToAmsFailure OBJECT-TYPE
        SYNTAX  Counter
        ACCESS  read-write
        STATUS  mandatory
        DESCRIPTION
            "Counter specifying the number of times an AO->AMS(as AT) routed
            message failed to be stored in the AMS."
        ::= { applicationEntry 371 }

    applicationCntAoAtAmsSuccess OBJECT-TYPE
        SYNTAX  Counter
        ACCESS  read-write
        STATUS  mandatory
        DESCRIPTION
            "Counter specifying the number of times an AO->AT->AMS
            routed message was accepted by the AMS for immediate delivery 
            as AT/SM."
        ::= { applicationEntry 372 }

    applicationCntAoAtAmsFailure OBJECT-TYPE
        SYNTAX  Counter
        ACCESS  read-write
        STATUS  mandatory
        DESCRIPTION
            "Counter specifying the number of times an AO->AT->AMS
            routed message failed to be submitted to the AMS for direct
            delivery as AT/SM."
        ::= { applicationEntry 373 }

    -- AO - Store - AO

    applicationCntAoAoToAmsSuccess OBJECT-TYPE
        SYNTAX  Counter
        ACCESS  read-write
        STATUS  mandatory
        DESCRIPTION
            "Counter specifying the number of times an AO->AMS(as AO) routed
            message was successfully stored in the AMS."
        ::= { applicationEntry 374 }

    applicationCntAoAoToAmsFailure OBJECT-TYPE
        SYNTAX  Counter
        ACCESS  read-write
        STATUS  mandatory
        DESCRIPTION
            "Counter specifying the number of times an AO->AMS(as AO) routed
            message failed to be stored in the AMS."
        ::= { applicationEntry 375 }

    -- AO - AO - Store

    applicationCntAoAoAmsPrimarySuccess OBJECT-TYPE
        SYNTAX  Counter
        ACCESS  read-write
        STATUS  mandatory
        DESCRIPTION
            "Counter specifying the number of times an AO->AO->AMS
            routed message was successfully forwarded as AO/SM."
        ::= { applicationEntry 376 }

    applicationCntAoAoAmsPrimaryFailure OBJECT-TYPE
        SYNTAX  Counter
        ACCESS  read-write
        STATUS  mandatory
        DESCRIPTION
            "Counter specifying the number of times an AO->AO->AMS
            routed message failed to be forwarded as AO/SM."
        ::= { applicationEntry 377 }

    applicationCntAoAoAmsFallbackSuccess OBJECT-TYPE
        SYNTAX  Counter
        ACCESS  read-write
        STATUS  mandatory
        DESCRIPTION
            "Counter specifying the number of times an AO->AO->AMS
            routed message was succesfully stored in the AMS after a
            first attempt to forward it as AO/SM."
        ::= { applicationEntry 378 }

    applicationCntAoAoAmsFallbackFailure OBJECT-TYPE
        SYNTAX  Counter
        ACCESS  read-write
        STATUS  mandatory
        DESCRIPTION
            "Counter specifying the number of times an AO->AO->AMS
            routed message failed to be stored in the AMS after a
            first attempt to forward it as AO/SM."
        ::= { applicationEntry 379 }

    applicationCntAoAoAmsFallbackNotAppliedDueToPermErrorOnPrimary OBJECT-TYPE
        SYNTAX  Counter
        ACCESS  read-write
        STATUS  mandatory
        DESCRIPTION
            "Counter specifying the number of times an AO->AO->AMS routed
            message was not attemptd to be stored in the AMS because the
            first attempt to forward it as AO/SM failed with an error
            classified as 'permanent'."
        ::= { applicationEntry 380 }

    applicationCntAoAoAmsFallbackNotAppliedDueToUnavailability OBJECT-TYPE
        SYNTAX  Counter
        ACCESS  read-write
        STATUS  mandatory
        DESCRIPTION
            "Counter specifying the number of times an AO->AO->AMS routed
            message was not attempted to be stored in the AMS after a
            failed first attempt to forward it as AO/SM, because the AMS
            was unavailable."
        ::= { applicationEntry 381 }

    -- AT - Store - AT

    applicationCntAtAtToAmsSuccess OBJECT-TYPE
        SYNTAX  Counter
        ACCESS  read-write
        STATUS  mandatory
        DESCRIPTION
            "Counter specifying the number of times an AT->AMS(as AT) routed
            message was successfully stored in the AMS."
        ::= { applicationEntry 382 }

    applicationCntAtAtToAmsFailure OBJECT-TYPE
        SYNTAX  Counter
        ACCESS  read-write
        STATUS  mandatory
        DESCRIPTION
            "Counter specifying the number of times an AT->AMS(as AT) routed
            message failed to be stored in the AMS."
        ::= { applicationEntry 383 }

    -- AT - AT - Store

    applicationCntAtAtAmsPrimarySuccess OBJECT-TYPE
        SYNTAX  Counter
        ACCESS  read-write
        STATUS  mandatory
        DESCRIPTION
            "Counter specifying the number of times an AT->AT->AMS
            routed message was successfully forwarded as AT/SM."
        ::= { applicationEntry 384 }

    applicationCntAtAtAmsPrimaryFailure OBJECT-TYPE
        SYNTAX  Counter
        ACCESS  read-write
        STATUS  mandatory
        DESCRIPTION
            "Counter specifying the number of times an AT->AT->AMS
            routed message failed to be forwarded as AT/SM."
        ::= { applicationEntry 385 }

    applicationCntAtAtAmsFallbackSuccess OBJECT-TYPE
        SYNTAX  Counter
        ACCESS  read-write
        STATUS  mandatory
        DESCRIPTION
            "Counter specifying the number of times an AT->AT->AMS
            routed message was succesfully stored in the AMS after a
            first attempt to forward it as AT/SM."
        ::= { applicationEntry 386 }

    applicationCntAtAtAmsFallbackFailure OBJECT-TYPE
        SYNTAX  Counter
        ACCESS  read-write
        STATUS  mandatory
        DESCRIPTION
            "Counter specifying the number of times an AT->AT->AMS
            routed message failed to be stored in the AMS after a
            first attempt to forward it as AT/SM."
        ::= { applicationEntry 387 }

    applicationCntAtAtAmsFallbackNotAppliedDueToPermErrorOnPrimary OBJECT-TYPE
        SYNTAX  Counter
        ACCESS  read-write
        STATUS  mandatory
        DESCRIPTION
            "Counter specifying the number of times an AT->AT->AMS routed
            message was not attemptd to be stored in the AMS because the
            first attempt to forward it as AT/SM failed with an error
            classified as 'permanent'."
        ::= { applicationEntry 388 }

    applicationCntAtAtAmsFallbackNotAppliedDueToUnavailability OBJECT-TYPE
        SYNTAX  Counter
        ACCESS  read-write
        STATUS  mandatory
        DESCRIPTION
            "Counter specifying the number of times an AT->AT->AMS routed
            message was not attempted to be stored in the AMS after a
            failed first attempt to forward it as AT/SM, because the AMS
            was unavailable."
        ::= { applicationEntry 389 }

    -- AT - AO

    applicationCntAtAoSuccess OBJECT-TYPE
        SYNTAX  Counter
        ACCESS  read-write
        STATUS  mandatory
        DESCRIPTION
            "Counter specifying the number of times an AT->AO routed
            message was succesfully submitted as AO/SM."
        ::= { applicationEntry 390 }

    applicationCntAtAoFailure OBJECT-TYPE
        SYNTAX  Counter
        ACCESS  read-write
        STATUS  mandatory
        DESCRIPTION
            "Counter specifying the number of times an AT->AO routed
            message failed to be submitted as AO/SM."
        ::= { applicationEntry 391 }

    -- AT - Store - AO

    applicationCntAtAoToAmsSuccess OBJECT-TYPE
        SYNTAX  Counter
        ACCESS  read-write
        STATUS  mandatory
        DESCRIPTION
            "Counter specifying the number of times an AT->AMS(as AO)
            routed message was successfully stored in the AMS."
        ::= { applicationEntry 392 }

    applicationCntAtAoToAmsFailure OBJECT-TYPE
        SYNTAX  Counter
        ACCESS  read-write
        STATUS  mandatory
        DESCRIPTION
            "Counter specifying the number of times an AT->AMS(as AO)
            routed message failed to be stored in the AMS."
        ::= { applicationEntry 393 }

    -- AT - AO - Store

    applicationCntAtAoAmsPrimarySuccess OBJECT-TYPE
        SYNTAX  Counter
        ACCESS  read-write
        STATUS  mandatory
        DESCRIPTION
            "Counter specifying the number of times an AT->AO->AMS
            routed message was successfully forwarded as AO/SM."
        ::= { applicationEntry 394 }

    applicationCntAtAoAmsPrimaryFailure OBJECT-TYPE
        SYNTAX  Counter
        ACCESS  read-write
        STATUS  mandatory
        DESCRIPTION
            "Counter specifying the number of times an AT->AO->AMS
            routed message failed to be forwarded as AO/SM."
        ::= { applicationEntry 395 }

    applicationCntAtAoAmsFallbackSuccess OBJECT-TYPE
        SYNTAX  Counter
        ACCESS  read-write
        STATUS  mandatory
        DESCRIPTION
            "Counter specifying the number of times an AT->AO->AMS
            routed message was succesfully stored in the AMS after a
            first attempt to forward it as AO/SM."
        ::= { applicationEntry 396 }

    applicationCntAtAoAmsFallbackFailure OBJECT-TYPE
        SYNTAX  Counter
        ACCESS  read-write
        STATUS  mandatory
        DESCRIPTION
            "Counter specifying the number of times an AT->AO->AMS
            routed message failed to be stored in the AMS after a
            first attempt to forward it as AO/SM."
        ::= { applicationEntry 397 }

    applicationCntAtAoAmsFallbackNotAppliedDueToPermErrorOnPrimary OBJECT-TYPE
        SYNTAX  Counter
        ACCESS  read-write
        STATUS  mandatory
        DESCRIPTION
            "Counter specifying the number of times an AT->AO->AMS routed
            message was not attemptd to be stored in the AMS because the
            first attempt to forward it as AO/SM failed with an error
            classified as 'permanent'."
        ::= { applicationEntry 398 }

    applicationCntAtAoAmsFallbackNotAppliedDueToUnavailability OBJECT-TYPE
        SYNTAX  Counter
        ACCESS  read-write
        STATUS  mandatory
        DESCRIPTION
            "Counter specifying the number of times an AT->AO->AMS routed
            message was not attempted to be stored in the AMS after a
            failed first attempt to forward it as AO/SM, because the AMS
            was unavailable."
        ::= { applicationEntry 399 }

    applicationCntAoThroughputLimitHit OBJECT-TYPE
        SYNTAX  Counter
        ACCESS  read-write
        STATUS  mandatory
        DESCRIPTION
            "Counter specifying the number of times that the AO throughput
            limit as set for the Application has been hit.
            This counter is only present in the TextPass RTR."
        ::= { applicationEntry 401 }

    applicationCntAtThroughputLimitHit OBJECT-TYPE
        SYNTAX  Counter
        ACCESS  read-write
        STATUS  mandatory
        DESCRIPTION
            "Counter specifying the number of times that the AT throughput
            limit as set for the Application has been hit.
            This counter is only present in the TextPass RTR."
        ::= { applicationEntry 402 }

    applicationCntLongAoMessagesProcessed OBJECT-TYPE
        SYNTAX  Counter
        ACCESS  read-write
        STATUS  mandatory
        DESCRIPTION
            "Counter specifying the number of times that a long AO/SM has 
            been received. A long AO/SM has a payload that is too long to be 
            carried by a single MT/SM.
            This counter is only present in the TextPass RTR."
        ::= { applicationEntry 411 }

    applicationCntAoOriginatorListViolations OBJECT-TYPE
        SYNTAX  Counter
        ACCESS  read-write
        STATUS  mandatory
        DESCRIPTION
            "Counter specifying the number of times that an AO/SM has been
            rejected as a result of the originator specified violating the 
            Application's originator white/black list.
            This counter is only present in the TextPass RTR."
        ::= { applicationEntry 412 }

    applicationCntOutsideAoRejected OBJECT-TYPE
        SYNTAX  Counter
        ACCESS  read-write
        STATUS  mandatory
        DESCRIPTION
            "Counter specifying the total number of times an AO/SM was
            rejected from an Application."
        ::= { applicationEntry 421 }

    applicationCntInsideAtRejected OBJECT-TYPE
        SYNTAX  Counter
        ACCESS  read-write
        STATUS  mandatory
        DESCRIPTION
            "Counter specifying the total number of times an AT/SM was
            rejected from a Service Centre."
        ::= { applicationEntry 422 }
        
    applicationCntAoMtFromAmsSuccess OBJECT-TYPE
        SYNTAX  Counter
        ACCESS  read-write
        STATUS  mandatory
        DESCRIPTION
            "Counter specifying the number of times that a delivery attempt 
            triggered by the AMS for an AO->MT routed message succeeded."
        ::= { applicationEntry 431 }

    applicationCntAoMtFromAmsTemporaryError OBJECT-TYPE 
        SYNTAX  Counter
        ACCESS  read-write
        STATUS  mandatory
        DESCRIPTION
            "Counter specifying the number of times that a delivery attempt 
            triggered by the AMS for an AO->MT routed message failed with a 
            temporary error."
        ::= { applicationEntry 432 }

    applicationCntAoMtFromAmsPermanentRecipientError OBJECT-TYPE
        SYNTAX  Counter
        ACCESS  read-write
        STATUS  mandatory
        DESCRIPTION
            "Counter specifying the number of times that a delivery attempt 
            triggered by the AMS for an AO->MT routed message failed with a 
            permanent recipient error."
        ::= { applicationEntry 433 }

    applicationCntAoMtFromAmsPermanentMessageError OBJECT-TYPE
        SYNTAX  Counter
        ACCESS  read-write
        STATUS  mandatory
        DESCRIPTION
            "Counter specifying the number of times that a delivery attempt 
            triggered by the AMS for an AO->MT routed message failed with a 
            permanent message error."
        ::= { applicationEntry 434 }

    applicationCntAoMtFromAmsExpired OBJECT-TYPE
        SYNTAX  Counter
        ACCESS  read-write
        STATUS  mandatory
        DESCRIPTION
            "Counter specifying the number of times that an AO->MT routed
            message has expired in the AMS."
        ::= { applicationEntry 435 }

    applicationCntAoMtFromAmsDeleted OBJECT-TYPE
        SYNTAX  Counter
        ACCESS  read-write
        STATUS  mandatory
        DESCRIPTION
            "Counter specifying the number of times that an AO->MT routed
            message has been deleted from the AMS."
        ::= { applicationEntry 436 }

    applicationCntAoMtFromAmsReplaced OBJECT-TYPE
        SYNTAX  Counter
        ACCESS  read-write
        STATUS  mandatory
        DESCRIPTION
            "Counter specifying the number of times that an AO->MT routed
            message has been replaced in the AMS."
        ::= { applicationEntry 437 }
    
    applicationCntMoMtFromAmsSuccess OBJECT-TYPE
        SYNTAX  Counter
        ACCESS  read-write
        STATUS  mandatory
        DESCRIPTION
            "Counter specifying the number of times that a delivery attempt 
            triggered by the AMS for an MO->MT routed message succeeded."
        ::= { applicationEntry 441 }

    applicationCntMoMtFromAmsTemporaryError OBJECT-TYPE 
        SYNTAX  Counter
        ACCESS  read-write
        STATUS  mandatory
        DESCRIPTION
            "Counter specifying the number of times that a delivery attempt 
            triggered by the AMS for an MO->MT routed message failed with a 
            temporary error."
        ::= { applicationEntry 442 }

    applicationCntMoMtFromAmsPermanentRecipientError OBJECT-TYPE
        SYNTAX  Counter
        ACCESS  read-write
        STATUS  mandatory
        DESCRIPTION
            "Counter specifying the number of times that a delivery attempt 
            triggered by the AMS for an MO->MT routed message failed with a 
            permanent recipient error."
        ::= { applicationEntry 443 }

    applicationCntMoMtFromAmsPermanentMessageError OBJECT-TYPE
        SYNTAX  Counter
        ACCESS  read-write
        STATUS  mandatory
        DESCRIPTION
            "Counter specifying the number of times that a delivery attempt 
            triggered by the AMS for an MO->MT routed message failed with a 
            permanent message error."
        ::= { applicationEntry 444 }

    applicationCntMoMtFromAmsExpired OBJECT-TYPE
        SYNTAX  Counter
        ACCESS  read-write
        STATUS  mandatory
        DESCRIPTION
            "Counter specifying the number of times that an MO->MT routed
            message has expired in the AMS."
        ::= { applicationEntry 445 }

    applicationCntMoMtFromAmsDeleted OBJECT-TYPE
        SYNTAX  Counter
        ACCESS  read-write
        STATUS  mandatory
        DESCRIPTION
            "Counter specifying the number of times that an MO->MT routed
            message has been deleted from the AMS."
        ::= { applicationEntry 446 }

    applicationCntMoMtFromAmsReplaced OBJECT-TYPE
        SYNTAX  Counter
        ACCESS  read-write
        STATUS  mandatory
        DESCRIPTION
            "Counter specifying the number of times that an MO->MT routed
            message has been replaced in the AMS."
        ::= { applicationEntry 447 }

    applicationCntAoAtFromAmsSuccess OBJECT-TYPE
        SYNTAX  Counter
        ACCESS  read-write
        STATUS  mandatory
        DESCRIPTION
            "Counter specifying the number of times that a delivery attempt 
            triggered by the AMS for an AO->AT routed message succeeded."
        ::= { applicationEntry 451 }

    applicationCntAoAtFromAmsTemporaryError OBJECT-TYPE 
        SYNTAX  Counter
        ACCESS  read-write
        STATUS  mandatory
        DESCRIPTION
            "Counter specifying the number of times that a delivery attempt 
            triggered by the AMS for an AO->AT routed message failed with a 
            temporary error."
        ::= { applicationEntry 452 }

    applicationCntAoAtFromAmsPermanentRecipientError OBJECT-TYPE
        SYNTAX  Counter
        ACCESS  read-write
        STATUS  mandatory
        DESCRIPTION
            "Counter specifying the number of times that a delivery attempt 
            triggered by the AMS for an AO->AT routed message failed with a 
            permanent recipient error."
        ::= { applicationEntry 453 }

    applicationCntAoAtFromAmsPermanentMessageError OBJECT-TYPE
        SYNTAX  Counter
        ACCESS  read-write
        STATUS  mandatory
        DESCRIPTION
            "Counter specifying the number of times that a delivery attempt 
            triggered by the AMS for an AO->AT routed message failed with a 
            permanent message error."
        ::= { applicationEntry 454 }

    applicationCntAoAtFromAmsExpired OBJECT-TYPE
        SYNTAX  Counter
        ACCESS  read-write
        STATUS  mandatory
        DESCRIPTION
            "Counter specifying the number of times that an AO->AT routed
            message has expired in the AMS."
        ::= { applicationEntry 455 }

    applicationCntAoAtFromAmsDeleted OBJECT-TYPE
        SYNTAX  Counter
        ACCESS  read-write
        STATUS  mandatory
        DESCRIPTION
            "Counter specifying the number of times that an AO->AT routed
            message has been deleted from the AMS."
        ::= { applicationEntry 456 }

    applicationCntAoAtFromAmsReplaced OBJECT-TYPE
        SYNTAX  Counter
        ACCESS  read-write
        STATUS  mandatory
        DESCRIPTION
            "Counter specifying the number of times that an AO->AT routed
            message has been replaced in the AMS."
        ::= { applicationEntry 457 }

    -- (AO -) Store - AO

    applicationCntAoAoFromAmsSuccess OBJECT-TYPE
        SYNTAX  Counter
        ACCESS  read-write
        STATUS  mandatory
        DESCRIPTION
            "Counter specifying the number of times that a forward attempt 
            triggered by the AMS for an AO->AO routed message succeeded."
        ::= { applicationEntry 461 }

    applicationCntAoAoFromAmsTemporaryError OBJECT-TYPE 
        SYNTAX  Counter
        ACCESS  read-write
        STATUS  mandatory
        DESCRIPTION
            "Counter specifying the number of times that a forward attempt 
            triggered by the AMS for an AO->AO routed message failed with a 
            temporary error."
        ::= { applicationEntry 462 }

    applicationCntAoAoFromAmsPermanentRecipientError OBJECT-TYPE
        SYNTAX  Counter
        ACCESS  read-write
        STATUS  mandatory
        DESCRIPTION
            "Counter specifying the number of times that a forward attempt 
            triggered by the AMS for an AO->AO routed message failed with a 
            permanent recipient error."
        ::= { applicationEntry 463 }

    applicationCntAoAoFromAmsPermanentMessageError OBJECT-TYPE
        SYNTAX  Counter
        ACCESS  read-write
        STATUS  mandatory
        DESCRIPTION
            "Counter specifying the number of times that a forward attempt 
            triggered by the AMS for an AO->AO routed message failed with a 
            permanent message error."
        ::= { applicationEntry 464 }

    applicationCntAoAoFromAmsExpired OBJECT-TYPE
        SYNTAX  Counter
        ACCESS  read-write
        STATUS  mandatory
        DESCRIPTION
            "Counter specifying the number of times that an AO->AO routed
            message has expired in the AMS."
        ::= { applicationEntry 465 }

    applicationCntAoAoFromAmsDeleted OBJECT-TYPE
        SYNTAX  Counter
        ACCESS  read-write
        STATUS  mandatory
        DESCRIPTION
            "Counter specifying the number of times that an AO->AT routed
            message has been deleted from the AMS."
        ::= { applicationEntry 466 }

    applicationCntAoAoFromAmsReplaced OBJECT-TYPE
        SYNTAX  Counter
        ACCESS  read-write
        STATUS  mandatory
        DESCRIPTION
            "Counter specifying the number of times that an AO->AO routed
            message has been replaced in the AMS."
        ::= { applicationEntry 467 }
    
    -- MO - Store - AT

    applicationCntMoAtFromAmsSuccess OBJECT-TYPE
        SYNTAX  Counter
        ACCESS  read-write
        STATUS  mandatory
        DESCRIPTION
            "Counter specifying the number of times that a delivery attempt 
            triggered by the AMS for an MO->AT/SM succeeded."
        ::= { applicationEntry 471 }

    applicationCntMoAtFromAmsTemporaryError OBJECT-TYPE 
        SYNTAX  Counter
        ACCESS  read-write
        STATUS  mandatory
        DESCRIPTION
            "Counter specifying the number of times that a delivery attempt 
            triggered by the AMS for an MO->AT routed message failed with a 
            temporary error."
        ::= { applicationEntry 472 }

    applicationCntMoAtFromAmsPermanentRecipientError OBJECT-TYPE
        SYNTAX  Counter
        ACCESS  read-write
        STATUS  mandatory
        DESCRIPTION
            "Counter specifying the number of times that a delivery attempt 
            triggered by the AMS for an MO->AT routed message failed with a 
            permanent recipient error."
        ::= { applicationEntry 473 }

    applicationCntMoAtFromAmsPermanentMessageError OBJECT-TYPE
        SYNTAX  Counter
        ACCESS  read-write
        STATUS  mandatory
        DESCRIPTION
            "Counter specifying the number of times that a delivery attempt 
            triggered by the AMS for an MO->AT routed message failed with a 
            permanent message error."
        ::= { applicationEntry 474 }

    applicationCntMoAtFromAmsExpired OBJECT-TYPE
        SYNTAX  Counter
        ACCESS  read-write
        STATUS  mandatory
        DESCRIPTION
            "Counter specifying the number of times that an MO->AT routed
            message has expired in the AMS."
        ::= { applicationEntry 475 }

    applicationCntMoAtFromAmsDeleted OBJECT-TYPE
        SYNTAX  Counter
        ACCESS  read-write
        STATUS  mandatory
        DESCRIPTION
            "Counter specifying the number of times that an MO->AT routed
            message has been deleted from the AMS."
        ::= { applicationEntry 476 }

    applicationCntMoAtFromAmsReplaced OBJECT-TYPE
        SYNTAX  Counter
        ACCESS  read-write
        STATUS  mandatory
        DESCRIPTION
            "Counter specifying the number of times that an MO->AT routed
            message has been replaced in the AMS."
        ::= { applicationEntry 477 }

    -- (AT -) Store - AO

    applicationCntAtAoFromAmsSuccess OBJECT-TYPE
        SYNTAX  Counter
        ACCESS  read-write
        STATUS  mandatory
        DESCRIPTION
            "Counter specifying the number of times that a forward attempt 
            triggered by the AMS for an AT->AO routed message succeeded."
        ::= { applicationEntry 481 }

    applicationCntAtAoFromAmsTemporaryError OBJECT-TYPE 
        SYNTAX  Counter
        ACCESS  read-write
        STATUS  mandatory
        DESCRIPTION
            "Counter specifying the number of times that a forward attempt 
            triggered by the AMS for an AT->AO routed message failed with a 
            temporary error."
        ::= { applicationEntry 482 }

    applicationCntAtAoFromAmsPermanentRecipientError OBJECT-TYPE
        SYNTAX  Counter
        ACCESS  read-write
        STATUS  mandatory
        DESCRIPTION
            "Counter specifying the number of times that a forward attempt 
            triggered by the AMS for an AT->AO routed message failed with a 
            permanent recipient error."
        ::= { applicationEntry 483 }

    applicationCntAtAoFromAmsPermanentMessageError OBJECT-TYPE
        SYNTAX  Counter
        ACCESS  read-write
        STATUS  mandatory
        DESCRIPTION
            "Counter specifying the number of times that a forward attempt 
            triggered by the AMS for an AT->AO routed message failed with a 
            permanent message error."
        ::= { applicationEntry 484 }

    applicationCntAtAoFromAmsExpired OBJECT-TYPE
        SYNTAX  Counter
        ACCESS  read-write
        STATUS  mandatory
        DESCRIPTION
            "Counter specifying the number of times that an AT->AO routed
            message has expired in the AMS."
        ::= { applicationEntry 485 }

    applicationCntAtAoFromAmsDeleted OBJECT-TYPE
        SYNTAX  Counter
        ACCESS  read-write
        STATUS  mandatory
        DESCRIPTION
            "Counter specifying the number of times that an AT->AO routed
            message has been deleted from the AMS."
        ::= { applicationEntry 486 }

    applicationCntAtAoFromAmsReplaced OBJECT-TYPE
        SYNTAX  Counter
        ACCESS  read-write
        STATUS  mandatory
        DESCRIPTION
            "Counter specifying the number of times that an AT->AO routed
            message has been replaced in the AMS."
        ::= { applicationEntry 487 }

    applicationCntAoUcp01Request OBJECT-TYPE
        SYNTAX  Counter
        ACCESS  read-only
        STATUS  mandatory
        DESCRIPTION
            "Counts the number of UCP call input request which were
             received from the specified application"
        ::= { applicationEntry 580 }

    applicationCntAoUcp01Ack OBJECT-TYPE
        SYNTAX  Counter
        ACCESS  read-only
        STATUS  mandatory
        DESCRIPTION
            "Counts the number of positive UCP call input responses
             which were sent to the specified application"
        ::= { applicationEntry 581 }

    applicationCntAoUcp01Nack OBJECT-TYPE
        SYNTAX  Counter
        ACCESS  read-only
        STATUS  mandatory
        DESCRIPTION
            "Counts the number of negative UCP call input responses sent
             to the specified application"
        ::= { applicationEntry 582 }

    applicationCntAoUcp02Request OBJECT-TYPE
        SYNTAX  Counter
        ACCESS  read-only
        STATUS  mandatory
        DESCRIPTION
            "Counts the number of UCP multiple address call input
             request which were received from the specified application"
        ::= { applicationEntry 583 }

    applicationCntAoUcp02Ack OBJECT-TYPE
        SYNTAX  Counter
        ACCESS  read-only
        STATUS  mandatory
        DESCRIPTION
            "Counts the number of positive UCP multiple address call
             input responses which were sent to the specified
             application"
        ::= { applicationEntry 584 }

    applicationCntAoUcp02Nack OBJECT-TYPE
        SYNTAX  Counter
        ACCESS  read-only
        STATUS  mandatory
        DESCRIPTION
            "Counts the number of negative UCP multiple address call
             input responses sent to the specified application"
        ::= { applicationEntry 585 }

    applicationCntAoUcp30Request OBJECT-TYPE
        SYNTAX  Counter
        ACCESS  read-only
        STATUS  mandatory
        DESCRIPTION
            "Counts the number of UCP message transfer requests which were
             received from the specified Application"
        ::= { applicationEntry 595 }

    applicationCntAoUcp30Ack OBJECT-TYPE
        SYNTAX  Counter
        ACCESS  read-only
        STATUS  mandatory
        DESCRIPTION
            "Counts the number of positive UCP message transfer responses 
             which were sent to the specified Application"
        ::= { applicationEntry 596 }

    applicationCntAoUcp30Nack OBJECT-TYPE
        SYNTAX  Counter
        ACCESS  read-only
        STATUS  mandatory
        DESCRIPTION
            "Counts the number of negative UCP message transfer responses 
             sent to the specified Application"
        ::= { applicationEntry 597 }

    applicationCntAoUcp31Request OBJECT-TYPE
        SYNTAX  Counter
        ACCESS  read-only
        STATUS  mandatory
        DESCRIPTION
            "Counts the number of UCP alert requests which were received
             from the specified Application"
        ::= { applicationEntry 600 }

    applicationCntAoUcp31Ack OBJECT-TYPE
        SYNTAX  Counter
        ACCESS  read-only
        STATUS  mandatory
        DESCRIPTION
            "Counts the number of positive UCP alert responses which
             were sent to the specified Application"
        ::= { applicationEntry 601 }

    applicationCntAoUcp31Nack OBJECT-TYPE
        SYNTAX  Counter
        ACCESS  read-only
        STATUS  mandatory
        DESCRIPTION
            "Counts the number of negative UCP alert responses sent to
             the specified Application"
        ::= { applicationEntry 602 }

    applicationCntAoUcp51Request OBJECT-TYPE
        SYNTAX  Counter
        ACCESS  read-only
        STATUS  mandatory
        DESCRIPTION
            "Counts the number of UCP submit sm requests which were
             received from the specified Application"
        ::= { applicationEntry 603 }

    applicationCntAoUcp51Ack OBJECT-TYPE
        SYNTAX  Counter
        ACCESS  read-only
        STATUS  mandatory
        DESCRIPTION
            "Counts the number of positive UCP submit sm responses which
             were sent to the specified Application"
        ::= { applicationEntry 604 }

    applicationCntAoUcp51Nack OBJECT-TYPE
        SYNTAX  Counter
        ACCESS  read-only
        STATUS  mandatory
        DESCRIPTION
            "Counts the number of negative UCP submit sm responses sent
             to the specified Application"
        ::= { applicationEntry 605 }

    applicationCntAoUcp54Request OBJECT-TYPE
        SYNTAX  Counter
        ACCESS  read-only
        STATUS  mandatory
        DESCRIPTION
            "Counts the number of UCP modify message requests which were
             received from the specified Application"
        ::= { applicationEntry 606 }

    applicationCntAoUcp54Ack OBJECT-TYPE
        SYNTAX  Counter
        ACCESS  read-only
        STATUS  mandatory
        DESCRIPTION
            "Counts the number of positive UCP modify message responses
             which were sent to the specified Application"
        ::= { applicationEntry 607 }

    applicationCntAoUcp54Nack OBJECT-TYPE
        SYNTAX  Counter
        ACCESS  read-only
        STATUS  mandatory
        DESCRIPTION
            "Counts the number of negative UCP modify message responses
             sent to the specified Application"
        ::= { applicationEntry 608 }

    applicationCntAoUcp60Request OBJECT-TYPE
        SYNTAX  Counter
        ACCESS  read-only
        STATUS  mandatory
        DESCRIPTION
            "Counts the number of UCP session management requests which
             were received from the specified application"
        ::= { applicationEntry 609 }

    applicationCntAoUcp60Ack OBJECT-TYPE
        SYNTAX  Counter
        ACCESS  read-only
        STATUS  mandatory
        DESCRIPTION
            "Counts the number of positive UCP session management
             responses which were sent to the specified Application"
        ::= { applicationEntry 610 }

    applicationCntAoUcp60Nack OBJECT-TYPE
        SYNTAX  Counter
        ACCESS  read-only
        STATUS  mandatory
        DESCRIPTION
            "Counts the number of negative UCP session management
             responses which were sent to the specified application"
        ::= { applicationEntry 611 }

    applicationCntAoUcpOtherRequest OBJECT-TYPE
        SYNTAX  Counter
        ACCESS  read-only
        STATUS  mandatory
        DESCRIPTION
            "Counts the number of unknown UCP requests which were
             received from the specified application"
        ::= { applicationEntry 612 }

    applicationCntAoUcpOtherAck OBJECT-TYPE
        SYNTAX  Counter
        ACCESS  read-only
        STATUS  mandatory
        DESCRIPTION
            "Counts the number of positive unknown UCP responses which
             were sent to the specified application"
        ::= { applicationEntry 613 }

    applicationCntAoUcpOtherNack OBJECT-TYPE
        SYNTAX  Counter
        ACCESS  read-only
        STATUS  mandatory
        DESCRIPTION
            "Counts the number of negative unknown UCP responses sent to
             the specified application"
        ::= { applicationEntry 614 }

    applicationCntAtUcp52Request OBJECT-TYPE
        SYNTAX  Counter
        ACCESS  read-only
        STATUS  mandatory
        DESCRIPTION
            "Counts the number of UCP deliver sm request which were sent
             to the specified application"
        ::= { applicationEntry 615 }

    applicationCntAtUcp52Ack OBJECT-TYPE
        SYNTAX  Counter
        ACCESS  read-only
        STATUS  mandatory
        DESCRIPTION
            "Counts the number of positive UCP deliver sm responses
             received from the specified application"
        ::= { applicationEntry 616 }

    applicationCntAtUcp52Nack OBJECT-TYPE
        SYNTAX  Counter
        ACCESS  read-only
        STATUS  mandatory
        DESCRIPTION
            "Counts the number of negative UCP deliver sm responses
             received from the specified application"
        ::= { applicationEntry 617 }

    applicationCntAtUcp53Request OBJECT-TYPE
        SYNTAX  Counter
        ACCESS  read-only
        STATUS  mandatory
        DESCRIPTION
            "Counts the number of UCP deliver notify requests which were
             sent to the specified application"
        ::= { applicationEntry 618 }

    applicationCntAtUcp53Ack OBJECT-TYPE
        SYNTAX  Counter
        ACCESS  read-only
        STATUS  mandatory
        DESCRIPTION
            "Counts the number of positive UCP deliver notify responses
             received from the specified application"
        ::= { applicationEntry 619 }

    applicationCntAtUcp53Nack OBJECT-TYPE
        SYNTAX  Counter
        ACCESS  read-only
        STATUS  mandatory
        DESCRIPTION
            "Counts the number of negative UCP deliver notify responses
             received from the specified application"
        ::= { applicationEntry 620 }

    applicationCntAtUcpOtherRequest OBJECT-TYPE
        SYNTAX  Counter
        ACCESS  read-only
        STATUS  mandatory
        DESCRIPTION
            "Counts the number of unknown UCP request which were sent to
             the specified application"
        ::= { applicationEntry 621 }

    applicationCntAtUcpOtherAck OBJECT-TYPE
        SYNTAX  Counter
        ACCESS  read-only
        STATUS  mandatory
        DESCRIPTION
            "Counts the number of positive unknown UCP responses
             received from the specified application"
        ::= { applicationEntry 622 }

    applicationCntAtUcpOtherNack OBJECT-TYPE
        SYNTAX  Counter
        ACCESS  read-only
        STATUS  mandatory
        DESCRIPTION
            "Counts the number of negative unknown UCP responses
             received from the specified application"
        ::= { applicationEntry 623 }

    applicationCntAtUcp01Request OBJECT-TYPE
        SYNTAX  Counter
        ACCESS  read-only
        STATUS  mandatory
        DESCRIPTION
            "Counts the number of UCP call input requests which were sent
             to the specified application"
        ::= { applicationEntry 624 }

    applicationCntAtUcp01Ack OBJECT-TYPE
        SYNTAX  Counter
        ACCESS  read-only
        STATUS  mandatory
        DESCRIPTION
            "Counts the number of positive UCP call input responses
             received from the specified application"
        ::= { applicationEntry 625 }

    applicationCntAtUcp01Nack OBJECT-TYPE
        SYNTAX  Counter
        ACCESS  read-only
        STATUS  mandatory
        DESCRIPTION
            "Counts the number of negative UCP call input responses
             received from the specified application"
        ::= { applicationEntry 626 }

    applicationCntAoUcp55Request OBJECT-TYPE
        SYNTAX  Counter
        ACCESS  read-only
        STATUS  mandatory
        DESCRIPTION
            "Counts the number of UCP inquiry message requests which
             were received from the specified application"
        ::= { applicationEntry 627 }

    applicationCntAoUcp55Ack OBJECT-TYPE
        SYNTAX  Counter
        ACCESS  read-only
        STATUS  mandatory
        DESCRIPTION
            "Counts the number of positive UCP inquiry message responses
             which were sent to the specified Application"
        ::= { applicationEntry 628 }

    applicationCntAoUcp55Nack OBJECT-TYPE
        SYNTAX  Counter
        ACCESS  read-only
        STATUS  mandatory
        DESCRIPTION
            "Counts the number of negative UCP inquiry message responses
             which were sent to the specified application"
        ::= { applicationEntry 629 }

    applicationCntAoUcp56Request OBJECT-TYPE
        SYNTAX  Counter
        ACCESS  read-only
        STATUS  mandatory
        DESCRIPTION
            "Counts the number of UCP session delete message which were
             received from the specified application"
        ::= { applicationEntry 630 }

    applicationCntAoUcp56Ack OBJECT-TYPE
        SYNTAX  Counter
        ACCESS  read-only
        STATUS  mandatory
        DESCRIPTION
            "Counts the number of positive UCP delete message responses
             which were sent to the specified Application"
        ::= { applicationEntry 631 }

    applicationCntAoUcp56Nack OBJECT-TYPE
        SYNTAX  Counter
        ACCESS  read-only
        STATUS  mandatory
        DESCRIPTION
            "Counts the number of negative UCP delete message responses
             which were sent to the specified application"
        ::= { applicationEntry 632 }

    applicationCntAtUcp57Request OBJECT-TYPE
        SYNTAX  Counter
        ACCESS  read-only
        STATUS  mandatory
        DESCRIPTION
            "Counts the number of UCP response inquiry message requests
             which were sent to the specified application"
        ::= { applicationEntry 633 }

    applicationCntAtUcp57Ack OBJECT-TYPE
        SYNTAX  Counter
        ACCESS  read-only
        STATUS  mandatory
        DESCRIPTION
            "Counts the number of positive UCP response inquiry message
             responses received from the specified application"
        ::= { applicationEntry 634 }

    applicationCntAtUcp57Nack OBJECT-TYPE
        SYNTAX  Counter
        ACCESS  read-only
        STATUS  mandatory
        DESCRIPTION
            "Counts the number of negative UCP response inquiry message
             responses received from the specified application"
        ::= { applicationEntry 635 }

    applicationCntAtUcp58Request OBJECT-TYPE
        SYNTAX  Counter
        ACCESS  read-only
        STATUS  mandatory
        DESCRIPTION
            "Counts the number of UCP response delete message requests
             which were sent to the specified application"
        ::= { applicationEntry 636 }

    applicationCntAtUcp58Ack OBJECT-TYPE
        SYNTAX  Counter
        ACCESS  read-only
        STATUS  mandatory
        DESCRIPTION
            "Counts the number of positive UCP response delete message
             responses received from the specified application"
        ::= { applicationEntry 637 }

    applicationCntAtUcp58Nack OBJECT-TYPE
        SYNTAX  Counter
        ACCESS  read-only
        STATUS  mandatory
        DESCRIPTION
            "Counts the number of negative UCP response delete message
             responses received from the specified application"
        ::= { applicationEntry 638 }

    applicationCntAoSmppSubmitSmRequest OBJECT-TYPE
        SYNTAX  Counter
        ACCESS  read-only
        STATUS  mandatory
        DESCRIPTION
            "Counts the number of SMPP submit sm requests which were
             received from the specified application"
        ::= { applicationEntry 650 }

    applicationCntAoSmppSubmitSmAck OBJECT-TYPE
        SYNTAX  Counter
        ACCESS  read-only
        STATUS  mandatory
        DESCRIPTION
            "Counts the number of positive SSMPP submit sm responses
             which were sent to the specified application"
        ::= { applicationEntry 651 }

    applicationCntAoSmppSubmitSmNack OBJECT-TYPE
        SYNTAX  Counter
        ACCESS  read-only
        STATUS  mandatory
        DESCRIPTION
            "Counts the number of negative SMPP submit sm responses sent
             to the specified application"
        ::= { applicationEntry 652 }

    applicationCntAoSmppDataSmRequest OBJECT-TYPE
        SYNTAX  Counter
        ACCESS  read-only
        STATUS  mandatory
        DESCRIPTION
            "Counts the number of SMPP data request which were received
             from the specified application"
        ::= { applicationEntry 653 }

    applicationCntAoSmppDataSmAck OBJECT-TYPE
        SYNTAX  Counter
        ACCESS  read-only
        STATUS  mandatory
        DESCRIPTION
            "Counts the number of positive SMPP data responses which
             were sent to the specified application"
        ::= { applicationEntry 654 }

    applicationCntAoSmppDataSmNack OBJECT-TYPE
        SYNTAX  Counter
        ACCESS  read-only
        STATUS  mandatory
        DESCRIPTION
            "Counts the number of negative SMPP data responses sent to
             the specified application"
        ::= { applicationEntry 655 }

    applicationCntAoSmppBindRxRequest OBJECT-TYPE
        SYNTAX  Counter
        ACCESS  read-only
        STATUS  mandatory
        DESCRIPTION
            "Counts the number of SMPP bind receiver requests which were
             received from the specified application"
        ::= { applicationEntry 656 }

    applicationCntAoSmppBindRxAck OBJECT-TYPE
        SYNTAX  Counter
        ACCESS  read-only
        STATUS  mandatory
        DESCRIPTION
            "Counts the number of positive SMPP bind receiver responses
             which were sent to the specified application"
        ::= { applicationEntry 657 }

    applicationCntAoSmppBindRxNack OBJECT-TYPE
        SYNTAX  Counter
        ACCESS  read-only
        STATUS  mandatory
        DESCRIPTION
            "Counts the number of negative SMPP bind receiver responses
             which were sent to the specified application"
        ::= { applicationEntry 658 }

    applicationCntAoSmppBindTxRequest OBJECT-TYPE
        SYNTAX  Counter
        ACCESS  read-only
        STATUS  mandatory
        DESCRIPTION
            "Counts the number of SMPP bind transmitter requests which
             were received from the specified application"
        ::= { applicationEntry 659 }

    applicationCntAoSmppBindTxAck OBJECT-TYPE
        SYNTAX  Counter
        ACCESS  read-only
        STATUS  mandatory
        DESCRIPTION
            "Counts the number of positive SMPP bind transmitter
             responses which were sent to the specified application"
        ::= { applicationEntry 660 }

    applicationCntAoSmppBindTxNack OBJECT-TYPE
        SYNTAX  Counter
        ACCESS  read-only
        STATUS  mandatory
        DESCRIPTION
            "Counts the number of negative SMPP bind transmitter
             responses which were sent to the specified application"
        ::= { applicationEntry 661 }

    applicationCntAoSmppBindTrxRequest OBJECT-TYPE
        SYNTAX  Counter
        ACCESS  read-only
        STATUS  mandatory
        DESCRIPTION
            "Counts the number of SMPP bind transceiver requests which
             were received from the specified application"
        ::= { applicationEntry 662 }

    applicationCntAoSmppBindTrxAck OBJECT-TYPE
        SYNTAX  Counter
        ACCESS  read-only
        STATUS  mandatory
        DESCRIPTION
            "Counts the number of positive SMPP bind transceiver
             responses which were sent to the specified application"
        ::= { applicationEntry 663 }

    applicationCntAoSmppBindTrxNack OBJECT-TYPE
        SYNTAX  Counter
        ACCESS  read-only
        STATUS  mandatory
        DESCRIPTION
            "Counts the number of negative SMPP bind transceiver
             responses which were sent to the specified application"
        ::= { applicationEntry 664 }

    applicationCntAoSmppUnbindRequest OBJECT-TYPE
        SYNTAX  Counter
        ACCESS  read-only
        STATUS  mandatory
        DESCRIPTION
            "Counts the number of SMPP unbind requests which were
             received from the specified application"
        ::= { applicationEntry 665 }

    applicationCntAoSmppUnbindAck OBJECT-TYPE
        SYNTAX  Counter
        ACCESS  read-only
        STATUS  mandatory
        DESCRIPTION
            "Counts the number of positive SMPP unbind responses which
             were sent to the specified application"
        ::= { applicationEntry 666 }

    applicationCntAoSmppUnbindNack OBJECT-TYPE
        SYNTAX  Counter
        ACCESS  read-only
        STATUS  mandatory
        DESCRIPTION
            "Counts the number of negative SMPP unbind responses sent to
             the specified application"
        ::= { applicationEntry 667 }

    applicationCntAoSmppQuerySmRequest OBJECT-TYPE
        SYNTAX  Counter
        ACCESS  read-only
        STATUS  mandatory
        DESCRIPTION
            "Counts the number of SMPP query sm requests which were
             received from the specified application"
        ::= { applicationEntry 668 }

    applicationCntAoSmppQuerySmAck OBJECT-TYPE
        SYNTAX  Counter
        ACCESS  read-only
        STATUS  mandatory
        DESCRIPTION
            "Counts the number of positive SMPP query sm responses which
             were sent to the specified application"
        ::= { applicationEntry 669 }

    applicationCntAoSmppQuerySmNack OBJECT-TYPE
        SYNTAX  Counter
        ACCESS  read-only
        STATUS  mandatory
        DESCRIPTION
            "Counts the number of negative SMPP query sm responses sent
             to the specified application"
        ::= { applicationEntry 670 }

    applicationCntAoSmppCancelSmRequest OBJECT-TYPE
        SYNTAX  Counter
        ACCESS  read-only
        STATUS  mandatory
        DESCRIPTION
            "Counts the number of SMPP cancel sm requests which were
             received from the specified application"
        ::= { applicationEntry 671 }

    applicationCntAoSmppCancelSmAck OBJECT-TYPE
        SYNTAX  Counter
        ACCESS  read-only
        STATUS  mandatory
        DESCRIPTION
            "Counts the number of positive SMPP cancel sm responses
             which were sent to the specified application"
        ::= { applicationEntry 672 }

    applicationCntAoSmppCancelSmNack OBJECT-TYPE
        SYNTAX  Counter
        ACCESS  read-only
        STATUS  mandatory
        DESCRIPTION
            "Counts the number of negative SMPP cancel sm responses sent
             to the specified application"
        ::= { applicationEntry 673 }

    applicationCntAoSmppReplaceSmRequest OBJECT-TYPE
        SYNTAX  Counter
        ACCESS  read-only
        STATUS  mandatory
        DESCRIPTION
            "Counts the number of SMPP replace sm requests which were
             received from the specified application"
        ::= { applicationEntry 674 }

    applicationCntAoSmppReplaceSmAck OBJECT-TYPE
        SYNTAX  Counter
        ACCESS  read-only
        STATUS  mandatory
        DESCRIPTION
            "Counts the number of positive SMPP replace sm responses
             which were sent to the specified application"
        ::= { applicationEntry 675 }

    applicationCntAoSmppReplaceSmNack OBJECT-TYPE
        SYNTAX  Counter
        ACCESS  read-only
        STATUS  mandatory
        DESCRIPTION
            "Counts the number of negative SMPP replace sm responses
             sent to the specified application"
        ::= { applicationEntry 676 }

    applicationCntAoSmppEnquireLinkRequest OBJECT-TYPE
        SYNTAX  Counter
        ACCESS  read-only
        STATUS  mandatory
        DESCRIPTION
            "Counts the number of SMPP enquire link requests which were
             received from the specified application"
        ::= { applicationEntry 677 }

    applicationCntAoSmppEnquireLinkAck OBJECT-TYPE
        SYNTAX  Counter
        ACCESS  read-only
        STATUS  mandatory
        DESCRIPTION
            "Counts the number of positive SMPP enquire link responses
             which were sent to the specified application"
        ::= { applicationEntry 678 }

    applicationCntAoSmppEnquireLinkNack OBJECT-TYPE
        SYNTAX  Counter
        ACCESS  read-only
        STATUS  mandatory
        DESCRIPTION
            "Counts the number of negative SMPP enquire link responses
             sent to the specified application"
        ::= { applicationEntry 679 }

    applicationCntAoSmppGenericNack OBJECT-TYPE
        SYNTAX  Counter
        ACCESS  read-only
        STATUS  mandatory
        DESCRIPTION
            "Counts the number of generic negative responses sent to the
             specified application"
        ::= { applicationEntry 680 }

    applicationCntAoSmppOtherRequest OBJECT-TYPE
        SYNTAX  Counter
        ACCESS  read-only
        STATUS  mandatory
        DESCRIPTION
            "Counts the number of unknown SMPP requests which were
             received from the specified application"
        ::= { applicationEntry 681 }

    applicationCntAoSmppOtherAck OBJECT-TYPE
        SYNTAX  Counter
        ACCESS  read-only
        STATUS  mandatory
        DESCRIPTION
            "Counts the number of positive unknown SMPP responses which
             were sent to the specified application"
        ::= { applicationEntry 682 }

    applicationCntAoSmppOtherNack OBJECT-TYPE
        SYNTAX  Counter
        ACCESS  read-only
        STATUS  mandatory
        DESCRIPTION
            "Counts the number of negative unknown SMPP responses sent
             to the specified application"
        ::= { applicationEntry 683 }

    applicationCntAtSmppDeliverSmRequest OBJECT-TYPE
        SYNTAX  Counter
        ACCESS  read-only
        STATUS  mandatory
        DESCRIPTION
            "Counts the number of SMPP deliver sm requests which were
             sent to the specified application"
        ::= { applicationEntry 684 }

    applicationCntAtSmppDeliverSmAck OBJECT-TYPE
        SYNTAX  Counter
        ACCESS  read-only
        STATUS  mandatory
        DESCRIPTION
            "Counts the number of positive SMPP deliver sm responses
             received from the specified application"
        ::= { applicationEntry 685 }

    applicationCntAtSmppDeliverSmNack OBJECT-TYPE
        SYNTAX  Counter
        ACCESS  read-only
        STATUS  mandatory
        DESCRIPTION
            "Counts the number of negative SMPP deliver sm responses
             received from the specified application"
        ::= { applicationEntry 686 }

    applicationCntAtSmppDataSmRequest OBJECT-TYPE
        SYNTAX  Counter
        ACCESS  read-only
        STATUS  mandatory
        DESCRIPTION
            "Counts the number of SMPP data sm requests which were sent
             to the specified application"
        ::= { applicationEntry 687 }

    applicationCntAtSmppDataSmAck OBJECT-TYPE
        SYNTAX  Counter
        ACCESS  read-only
        STATUS  mandatory
        DESCRIPTION
            "Counts the number of positive SMPP data sm responses
             received from the specified application"
        ::= { applicationEntry 688 }

    applicationCntAtSmppDataSmNack OBJECT-TYPE
        SYNTAX  Counter
        ACCESS  read-only
        STATUS  mandatory
        DESCRIPTION
            "Counts the number of negative SMPP data sm responses
             received from the specified application"
        ::= { applicationEntry 689 }

    applicationCntAtSmppGenericNack OBJECT-TYPE
        SYNTAX  Counter
        ACCESS  read-only
        STATUS  mandatory
        DESCRIPTION
            "Counts the number of generic SMPP negative responses
             received from the specified application"
        ::= { applicationEntry 690 }

    applicationCntAtSmppOtherRequest OBJECT-TYPE
        SYNTAX  Counter
        ACCESS  read-only
        STATUS  mandatory
        DESCRIPTION
            "Counts the number of unknown SMPP requests which were sent
             to the specified application"
        ::= { applicationEntry 691 }

    applicationCntAtSmppOtherAck OBJECT-TYPE
        SYNTAX  Counter
        ACCESS  read-only
        STATUS  mandatory
        DESCRIPTION
            "Counts the number of positive unknown SMPP responses
             received from the specified application"
        ::= { applicationEntry 692 }

    applicationCntAtSmppOtherNack OBJECT-TYPE
        SYNTAX  Counter
        ACCESS  read-only
        STATUS  mandatory
        DESCRIPTION
            "Counts the number of negative unknown SMPP responses
             received from the specified application"
        ::= { applicationEntry 693 }

    applicationCntAoCimdLoginRequest OBJECT-TYPE
        SYNTAX  Counter
        ACCESS  read-only
        STATUS  mandatory
        DESCRIPTION
            "Counts the number of CIMD login requests which were received
             from the specified application"
        ::= { applicationEntry 700 }

    applicationCntAoCimdLoginAck OBJECT-TYPE
        SYNTAX  Counter
        ACCESS  read-only
        STATUS  mandatory
        DESCRIPTION
            "Counts the number of positive CIMD login responses which
             were sent to the specified application"
        ::= { applicationEntry 701 }

    applicationCntAoCimdLoginNack OBJECT-TYPE
        SYNTAX  Counter
        ACCESS  read-only
        STATUS  mandatory
        DESCRIPTION
            "Counts the number of negative CIMD login responses which
             were sent to the specified application"
        ::= { applicationEntry 702 }

    applicationCntAoCimdLogoutRequest OBJECT-TYPE
        SYNTAX  Counter
        ACCESS  read-only
        STATUS  mandatory
        DESCRIPTION
            "Counts the number of CIMD logout requests which were
             received from the specified application"
        ::= { applicationEntry 703 }

    applicationCntAoCimdLogoutAck OBJECT-TYPE
        SYNTAX  Counter
        ACCESS  read-only
        STATUS  mandatory
        DESCRIPTION
            "Counts the number of positive CIMD logout responses which
             were sent to the specified application"
        ::= { applicationEntry 704 }

    applicationCntAoCimdLogoutNack OBJECT-TYPE
        SYNTAX  Counter
        ACCESS  read-only
        STATUS  mandatory
        DESCRIPTION
            "Counts the number of negative CIMD logout responses sent to
             the specified application"
        ::= { applicationEntry 705 }

    applicationCntAoCimdSubmitRequest OBJECT-TYPE
        SYNTAX  Counter
        ACCESS  read-only
        STATUS  mandatory
        DESCRIPTION
            "Counts the number of CIMD submit message requests which were
             received from the specified application"
        ::= { applicationEntry 706 }

    applicationCntAoCimdSubmitAck OBJECT-TYPE
        SYNTAX  Counter
        ACCESS  read-only
        STATUS  mandatory
        DESCRIPTION
            "Counts the number of positive CIMD submit message responses
             which were sent to the specified application"
        ::= { applicationEntry 707 }

    applicationCntAoCimdSubmitNack OBJECT-TYPE
        SYNTAX  Counter
        ACCESS  read-only
        STATUS  mandatory
        DESCRIPTION
            "Counts the number of negative CIMD submit message responses
             sent to the specified application"
        ::= { applicationEntry 708 }

    applicationCntAoCimdEnquireRequest OBJECT-TYPE
        SYNTAX  Counter
        ACCESS  read-only
        STATUS  mandatory
        DESCRIPTION
            "Counts the number of CIMD enquire message status requests
             which were received from the specified application"
        ::= { applicationEntry 709 }

    applicationCntAoCimdEnquireAck OBJECT-TYPE
        SYNTAX  Counter
        ACCESS  read-only
        STATUS  mandatory
        DESCRIPTION
            "Counts the number of positive CIMD enquire message status
             responses which were sent to the specified application"
        ::= { applicationEntry 710 }

    applicationCntAoCimdEnquireNack OBJECT-TYPE
        SYNTAX  Counter
        ACCESS  read-only
        STATUS  mandatory
        DESCRIPTION
            "Counts the number of negative CIMD enquire message status
             responses sent to the specified application"
        ::= { applicationEntry 711 }

    applicationCntAoCimdOtherRequest OBJECT-TYPE
        SYNTAX  Counter
        ACCESS  read-only
        STATUS  mandatory
        DESCRIPTION
            "Counts the number of unknown CIMD requests which were
             received from the specified application"
        ::= { applicationEntry 712 }

    applicationCntAoCimdOtherAck OBJECT-TYPE
        SYNTAX  Counter
        ACCESS  read-only
        STATUS  mandatory
        DESCRIPTION
            "Counts the number of positive unknown CIMD responses which
             were sent to the specified application"
        ::= { applicationEntry 713 }

    applicationCntAoCimdOtherNack OBJECT-TYPE
        SYNTAX  Counter
        ACCESS  read-only
        STATUS  mandatory
        DESCRIPTION
            "Counts the number of negative unknown CIMD responses sent
             to the specified application"
        ::= { applicationEntry 714 }

    applicationCntAtCimdDeliverRequest OBJECT-TYPE
        SYNTAX  Counter
        ACCESS  read-only
        STATUS  mandatory
        DESCRIPTION
            "Counts the number of CIMD deliver message requests which
             were sent to the specified application"
        ::= { applicationEntry 715 }

    applicationCntAtCimdDeliverAck OBJECT-TYPE
        SYNTAX  Counter
        ACCESS  read-only
        STATUS  mandatory
        DESCRIPTION
            "Counts the number of positive CIMD deliver message
             responses received from the specified application"
        ::= { applicationEntry 716 }

    applicationCntAtCimdDeliverNack OBJECT-TYPE
        SYNTAX  Counter
        ACCESS  read-only
        STATUS  mandatory
        DESCRIPTION
            "Counts the number of negative CIMD deliver message
             responses received from the specified application"
        ::= { applicationEntry 717 }

    applicationCntAtCimdDeliverStatusRequest OBJECT-TYPE
        SYNTAX  Counter
        ACCESS  read-only
        STATUS  mandatory
        DESCRIPTION
            "Counts the number of CIMD deliver status report requests
             which were sent to the specified application"
        ::= { applicationEntry 718 }

    applicationCntAtCimdDeliverStatusAck OBJECT-TYPE
        SYNTAX  Counter
        ACCESS  read-only
        STATUS  mandatory
        DESCRIPTION
            "Counts the number of positive CIMD deliver status report
             responses received from the specified application"
        ::= { applicationEntry 719 }

    applicationCntAtCimdDeliverStatusNack OBJECT-TYPE
        SYNTAX  Counter
        ACCESS  read-only
        STATUS  mandatory
        DESCRIPTION
            "Counts the number of negative CIMD deliver status report
             responses received from the specified application"
        ::= { applicationEntry 720 }

    applicationCntAtCimdAliveRequest OBJECT-TYPE
        SYNTAX  Counter
        ACCESS  read-only
        STATUS  mandatory
        DESCRIPTION
            "Counts the number of CIMD alive message requests which were
             sent to the specified application"
        ::= { applicationEntry 721 }

    applicationCntAtCimdAliveAck OBJECT-TYPE
        SYNTAX  Counter
        ACCESS  read-only
        STATUS  mandatory
        DESCRIPTION
            "Counts the number of positive CIMD alive message responses
             received from the specified application"
        ::= { applicationEntry 722 }

    applicationCntAtCimdAliveNack OBJECT-TYPE
        SYNTAX  Counter
        ACCESS  read-only
        STATUS  mandatory
        DESCRIPTION
            "Counts the number of negative CIMD alive message responses
             received from the specified application"
        ::= { applicationEntry 723 }

    applicationCntAtCimdOtherRequest OBJECT-TYPE
        SYNTAX  Counter
        ACCESS  read-only
        STATUS  mandatory
        DESCRIPTION
            "Counts the number of unknown CIMD requests which were sent
             to the specified application"
        ::= { applicationEntry 724 }

    applicationCntAtCimdOtherAck OBJECT-TYPE
        SYNTAX  Counter
        ACCESS  read-only
        STATUS  mandatory
        DESCRIPTION
            "Counts the number of positive unknown CIMD responses
             received from the specified application"
        ::= { applicationEntry 725 }

    applicationCntAtCimdOtherNack OBJECT-TYPE
        SYNTAX  Counter
        ACCESS  read-only
        STATUS  mandatory
        DESCRIPTION
            "Counts the number of negative unknown CIMD responses
             received from the specified application"
        ::= { applicationEntry 726 }

    applicationOriginatorReplacementEnabled OBJECT-TYPE
        SYNTAX  Boolean
        ACCESS  read-write
        STATUS  mandatory
        DESCRIPTION
            "Switch to turn the per-application originator replacement
            functionality on or off. By default, this functionality is
            disabled (false)."
        ::= { applicationEntry 801 }

    applicationOriginatorReplacementAddress OBJECT-TYPE
        SYNTAX  AddressString
        ACCESS  read-write
        STATUS  mandatory
        DESCRIPTION
            "This object specifies the value to be used for replacing
            the originator address of an AO message. If no value is specified
            (default), the application's short number is used instead.
            This object has no effect while the originator replacement
            functionality is turned off.
            Note: When specifying alphanumeric addresses, care must be taken
            that the alphabet used to encode the address can actually
            represent the provisioned characters."
        ::= { applicationEntry 802 }

    -- OID 704 used to be the applicationRecipientShortNumberList.

    applicationAmsQueueForDialoutNotifications OBJECT-TYPE
        SYNTAX  AmsQueueIndex
        ACCESS  read-write
        STATUS  mandatory
        DESCRIPTION
            "Index specifying the AMS queue for storing a Dialout
            Notification. When set to 0 (default), the router's global
            configuration specifies the AMS queue."
        ::= { applicationEntry 804 }

    applicationTcpKeepAlive OBJECT-TYPE
        SYNTAX  Boolean
        ACCESS  read-write
        STATUS  mandatory
        DESCRIPTION
            "Controls the TCP Keep-Alive functionality on connections from 
            this application. When enabled the functionality will be activated 
            for connections started thereafter. That means, for the newer 
            outside sessions, it will enable the TCP Keep-Alive functionality 
            on all successfully authenticated sessions. For the inside 
            sessions and outside dial-out sessions the feature will be enabled 
            as soon as the connection is started. When disabled the feature 
            will be disabled on all newer connections.
            Default: FALSE."
        ::= { applicationEntry 805 }
        
    applicationOriginatorChargingUnitsValid OBJECT-TYPE
        SYNTAX  Boolean
        ACCESS  read-write
        STATUS  mandatory
        DESCRIPTION
            "Flag defining whether or not the value specified by the
            applicationOriginatorChargingUnits field is valid or not.
            By default, the field is not valid."
        ::= { applicationEntry 806 }

    applicationRecipientChargingUnitsValid OBJECT-TYPE
        SYNTAX  Boolean
        ACCESS  read-write
        STATUS  mandatory
        DESCRIPTION
            "Flag defining whether or not the value specified by the
            applicationRecipientChargingUnits field is valid or not.
            By default, the field is not valid."
        ::= { applicationEntry 807 }

    applicationOriginatorChargingUnits OBJECT-TYPE
        SYNTAX  ChargingUnits
        ACCESS  read-write
        STATUS  mandatory
        DESCRIPTION
            "An integer number of units associated with the charging of
            AO messages originated on this application. By default, the
            value is set to 0."
        ::= { applicationEntry 808 }

    applicationRecipientChargingUnits OBJECT-TYPE
        SYNTAX  ChargingUnits
        ACCESS  read-write
        STATUS  mandatory
        DESCRIPTION
            "An integer number of units associated with the charging of
            AT messages terminated on this application. By default, the
            value is set to 0."
        ::= { applicationEntry 809 }

    applicationAoDelayTime OBJECT-TYPE
        SYNTAX  DelayTime
        ACCESS  read-write
        STATUS  mandatory
        DESCRIPTION
            "The number of seconds a message will be queued within the HUB
            before it is processed any further. Setting this value to a 
            non-zero value will extend the response to a minimum length equal 
            to this delay time.
            By default, the value is set to 0."
             ::= { applicationEntry 810 }

    applicationAoCurrentDelayed OBJECT-TYPE 
        SYNTAX  Gauge 
        ACCESS  read-only 
        STATUS  mandatory 
        DESCRIPTION 
             "The number of messages in this application's delayed queue." 
             ::= { applicationEntry 811 } 

    -- the ApplicationGroup Entity

    applicationGroupTable OBJECT-TYPE
        SYNTAX  SEQUENCE OF ApplicationGroupEntry
        ACCESS  not-accessible
        STATUS  mandatory
        DESCRIPTION
            "A table containing properties for each Application Group."
        ::= { apc 12 }

    applicationGroupEntry OBJECT-TYPE
        SYNTAX  ApplicationGroupEntry
        ACCESS  not-accessible
        STATUS  mandatory
        DESCRIPTION
            "Table entry defining a single ApplicationGroup."
        INDEX   { applicationGroupIndex }
        ::= { applicationGroupTable 1 }

    ApplicationGroupEntry ::=
        SEQUENCE {

            applicationGroupIndex                         ApplicationGroupTableIndex,
            applicationGroupAdminState                    AdminState,
            applicationGroupName                          NameString,
            applicationGroupThroughputAo                  Throughput,
            applicationGroupThroughputAt                  Throughput,
            applicationGroupCntAoThroughputLimitHit       Counter,
            applicationGroupCntAtThroughputLimitHit       Counter
        }

    applicationGroupIndex OBJECT-TYPE
        SYNTAX  ApplicationGroupTableIndex
        ACCESS  read-write
        STATUS  mandatory
        DESCRIPTION
            "Index of entry in Application Group table."
        ::= { applicationGroupEntry 1 }

    applicationGroupAdminState OBJECT-TYPE
        SYNTAX  AdminState
        ACCESS  read-write
        STATUS  mandatory
        DESCRIPTION
            "Administrative state of the Application Group.

            Transition from 'inactive' to 'active' is only possible when:
            1) name supplied and not already in use by another
               Application Group.

            Transition from 'active' to 'inactive' is always possible but will
            result in a graceful shutdown of all session to the associated
            applications.

            Transition to 'destroy' is only possible when:
            1) Application Group is not being referred
               (Application, aoRtg, aoCnt, aoExtCondRule, atRtg, atCnt,
                atExtCondRule)

            For details, refer to the comment on the AdminState type."
        ::= { applicationGroupEntry 2 }

    applicationGroupName OBJECT-TYPE
        SYNTAX  NameString
        ACCESS  read-write
        STATUS  mandatory
        DESCRIPTION
            "The name of the Application Group entity."
        ::= { applicationGroupEntry 3 }

    applicationGroupThroughputAo OBJECT-TYPE
        SYNTAX  Throughput
        ACCESS  read-write
        STATUS  mandatory
        DESCRIPTION
            "Maximum throughput from the associated applications towards the
            textpass system in terms of SM's per second."
        ::= { applicationGroupEntry 11 }

    applicationGroupThroughputAt OBJECT-TYPE
        SYNTAX  Throughput
        ACCESS  read-write
        STATUS  mandatory
        DESCRIPTION
            "Maximum throughput from the textpass system towards the
            associated applications in terms of SM's per second."
        ::= { applicationGroupEntry 12 }
  
    applicationGroupCntAoThroughputLimitHit OBJECT-TYPE
        SYNTAX  Counter
        ACCESS  read-write
        STATUS  mandatory
        DESCRIPTION
            "Counter specifying the number of times that the AO throughput
            limit as set for the Application Group has been hit."
        ::= { applicationGroupEntry 13 }

    applicationGroupCntAtThroughputLimitHit OBJECT-TYPE
        SYNTAX  Counter
        ACCESS  read-write
        STATUS  mandatory
        DESCRIPTION
            "Counter specifying the number of times that the AT throughput
            limit as set for the Application Group has been hit."
        ::= { applicationGroupEntry 14 }

 
    -- the ApplicationCategory Entity

    applicationCategoryTable OBJECT-TYPE
        SYNTAX  SEQUENCE OF ApplicationCategoryEntry
        ACCESS  not-accessible
        STATUS  mandatory
        DESCRIPTION
            "A table containing properties for each Application Category."
        ::= { apc 13 }

    applicationCategoryEntry OBJECT-TYPE
        SYNTAX  ApplicationCategoryEntry
        ACCESS  not-accessible
        STATUS  mandatory
        DESCRIPTION
            "Table entry defining a single Application Category."
        INDEX   { applicationCategoryIndex }
        ::= { applicationCategoryTable 1 }

    ApplicationCategoryEntry ::=
        SEQUENCE {
            applicationCategoryIndex                      ApplicationCategoryTableIndex,
            applicationCategoryAdminState                 AdminState,
            applicationCategoryName                       NameString
        }

    applicationCategoryIndex OBJECT-TYPE
        SYNTAX  ApplicationCategoryTableIndex
        ACCESS  read-write
        STATUS  mandatory
        DESCRIPTION
            "Index of entry in Application Category table."
        ::= { applicationCategoryEntry 1 }

    applicationCategoryAdminState OBJECT-TYPE
        SYNTAX  AdminState
        ACCESS  read-write
        STATUS  mandatory
        DESCRIPTION
            "Administrative state of the ApplicationCategory.

            Transition from 'inactive' to 'active' is only possible when:
            1) name supplied and not already in use by another
               ApplicationCategory.

            Transition from 'active' to 'inactive' is always possible.

            Transition to 'destroy' is only possible when:
            1) ApplicationCategory is not being referred.
                (Application, aoRtg, aoCnt, aoExtCondRule, atRtg, atCnt,
                 atExtCondRule)

            For details, refer to the comment on the AdminState type."
        ::= { applicationCategoryEntry 2 }

    applicationCategoryName OBJECT-TYPE
        SYNTAX  NameString
        ACCESS  read-write
        STATUS  mandatory
        DESCRIPTION
            "The name of the Application Category entity."
        ::= { applicationCategoryEntry 3 }

    -- the ServiceClass Entity

    serviceClassTable OBJECT-TYPE
        SYNTAX  SEQUENCE OF ServiceClassEntry
        ACCESS  not-accessible
        STATUS  mandatory
        DESCRIPTION
            "A table containing properties for each Service Class."
        ::= { apc 14 }

    serviceClassEntry OBJECT-TYPE
        SYNTAX  ServiceClassEntry
        ACCESS  not-accessible
        STATUS  mandatory
        DESCRIPTION
            "Table entry defining a single Service Class."
        INDEX   { serviceClassIndex }
        ::= { serviceClassTable 1 }

    ServiceClassEntry ::=
        SEQUENCE {
            serviceClassIndex                      ServiceClassTableIndex,
            serviceClassAdminState                 AdminState,
            serviceClassName                       NameString,
            serviceClassThroughputAo               Throughput,
            serviceClassThroughputAt               Throughput,
            serviceClassCntAoThroughputLimitHit    Counter,
            serviceClassCntAtThroughputLimitHit    Counter,
            serviceClassDialoutAllowed             Boolean,
            serviceClassModificationAllowed        Boolean,
            serviceClassLearningEnabled            Boolean,
            serviceClassDeferredDeliveryAllowed    Boolean,
            serviceClassNotificationAllowed        NotificationType,
            serviceClassSessionModel               ServiceClassSessionModel,
            serviceClassAllowedTraffic             TrafficType,
            serviceClassChargeIndication           ChargeIndication            
        }

    serviceClassIndex OBJECT-TYPE
        SYNTAX  ServiceClassTableIndex
        ACCESS  read-write
        STATUS  mandatory
        DESCRIPTION
            "Index of entry in Service Class table."

        ::= { serviceClassEntry 1 }

    serviceClassAdminState OBJECT-TYPE
        SYNTAX  AdminState
        ACCESS  read-write
        STATUS  mandatory
        DESCRIPTION
            "Administrative state of the ServiceClass.

            Transition from 'inactive' to 'active' is only possible when:
            1) name supplied and not already in use by another ServiceClass.

            Transition from 'active' to 'inactive' is always possible but
            will result in a graceful shutdown of all associated sessions
            with the Listener, Application and Termination Point with this
            Service Class.

            Transition to 'destroy' is only possible when:
            1) ServiceClass is not being referred
               (OutsideListener, Application, ScTerminationPoint,
                aoRtg, aoCnt, aoExtCondRule, atRtg, atCnt, atExtCondRule).

            For details, refer to the comment on the AdminState type."
        ::= { serviceClassEntry 2 }

    serviceClassName OBJECT-TYPE

        SYNTAX  NameString
        ACCESS  read-write
        STATUS  mandatory
        DESCRIPTION
            "The name of the Service Class entity."
        ::= { serviceClassEntry 3 }

    serviceClassThroughputAo OBJECT-TYPE
        SYNTAX  Throughput
        ACCESS  read-write
        STATUS  mandatory
        DESCRIPTION
            "Maximum throughput from the associated applications towards the
            textpass system in terms of SM's per second."
        ::= { serviceClassEntry 11 }

    serviceClassThroughputAt OBJECT-TYPE
        SYNTAX  Throughput
        ACCESS  read-write
        STATUS  mandatory
        DESCRIPTION
            "Maximum throughput from the textpass system towards the
            associated applications in terms of SM's per second."
        ::= { serviceClassEntry 12 }
  
    serviceClassCntAoThroughputLimitHit OBJECT-TYPE
        SYNTAX  Counter
        ACCESS  read-write
        STATUS  mandatory
        DESCRIPTION
            "Counter specifying the number of times that the AO throughput
            limit as set for the Service Class has been hit."
        ::= { serviceClassEntry 13 }

    serviceClassCntAtThroughputLimitHit OBJECT-TYPE
        SYNTAX  Counter
        ACCESS  read-write
        STATUS  mandatory
        DESCRIPTION
            "Counter specifying the number of times that the AT throughput
            limit as set for the Service Class has been hit."
        ::= { serviceClassEntry 14 }

    serviceClassDialoutAllowed OBJECT-TYPE
        SYNTAX  Boolean
        ACCESS  read-write
        STATUS  mandatory
        DESCRIPTION
            "Flag indicating whether or not Dialout is allowed for
            applications using this ServiceClass. Default is false."
        ::= { serviceClassEntry 21 }

    serviceClassModificationAllowed OBJECT-TYPE
        SYNTAX  Boolean
        ACCESS  read-write
        STATUS  mandatory
        DESCRIPTION
            "Flag indicating whether or not modification of submitted messages
            using this ServiceClass is allowed. Default is true."
        ::= { serviceClassEntry 22 }

    serviceClassLearningEnabled OBJECT-TYPE
        SYNTAX  Boolean
        ACCESS  read-write
        STATUS  mandatory
        DESCRIPTION
            "Enable 'learning mode' for this Service Class or not.
             Default is false."
        ::= { serviceClassEntry 23 }

    serviceClassDeferredDeliveryAllowed OBJECT-TYPE
        SYNTAX  Boolean
        ACCESS  read-write
        STATUS  mandatory
        DESCRIPTION
            "Allow deferred delivery for applications using this
            Service Class. Default is true."
        ::= { serviceClassEntry 24 }
        
    serviceClassNotificationAllowed OBJECT-TYPE
        SYNTAX  NotificationType
        ACCESS  read-write
        STATUS  mandatory
        DESCRIPTION
            "Indication which type of notifications is allowed.
            For detail, refer to the comment on the NotificationType type.
            Default is '111' (= all notifications). The message will be
            rejected if the Application request a notification with a
            specific type when it is not allowed to request that type."
        ::= { serviceClassEntry 25 }

    serviceClassSessionModel OBJECT-TYPE
        SYNTAX  ServiceClassSessionModel
        ACCESS  read-write
        STATUS  mandatory
        DESCRIPTION
            "Session Model describing how the sessions of the applications
            using this Service Class should be handled.
            Note: if in the Application the Session Model is set different
            from 'useServiceClassModel', that model overrules this setting
            for that Applicaion.
            #The type 'useServiceClassModel' may not be used.#
            #For details, refer to the comment on the SessionModel type.#"
        ::= { serviceClassEntry 26 }

    serviceClassAllowedTraffic OBJECT-TYPE
        SYNTAX  TrafficType
        ACCESS  read-write
        STATUS  mandatory
        DESCRIPTION
            "Type of traffic which is allowed for this Service Class.
            For details, refer to the comment on the TrafficType type.
            Default is 'aoAt'."
        ::= { serviceClassEntry 27 }

    serviceClassChargeIndication OBJECT-TYPE
        SYNTAX  ChargeIndication
        ACCESS  read-write
        STATUS  mandatory
        DESCRIPTION
            "Indication defines how to charge messages belonging to this 
            Service Class.
            Default is 'chargeOriginator'."
        ::= { serviceClassEntry 28 }
    
            
    -- the ApplicationServiceClass Entity

    applicationServiceClassTable OBJECT-TYPE
        SYNTAX  SEQUENCE OF ApplicationServiceClassEntry
        ACCESS  not-accessible
        STATUS  mandatory
        DESCRIPTION
            "A table containing properties for each association between an
            Application and a ServiceClass."
        ::= { apc 15 }

    applicationServiceClassEntry OBJECT-TYPE
        SYNTAX  ApplicationServiceClassEntry
        ACCESS  not-accessible
        STATUS  mandatory
        DESCRIPTION
            "Table entry defining a single ApplicationServiceClass."
        INDEX   { applicationServiceClassApplicationIndex,
                  applicationServiceClassIndex }
        ::= { applicationServiceClassTable 1 }

    ApplicationServiceClassEntry ::=
        SEQUENCE {
            applicationServiceClassApplicationIndex        ApplicationTableIndex,
            applicationServiceClassIndex                   ApplicationServiceClassTableIndex,
            applicationServiceClassServiceClassIndex       ServiceClassTableIndex,
            applicationServiceClassAdminState              AdminState,
            applicationServiceClassOperationalState        OperationalState
        }

    applicationServiceClassApplicationIndex OBJECT-TYPE
        SYNTAX  ApplicationTableIndex
        ACCESS  read-write
        STATUS  mandatory
        DESCRIPTION
            "Index referring to an entry in the Application table."
        ::= { applicationServiceClassEntry 1 }

    applicationServiceClassIndex OBJECT-TYPE
        SYNTAX  ApplicationServiceClassTableIndex
        ACCESS  read-write
        STATUS  mandatory
        DESCRIPTION
            "Index referring to this entry the table."
        ::= { applicationServiceClassEntry 2 }

    applicationServiceClassServiceClassIndex OBJECT-TYPE
        SYNTAX  ServiceClassTableIndex
        ACCESS  read-write
        STATUS  mandatory
        DESCRIPTION
            "Index referring to an entry in the Service Class table.
            If the Service Class exists then the admin state will be changed
            to active. Otherwise it will stay inactive.
            This attribute may not be changed after setting."
        ::= { applicationServiceClassEntry 3 }

    applicationServiceClassAdminState OBJECT-TYPE
        SYNTAX  AdminState
        ACCESS  read-write
        STATUS  mandatory
        DESCRIPTION
            "Administrative state of the ApplicationServiceClass.

            This admin state is maintained automatically by Textpass
            setting it to active/inactive will be accepted but will not
            result in a state change. Setting it to 'destroy' will remove
            the relation between this Application and the Service Class.

            For details, refer to the comment on the AdminState type."
        ::= { applicationServiceClassEntry 4 }

    applicationServiceClassOperationalState OBJECT-TYPE
        SYNTAX  OperationalState
        ACCESS  read-only
        STATUS  mandatory
        DESCRIPTION
            "The operational state of the Application Service Class entity."
        ::= { applicationServiceClassEntry 5 }

    -- the Service Centre Entity

    serviceCentreTable OBJECT-TYPE
        SYNTAX  SEQUENCE OF ServiceCentreEntry
        ACCESS  not-accessible
        STATUS  mandatory
        DESCRIPTION
            "A table containing properties for each Service Centre."
        ::= { apc 21 }

    serviceCentreEntry OBJECT-TYPE
        SYNTAX  ServiceCentreEntry
        ACCESS  not-accessible
        STATUS  mandatory
        DESCRIPTION
            "Table entry defining a single Service Centre."
        INDEX   { serviceCentreIndex }
        ::= { serviceCentreTable 1 }

    ServiceCentreEntry ::=
        SEQUENCE {
            serviceCentreIndex                     ServiceCentreTableIndex,
            serviceCentreAdminState                AdminState,
            serviceCentreName                      NameString,
            serviceCentreOperationalState          OperationalState,
            serviceCentreCharacterSet              CustomCharacterSet,            
            serviceCentreThroughputAo              Throughput,
            serviceCentreThroughputAt              Throughput,
            serviceCentreWeight                    Weight,
            serviceCentreSessionsCounter           Gauge,
            serviceCentreCntAoThroughputLimitHit   Counter,
            serviceCentreUcpForwardErrorMapIndex   ErrorMapIndex,
            serviceCentreUcpReverseErrorMapIndex   ErrorMapIndex,
            serviceCentreSmppForwardErrorMapIndex  ErrorMapIndex,
            serviceCentreSmppReverseErrorMapIndex  ErrorMapIndex,
            serviceCentreCimdForwardErrorMapIndex  ErrorMapIndex,
            serviceCentreCimdReverseErrorMapIndex  ErrorMapIndex,
            serviceCentreCntAoUcp01Request                      Counter,
            serviceCentreCntAoUcp01Ack                          Counter,
            serviceCentreCntAoUcp01Nack                         Counter,
            serviceCentreAoUcp01TimeSpent                       HighResTime,
            serviceCentreAoUcp01ShortestRespTime                HighResTime,
            serviceCentreAoUcp01TimestampShortestResp           TimeStamp,
            serviceCentreAoUcp01LongestRespTime                 HighResTime,
            serviceCentreAoUcp01TimestampLongestResp            TimeStamp,
            serviceCentreCntAoUcp30Request                      Counter,
            serviceCentreCntAoUcp30Ack                          Counter,
            serviceCentreCntAoUcp30Nack                         Counter,
            serviceCentreAoUcp30TimeSpent                       HighResTime,
            serviceCentreAoUcp30ShortestRespTime                HighResTime,
            serviceCentreAoUcp30TimestampShortestResp           TimeStamp,
            serviceCentreAoUcp30LongestRespTime                 HighResTime,
            serviceCentreAoUcp30TimestampLongestResp            TimeStamp,
            serviceCentreCntAoUcp31Request                      Counter,
            serviceCentreCntAoUcp31Ack                          Counter,
            serviceCentreCntAoUcp31Nack                         Counter,
            serviceCentreAoUcp31TimeSpent                       HighResTime,
            serviceCentreAoUcp31ShortestRespTime                HighResTime,
            serviceCentreAoUcp31TimestampShortestResp           TimeStamp,
            serviceCentreAoUcp31LongestRespTime                 HighResTime,
            serviceCentreAoUcp31TimestampLongestResp            TimeStamp,
            serviceCentreCntAoUcp51Request                      Counter,
            serviceCentreCntAoUcp51Ack                          Counter,
            serviceCentreCntAoUcp51Nack                         Counter,
            serviceCentreAoUcp51TimeSpent                       HighResTime,
            serviceCentreAoUcp51ShortestRespTime                HighResTime,
            serviceCentreAoUcp51TimestampShortestResp           TimeStamp,
            serviceCentreAoUcp51LongestRespTime                 HighResTime,
            serviceCentreAoUcp51TimestampLongestResp            TimeStamp,
            serviceCentreCntAoUcp54Request                      Counter,
            serviceCentreCntAoUcp54Ack                          Counter,
            serviceCentreCntAoUcp54Nack                         Counter,
            serviceCentreAoUcp54TimeSpent                       HighResTime,
            serviceCentreAoUcp54ShortestRespTime                HighResTime,
            serviceCentreAoUcp54TimestampShortestResp           TimeStamp,
            serviceCentreAoUcp54LongestRespTime                 HighResTime,
            serviceCentreAoUcp54TimestampLongestResp            TimeStamp,
            serviceCentreCntAoUcp60Request                      Counter,
            serviceCentreCntAoUcp60Ack                          Counter,
            serviceCentreCntAoUcp60Nack                         Counter,
            serviceCentreAoUcp60TimeSpent                       HighResTime,
            serviceCentreAoUcp60ShortestRespTime                HighResTime,
            serviceCentreAoUcp60TimestampShortestResp           TimeStamp,
            serviceCentreAoUcp60LongestRespTime                 HighResTime,
            serviceCentreAoUcp60TimestampLongestResp            TimeStamp,
            serviceCentreCntAoUcpOtherRequest                   Counter,
            serviceCentreCntAoUcpOtherAck                       Counter,
            serviceCentreCntAoUcpOtherNack                      Counter,
            serviceCentreAoUcpOtherTimeSpent                    HighResTime,
            serviceCentreAoUcpOtherShortestRespTime             HighResTime,
            serviceCentreAoUcpOtherTimestampShortestResp        TimeStamp,
            serviceCentreAoUcpOtherLongestRespTime              HighResTime,
            serviceCentreAoUcpOtherTimestampLongestResp         TimeStamp,
            serviceCentreCntAoUcp55Request                      Counter,
            serviceCentreCntAoUcp55Ack                          Counter,
            serviceCentreCntAoUcp55Nack                         Counter,
            serviceCentreAoUcp55TimeSpent                       HighResTime,
            serviceCentreAoUcp55ShortestRespTime                HighResTime,
            serviceCentreAoUcp55TimestampShortestResp           TimeStamp,
            serviceCentreAoUcp55LongestRespTime                 HighResTime,
            serviceCentreAoUcp55TimestampLongestResp            TimeStamp,
            serviceCentreCntAoUcp56Request                      Counter,
            serviceCentreCntAoUcp56Ack                          Counter,
            serviceCentreCntAoUcp56Nack                         Counter,
            serviceCentreAoUcp56TimeSpent                       HighResTime,
            serviceCentreAoUcp56ShortestRespTime                HighResTime,
            serviceCentreAoUcp56TimestampShortestResp           TimeStamp,
            serviceCentreAoUcp56LongestRespTime                 HighResTime,
            serviceCentreAoUcp56TimestampLongestResp            TimeStamp,

            serviceCentreCntAoSmppSubmitSmRequest               Counter,
            serviceCentreCntAoSmppSubmitSmAck                   Counter,
            serviceCentreCntAoSmppSubmitSmNack                  Counter,
            serviceCentreAoSmppSubmitSmTimeSpent                HighResTime,
            serviceCentreAoSmppSubmitSmShortestRespTime         HighResTime,
            serviceCentreAoSmppSubmitSmTimestampShortestResp    TimeStamp,
            serviceCentreAoSmppSubmitSmLongestRespTime          HighResTime,
            serviceCentreAoSmppSubmitSmTimestampLongestResp     TimeStamp,
            serviceCentreCntAoSmppDataSmRequest                 Counter,
            serviceCentreCntAoSmppDataSmAck                     Counter,
            serviceCentreCntAoSmppDataSmNack                    Counter,
            serviceCentreAoSmppDataSmTimeSpent                  HighResTime,
            serviceCentreAoSmppDataSmShortestRespTime           HighResTime,
            serviceCentreAoSmppDataSmTimestampShortestResp      TimeStamp,
            serviceCentreAoSmppDataSmLongestRespTime            HighResTime,
            serviceCentreAoSmppDataSmTimestampLongestResp       TimeStamp,
            serviceCentreCntAoSmppBindRxRequest                 Counter,
            serviceCentreCntAoSmppBindRxAck                     Counter,
            serviceCentreCntAoSmppBindRxNack                    Counter,
            serviceCentreAoSmppBindRxTimeSpent                  HighResTime,
            serviceCentreAoSmppBindRxShortestRespTime           HighResTime,
            serviceCentreAoSmppBindRxTimestampShortestResp      TimeStamp,
            serviceCentreAoSmppBindRxLongestRespTime            HighResTime,
            serviceCentreAoSmppBindRxTimestampLongestResp       TimeStamp,
            serviceCentreCntAoSmppBindTxRequest                 Counter,
            serviceCentreCntAoSmppBindTxAck                     Counter,
            serviceCentreCntAoSmppBindTxNack                    Counter,
            serviceCentreAoSmppBindTxTimeSpent                  HighResTime,
            serviceCentreAoSmppBindTxShortestRespTime           HighResTime,
            serviceCentreAoSmppBindTxTimestampShortestResp      TimeStamp,
            serviceCentreAoSmppBindTxLongestRespTime            HighResTime,
            serviceCentreAoSmppBindTxTimestampLongestResp       TimeStamp,
            serviceCentreCntAoSmppBindTrxRequest                Counter,
            serviceCentreCntAoSmppBindTrxAck                    Counter,
            serviceCentreCntAoSmppBindTrxNack                   Counter,
            serviceCentreAoSmppBindTrxTimeSpent                 HighResTime,
            serviceCentreAoSmppBindTrxShortestRespTime          HighResTime,
            serviceCentreAoSmppBindTrxTimestampShortestResp     TimeStamp,
            serviceCentreAoSmppBindTrxLongestRespTime           HighResTime,
            serviceCentreAoSmppBindTrxTimestampLongestResp      TimeStamp,
            serviceCentreCntAoSmppUnbindRequest                 Counter,
            serviceCentreCntAoSmppUnbindAck                     Counter,
            serviceCentreCntAoSmppUnbindNack                    Counter,
            serviceCentreAoSmppUnbindTimeSpent                  HighResTime,
            serviceCentreAoSmppUnbindShortestRespTime           HighResTime,
            serviceCentreAoSmppUnbindTimestampShortestResp      TimeStamp,
            serviceCentreAoSmppUnbindLongestRespTime            HighResTime,
            serviceCentreAoSmppUnbindTimestampLongestResp       TimeStamp,
            serviceCentreCntAoSmppQuerySmRequest                Counter,
            serviceCentreCntAoSmppQuerySmAck                    Counter,
            serviceCentreCntAoSmppQuerySmNack                   Counter,
            serviceCentreAoSmppQuerySmTimeSpent                 HighResTime,
            serviceCentreAoSmppQuerySmShortestRespTime          HighResTime,
            serviceCentreAoSmppQuerySmTimestampShortestResp     TimeStamp,
            serviceCentreAoSmppQuerySmLongestRespTime           HighResTime,
            serviceCentreAoSmppQuerySmTimestampLongestResp      TimeStamp,
            serviceCentreCntAoSmppReplaceSmRequest              Counter,
            serviceCentreCntAoSmppReplaceSmAck                  Counter,
            serviceCentreCntAoSmppReplaceSmNack                 Counter,
            serviceCentreAoSmppReplaceSmTimeSpent               HighResTime,
            serviceCentreAoSmppReplaceSmShortestRespTime        HighResTime,
            serviceCentreAoSmppReplaceSmTimestampShortestResp   TimeStamp,
            serviceCentreAoSmppReplaceSmLongestRespTime         HighResTime,
            serviceCentreAoSmppReplaceSmTimestampLongestResp    TimeStamp,
            serviceCentreCntAoSmppCancelSmRequest               Counter,
            serviceCentreCntAoSmppCancelSmAck                   Counter,
            serviceCentreCntAoSmppCancelSmNack                  Counter,
            serviceCentreAoSmppCancelSmTimeSpent                HighResTime,
            serviceCentreAoSmppCancelSmShortestRespTime         HighResTime,
            serviceCentreAoSmppCancelSmTimestampShortestResp    TimeStamp,
            serviceCentreAoSmppCancelSmLongestRespTime          HighResTime,
            serviceCentreAoSmppCancelSmTimestampLongestResp     TimeStamp,
            serviceCentreCntAoSmppEnquireLinkRequest            Counter,
            serviceCentreCntAoSmppEnquireLinkAck                Counter,
            serviceCentreCntAoSmppEnquireLinkNack               Counter,
            serviceCentreAoSmppEnquireLinkTimeSpent             HighResTime,
            serviceCentreAoSmppEnquireLinkShortestRespTime      HighResTime,
            serviceCentreAoSmppEnquireLinkTimestampShortestResp      TimeStamp,
            serviceCentreAoSmppEnquireLinkLongestRespTime       HighResTime,
            serviceCentreAoSmppEnquireLinkTimestampLongestResp      TimeStamp,
            serviceCentreCntAoSmppOtherRequest                  Counter,
            serviceCentreCntAoSmppOtherAck                      Counter,
            serviceCentreCntAoSmppOtherNack                     Counter,
            serviceCentreAoSmppOtherTimeSpent                   HighResTime,
            serviceCentreAoSmppOtherShortestRespTime            HighResTime,
            serviceCentreAoSmppOtherTimestampShortestResp       TimeStamp,
            serviceCentreAoSmppOtherLongestRespTime             HighResTime,
            serviceCentreAoSmppOtherTimestampLongestResp        TimeStamp,
            serviceCentreAoSmppGenericNack                      Counter,
            serviceCentreCntAoCimdLoginRequest                  Counter,
            serviceCentreCntAoCimdLoginAck                      Counter,
            serviceCentreCntAoCimdLoginNack                     Counter,
            serviceCentreAoCimdLoginTimeSpent                   HighResTime,
            serviceCentreAoCimdLoginShortestRespTime            HighResTime,
            serviceCentreAoCimdLoginTimestampShortestResp       TimeStamp,
            serviceCentreAoCimdLoginLongestRespTime             HighResTime,
            serviceCentreAoCimdLoginTimestampLongestResp        TimeStamp,
            serviceCentreCntAoCimdLogoutRequest                 Counter,
            serviceCentreCntAoCimdLogoutAck                     Counter,
            serviceCentreCntAoCimdLogoutNack                    Counter,
            serviceCentreAoCimdLogoutTimeSpent                  HighResTime,
            serviceCentreAoCimdLogoutShortestRespTime           HighResTime,
            serviceCentreAoCimdLogoutTimestampShortestResp      TimeStamp,
            serviceCentreAoCimdLogoutLongestRespTime            HighResTime,
            serviceCentreAoCimdLogoutTimestampLongestResp       TimeStamp,
            serviceCentreCntAoCimdSubmitRequest                 Counter,
            serviceCentreCntAoCimdSubmitAck                     Counter,
            serviceCentreCntAoCimdSubmitNack                    Counter,
            serviceCentreAoCimdSubmitTimeSpent                  HighResTime,
            serviceCentreAoCimdSubmitShortestRespTime           HighResTime,
            serviceCentreAoCimdSubmitTimestampShortestResp      TimeStamp,
            serviceCentreAoCimdSubmitLongestRespTime            HighResTime,
            serviceCentreAoCimdSubmitTimestampLongestResp       TimeStamp,
            serviceCentreCntAoCimdEnquireRequest                Counter,
            serviceCentreCntAoCimdEnquireAck                    Counter,
            serviceCentreCntAoCimdEnquireNack                   Counter,
            serviceCentreAoCimdEnquireTimeSpent                 HighResTime,
            serviceCentreAoCimdEnquireShortestRespTime          HighResTime,
            serviceCentreAoCimdEnquireTimestampShortestResp     TimeStamp,
            serviceCentreAoCimdEnquireLongestRespTime           HighResTime,
            serviceCentreAoCimdEnquireTimestampLongestResp      TimeStamp,
            serviceCentreCntAoCimdOtherRequest                  Counter,
            serviceCentreCntAoCimdOtherAck                      Counter,
            serviceCentreCntAoCimdOtherNack                     Counter,
            serviceCentreAoCimdOtherTimeSpent                   HighResTime,
            serviceCentreAoCimdOtherShortestRespTime            HighResTime,
            serviceCentreAoCimdOtherTimestampShortestResp       TimeStamp,
            serviceCentreAoCimdOtherLongestRespTime             HighResTime,
            serviceCentreAoCimdOtherTimestampLongestResp        TimeStamp,
            serviceCentreCntAtUcp52Request                      Counter,
            serviceCentreCntAtUcp52Ack                          Counter,
            serviceCentreCntAtUcp52Nack                         Counter,
            serviceCentreCntAtUcp53Request                      Counter,
            serviceCentreCntAtUcp53Ack                          Counter,
            serviceCentreCntAtUcp53Nack                         Counter,
            serviceCentreCntAtUcpOtherRequest                   Counter,
            serviceCentreCntAtUcpOtherAck                       Counter,
            serviceCentreCntAtUcpOtherNack                      Counter,
            serviceCentreCntAtUcp57Request                      Counter,
            serviceCentreCntAtUcp57Ack                          Counter,
            serviceCentreCntAtUcp57Nack                         Counter,
            serviceCentreCntAtUcp58Request                      Counter,
            serviceCentreCntAtUcp58Ack                          Counter,
            serviceCentreCntAtUcp58Nack                         Counter,
            serviceCentreCntAtSmppDeliverSmRequest              Counter,
            serviceCentreCntAtSmppDeliverSmAck                  Counter,
            serviceCentreCntAtSmppDeliverSmNack                 Counter,
            serviceCentreCntAtSmppDataSmRequest                 Counter,
            serviceCentreCntAtSmppDataSmAck                     Counter,
            serviceCentreCntAtSmppDataSmNack                    Counter,
            serviceCentreCntAtSmppOtherRequest                  Counter,
            serviceCentreCntAtSmppOtherAck                      Counter,
            serviceCentreCntAtSmppOtherNack                     Counter,
            serviceCentreCntAtCimdDeliverRequest                Counter,
            serviceCentreCntAtCimdDeliverAck                    Counter,
            serviceCentreCntAtCimdDeliverNack                   Counter,
            serviceCentreCntAtCimdDeliverStatusRequest          Counter,
            serviceCentreCntAtCimdDeliverStatusAck              Counter,
            serviceCentreCntAtCimdDeliverStatusNack             Counter,
            serviceCentreCntAtCimdAliveRequest                  Counter,
            serviceCentreCntAtCimdAliveAck                      Counter,
            serviceCentreCntAtCimdAliveNack                     Counter,
            serviceCentreCntAtCimdOtherRequest                  Counter,
            serviceCentreCntAtCimdOtherAck                      Counter,
            serviceCentreCntAtCimdOtherNack                     Counter

        }

    serviceCentreIndex OBJECT-TYPE
        SYNTAX  ServiceCentreTableIndex
        ACCESS  not-accessible
        STATUS  mandatory
        DESCRIPTION
            "Index of entry in Service Centre table."
        ::= { serviceCentreEntry 1 }

    serviceCentreAdminState OBJECT-TYPE
        SYNTAX  AdminState
        ACCESS  read-write
        STATUS  mandatory
        DESCRIPTION
            "Administrative state of the Service Centre.

            Transition from 'inactive' to 'active' is only possible when:
            1) name supplied and not already in use by another Service Centre;

            Transition from 'active' to 'inactive' is always possible but will
            result in a graceful shutdown of all inside sessions towards the
            Termination Points of the nodes of this Service Centre.

            Transition to 'destroy' is only possible when:
            1) Service Centre is not being referred.

            For details, refer to the comment on the AdminState type."
        ::= { serviceCentreEntry 2 }

    serviceCentreName OBJECT-TYPE
        SYNTAX  NameString
        ACCESS  read-write
        STATUS  mandatory
        DESCRIPTION
            "Name of the Service Centre entity."
        ::= { serviceCentreEntry 3 }

    serviceCentreOperationalState OBJECT-TYPE
        SYNTAX  OperationalState
        ACCESS  read-only
        STATUS  mandatory
        DESCRIPTION
            "The operational state of the Service Centre entity."
        ::= { serviceCentreEntry 4 }

    serviceCentreCharacterSet OBJECT-TYPE
        SYNTAX  CustomCharacterSet
        ACCESS  read-write
        STATUS  mandatory
        DESCRIPTION
            "Specifies which custom character is used.
             Default is 0 (No custom character set is used)."
        ::= { serviceCentreEntry 8 }

    

    serviceCentreThroughputAo OBJECT-TYPE
        SYNTAX  Throughput
        ACCESS  read-write
        STATUS  mandatory
        DESCRIPTION
            "Maximum incoming throughput the Service Centre can handle from
            external entities like the TextPassHub in terms of SM's per
            second."
        ::= { serviceCentreEntry 11 }

    serviceCentreThroughputAt OBJECT-TYPE
        SYNTAX  Throughput
        ACCESS  read-write
        STATUS  mandatory
        DESCRIPTION
            "Maximum outgoing throughput the Service Centre can send towards
            external entities like the TextPassHub in terms of SM's per
            second."
        ::= { serviceCentreEntry 12 }

    serviceCentreWeight OBJECT-TYPE
        SYNTAX  Weight
        ACCESS  read-write
        STATUS  mandatory
        DESCRIPTION
            "Weight in load-balancing scheme for a Service Centre when routing
            AO messages to a set of Service Centres. Only changeable if the
            Service Centre is inactive. The TextPass HUB uses this
            setting to load-balance the number of sessions between the
            serviceCentres in case of a Replicate session model."
        ::= { serviceCentreEntry 15 }

    serviceCentreSessionsCounter OBJECT-TYPE
        SYNTAX  Gauge
        ACCESS  read-write
        STATUS  mandatory
        DESCRIPTION
            "Number of total sessions currently established towards the SC."
        ::= { serviceCentreEntry 21 }
  
    serviceCentreCntAoThroughputLimitHit OBJECT-TYPE
        SYNTAX  Counter
        ACCESS  read-write
        STATUS  mandatory
        DESCRIPTION
            "Counter specifying the number of times that the AO throughput
            limit as set for the SC Service Centre has been hit."
        ::= { serviceCentreEntry 22 }

    serviceCentreSmppForwardErrorMapIndex OBJECT-TYPE
        SYNTAX  ErrorMapIndex
        ACCESS  read-write
        STATUS  mandatory
        DESCRIPTION
            "Index of forward error mapping table to be used for Smpp."
        ::= { serviceCentreEntry 31 }

    serviceCentreSmppReverseErrorMapIndex OBJECT-TYPE
        SYNTAX  ErrorMapIndex
        ACCESS  read-write
        STATUS  mandatory
        DESCRIPTION
            "Index of reverse error mapping table to be used for Smpp."
        ::= { serviceCentreEntry 32 }

    serviceCentreUcpForwardErrorMapIndex OBJECT-TYPE
        SYNTAX  ErrorMapIndex
        ACCESS  read-write
        STATUS  mandatory
        DESCRIPTION
            "Index of forward error mapping table to be used for Ucp."
        ::= { serviceCentreEntry 33 }

    serviceCentreUcpReverseErrorMapIndex OBJECT-TYPE
        SYNTAX  ErrorMapIndex
        ACCESS  read-write
        STATUS  mandatory
        DESCRIPTION
            "Index of reverse error mapping table to be used for Ucp."
        ::= { serviceCentreEntry 34 }

    serviceCentreCimdForwardErrorMapIndex OBJECT-TYPE
        SYNTAX  ErrorMapIndex
        ACCESS  read-write
        STATUS  mandatory
        DESCRIPTION
            "Index of forward error mapping table to be used for Cimd."
        ::= { serviceCentreEntry 35 }

    serviceCentreCimdReverseErrorMapIndex OBJECT-TYPE
        SYNTAX  ErrorMapIndex
        ACCESS  read-write
        STATUS  mandatory
        DESCRIPTION
            "Index of reverse error mapping table to be used for Cimd."
        ::= { serviceCentreEntry 36 }

    serviceCentreCntAoUcp01Request OBJECT-TYPE
        SYNTAX  Counter
        ACCESS  read-only
        STATUS  mandatory
        DESCRIPTION
            "Counts the total number of UCP call input request which
             were sent to the service centre."
        ::= { serviceCentreEntry 70 }

    serviceCentreCntAoUcp01Ack OBJECT-TYPE
        SYNTAX  Counter
        ACCESS  read-only
        STATUS  mandatory
        DESCRIPTION
            "Counts the total number of positive UCP call input
             responses which were received from the service centre."
        ::= { serviceCentreEntry 71 }

    serviceCentreCntAoUcp01Nack OBJECT-TYPE
        SYNTAX  Counter
        ACCESS  read-only
        STATUS  mandatory
        DESCRIPTION
            "Counts the total number of negative UCP call input
             responses which were received from the service centre."
        ::= { serviceCentreEntry 72 }

    serviceCentreAoUcp01TimeSpent OBJECT-TYPE
        SYNTAX  HighResTime
        ACCESS  read-only
        STATUS  mandatory
        DESCRIPTION
            "Total time spent in processing UCP call input requests."
        ::= { serviceCentreEntry 73 }

    serviceCentreAoUcp01ShortestRespTime OBJECT-TYPE
        SYNTAX  HighResTime
        ACCESS  read-only
        STATUS  mandatory
        DESCRIPTION
            "Shortest response time for processing a UCP call input
             requests."
        ::= { serviceCentreEntry 74 }

    serviceCentreAoUcp01TimestampShortestResp OBJECT-TYPE
        SYNTAX  TimeStamp
        ACCESS  read-write
        STATUS  mandatory
        DESCRIPTION
            "Time stamp when shortest response time of a UCP call input
             request occurred. The shortest response time can be reset
             by setting shortest response time stamp to zero."
        ::= { serviceCentreEntry 75 }

    serviceCentreAoUcp01LongestRespTime OBJECT-TYPE
        SYNTAX  HighResTime
        ACCESS  read-only
        STATUS  mandatory
        DESCRIPTION
            "Longest response time for processing a UCP call input
             requests."
        ::= { serviceCentreEntry 76 }

    serviceCentreAoUcp01TimestampLongestResp OBJECT-TYPE
        SYNTAX  TimeStamp
        ACCESS  read-write
        STATUS  mandatory
        DESCRIPTION
            "Time stamp when longest response time of a UCP call input
             request occurred. The longest response time can be reset by
             setting longtest response time stamp to zero."
        ::= { serviceCentreEntry 77 }

    serviceCentreCntAoUcp30Request OBJECT-TYPE
        SYNTAX  Counter
        ACCESS  read-only
        STATUS  mandatory
        DESCRIPTION
            "Counts the total number of UCP message transfer requests which
             were sent to the Service Centre."
        ::= { serviceCentreEntry 90 }

    serviceCentreCntAoUcp30Ack OBJECT-TYPE
        SYNTAX  Counter
        ACCESS  read-only
        STATUS  mandatory
        DESCRIPTION
            "Counts the total number of positive UCP message transfer 
             responses which were received from the Service Centre."
        ::= { serviceCentreEntry 91 }

    serviceCentreCntAoUcp30Nack OBJECT-TYPE
        SYNTAX  Counter
        ACCESS  read-only
        STATUS  mandatory
        DESCRIPTION
            "Counts the total number of negative UCP message transfer 
             responses which were received from the Service Centre."
        ::= { serviceCentreEntry 92 }

    serviceCentreAoUcp30TimeSpent OBJECT-TYPE
        SYNTAX  HighResTime
        ACCESS  read-only
        STATUS  mandatory
        DESCRIPTION
            "Total time spent in processing UCP message transfer requests."
        ::= { serviceCentreEntry 93 }

    serviceCentreAoUcp30ShortestRespTime OBJECT-TYPE
        SYNTAX  HighResTime
        ACCESS  read-only
        STATUS  mandatory
        DESCRIPTION
            "Shortest response time for processing a UCP message transfer
             request."
        ::= { serviceCentreEntry 94 }

    serviceCentreAoUcp30TimestampShortestResp OBJECT-TYPE
        SYNTAX  TimeStamp
        ACCESS  read-write
        STATUS  mandatory
        DESCRIPTION
            "Timestamp when shortest response time of a UCP message transfer
             request occurred. The shortest response time can be reset
             by setting shortest response timestamp to zero."
        ::= { serviceCentreEntry 95 }

    serviceCentreAoUcp30LongestRespTime OBJECT-TYPE
        SYNTAX  HighResTime
        ACCESS  read-only
        STATUS  mandatory
        DESCRIPTION
            "Longest response time for processing a UCP message transfer
             request."
        ::= { serviceCentreEntry 96 }

    serviceCentreAoUcp30TimestampLongestResp OBJECT-TYPE
        SYNTAX  TimeStamp
        ACCESS  read-write
        STATUS  mandatory
        DESCRIPTION
            "Timestamp when longest response time of a UCP message transfer
             request occurred. The longest response time can be reset by
             setting longest response timestamp to zero."
        ::= { serviceCentreEntry 97 }

    serviceCentreCntAoUcp31Request OBJECT-TYPE
        SYNTAX  Counter
        ACCESS  read-only
        STATUS  mandatory
        DESCRIPTION
            "Counts the total number of UCP alert requests which were
             sent to the Service Centre."
        ::= { serviceCentreEntry 100 }

    serviceCentreCntAoUcp31Ack OBJECT-TYPE
        SYNTAX  Counter
        ACCESS  read-only
        STATUS  mandatory
        DESCRIPTION
            "Counts the total number of positive UCP alert responses
             which were received from the Service Centre."
        ::= { serviceCentreEntry 101 }

    serviceCentreCntAoUcp31Nack OBJECT-TYPE
        SYNTAX  Counter
        ACCESS  read-only
        STATUS  mandatory
        DESCRIPTION
            "Counts the total number of negative UCP alert responses
             which were received from the Service Centre."
        ::= { serviceCentreEntry 102 }

    serviceCentreAoUcp31TimeSpent OBJECT-TYPE
        SYNTAX  HighResTime
        ACCESS  read-only
        STATUS  mandatory
        DESCRIPTION
            "Total time spent in processing UCP alert requests."
        ::= { serviceCentreEntry 103 }

    serviceCentreAoUcp31ShortestRespTime OBJECT-TYPE
        SYNTAX  HighResTime
        ACCESS  read-only
        STATUS  mandatory
        DESCRIPTION
            "Shortest response time for processing a UCP alert
             request."
        ::= { serviceCentreEntry 104 }

    serviceCentreAoUcp31TimestampShortestResp OBJECT-TYPE
        SYNTAX  TimeStamp
        ACCESS  read-write
        STATUS  mandatory
        DESCRIPTION
            "Timestamp when shortest response time of a UCP alert
             request occurred. The shortest response time can be reset
             by setting shortest response timestamp to zero."
        ::= { serviceCentreEntry 105 }

    serviceCentreAoUcp31LongestRespTime OBJECT-TYPE
        SYNTAX  HighResTime
        ACCESS  read-only
        STATUS  mandatory
        DESCRIPTION
            "Longest response time for processing a UCP alert request."
        ::= { serviceCentreEntry 106 }

    serviceCentreAoUcp31TimestampLongestResp OBJECT-TYPE
        SYNTAX  TimeStamp
        ACCESS  read-write
        STATUS  mandatory
        DESCRIPTION
            "Timestamp when longest response time of a UCP alert
             request occurred. The longest response time can be reset by
             setting longest response timestamp to zero."
        ::= { serviceCentreEntry 107 }

    serviceCentreCntAoUcp51Request OBJECT-TYPE
        SYNTAX  Counter
        ACCESS  read-only
        STATUS  mandatory
        DESCRIPTION
            "Counts the total number of UCP submit sm requests which were
             sent to the Service Centre."
        ::= { serviceCentreEntry 108 }

    serviceCentreCntAoUcp51Ack OBJECT-TYPE
        SYNTAX  Counter
        ACCESS  read-only
        STATUS  mandatory
        DESCRIPTION
            "Counts the total number of positive UCP submit sm responses
             which were received from the Service Centre."
        ::= { serviceCentreEntry 109 }

    serviceCentreCntAoUcp51Nack OBJECT-TYPE
        SYNTAX  Counter
        ACCESS  read-only
        STATUS  mandatory
        DESCRIPTION
            "Counts the total number of negative UCP submit sm responses
             which were received from the Service Centre."
        ::= { serviceCentreEntry 110 }

    serviceCentreAoUcp51TimeSpent OBJECT-TYPE
        SYNTAX  HighResTime
        ACCESS  read-only
        STATUS  mandatory
        DESCRIPTION
            "Total time spent in processing UCP submit sm requests."
        ::= { serviceCentreEntry 111 }

    serviceCentreAoUcp51ShortestRespTime OBJECT-TYPE
        SYNTAX  HighResTime
        ACCESS  read-only
        STATUS  mandatory
        DESCRIPTION
            "Shortest response time for processing a UCP submit sm
             request."
        ::= { serviceCentreEntry 112 }

    serviceCentreAoUcp51TimestampShortestResp OBJECT-TYPE
        SYNTAX  TimeStamp
        ACCESS  read-write
        STATUS  mandatory
        DESCRIPTION
            "Timestamp when shortest response time of a UCP submit sm
             request occurred. The shortest response time can be reset
             by setting shortest response timestamp to zero."
        ::= { serviceCentreEntry 113 }

    serviceCentreAoUcp51LongestRespTime OBJECT-TYPE
        SYNTAX  HighResTime
        ACCESS  read-only
        STATUS  mandatory
        DESCRIPTION
            "Longest response time for processing a UCP submit sm
             request."
        ::= { serviceCentreEntry 114 }

    serviceCentreAoUcp51TimestampLongestResp OBJECT-TYPE
        SYNTAX  TimeStamp
        ACCESS  read-write
        STATUS  mandatory
        DESCRIPTION
            "Timestamp when longest response time of a UCP submit sm
             request occurred. The longest response time can be reset by
             setting longest response timestamp to zero."
        ::= { serviceCentreEntry 115 }

    serviceCentreCntAoUcp54Request OBJECT-TYPE
        SYNTAX  Counter
        ACCESS  read-only
        STATUS  mandatory
        DESCRIPTION
            "Counts the total number of UCP modify request which were
             sent to the Service Centre."
        ::= { serviceCentreEntry 116 }

    serviceCentreCntAoUcp54Ack OBJECT-TYPE
        SYNTAX  Counter
        ACCESS  read-only
        STATUS  mandatory
        DESCRIPTION
            "Counts the total number of positive UCP modify responses
             which were received from the Service Centre."
        ::= { serviceCentreEntry 117 }

    serviceCentreCntAoUcp54Nack OBJECT-TYPE
        SYNTAX  Counter
        ACCESS  read-only
        STATUS  mandatory
        DESCRIPTION
            "Counts the total number of negative UCP modify responses
             which were received from the Service Centre."
        ::= { serviceCentreEntry 118 }

    serviceCentreAoUcp54TimeSpent OBJECT-TYPE
        SYNTAX  HighResTime
        ACCESS  read-only
        STATUS  mandatory
        DESCRIPTION
            "Total time spent in processing UCP modify requests."
        ::= { serviceCentreEntry 119 }

    serviceCentreAoUcp54ShortestRespTime OBJECT-TYPE
        SYNTAX  HighResTime
        ACCESS  read-only
        STATUS  mandatory
        DESCRIPTION
            "Shortest response time for processing a UCP modify
             request."
        ::= { serviceCentreEntry 120 }

    serviceCentreAoUcp54TimestampShortestResp OBJECT-TYPE
        SYNTAX  TimeStamp
        ACCESS  read-write
        STATUS  mandatory
        DESCRIPTION
            "Timestamp when shortest response time of a UCP modify
             request occurred. The shortest response time can be reset
             by setting shortest response timestamp to zero."
        ::= { serviceCentreEntry 121 }

    serviceCentreAoUcp54LongestRespTime OBJECT-TYPE
        SYNTAX  HighResTime
        ACCESS  read-only
        STATUS  mandatory
        DESCRIPTION
            "Longest response time for processing a UCP modify
             request."
        ::= { serviceCentreEntry 122 }

    serviceCentreAoUcp54TimestampLongestResp OBJECT-TYPE
        SYNTAX  TimeStamp
        ACCESS  read-write
        STATUS  mandatory
        DESCRIPTION
            "Timestamp when longest response time of a UCP modify
             request occurred. The longest response time can be reset by
             setting longest response timestamp to zero."
        ::= { serviceCentreEntry 123 }

    serviceCentreCntAoUcp60Request OBJECT-TYPE
        SYNTAX  Counter
        ACCESS  read-only
        STATUS  mandatory
        DESCRIPTION
            "Counts the total number of UCP session management requests
             which were sent to the Service Centre."
        ::= { serviceCentreEntry 124 }

    serviceCentreCntAoUcp60Ack OBJECT-TYPE
        SYNTAX  Counter
        ACCESS  read-only
        STATUS  mandatory
        DESCRIPTION
            "Counts the total number of positive UCP session management
             responses which were received from the Service Centre."
        ::= { serviceCentreEntry 125 }

    serviceCentreCntAoUcp60Nack OBJECT-TYPE
        SYNTAX  Counter
        ACCESS  read-only
        STATUS  mandatory
        DESCRIPTION
            "Counts the total number of negative UCP session management
             responses which were received from the Service Centre."
        ::= { serviceCentreEntry 126 }

    serviceCentreAoUcp60TimeSpent OBJECT-TYPE
        SYNTAX  HighResTime
        ACCESS  read-only
        STATUS  mandatory
        DESCRIPTION
            "Total time spent in processing UCP session management
             requests."
        ::= { serviceCentreEntry 127 }

    serviceCentreAoUcp60ShortestRespTime OBJECT-TYPE
        SYNTAX  HighResTime
        ACCESS  read-only
        STATUS  mandatory
        DESCRIPTION
            "Shortest response time for processing a UCP session
             management request."
        ::= { serviceCentreEntry 128 }

    serviceCentreAoUcp60TimestampShortestResp OBJECT-TYPE
        SYNTAX  TimeStamp
        ACCESS  read-write
        STATUS  mandatory
        DESCRIPTION
            "Timestamp when shortest response time of a UCP session
             management request occurred. The shortest response time can
             be reset by setting shortest response timestamp to zero."
        ::= { serviceCentreEntry 129 }

    serviceCentreAoUcp60LongestRespTime OBJECT-TYPE
        SYNTAX  HighResTime
        ACCESS  read-only
        STATUS  mandatory
        DESCRIPTION
            "Longest response time for processing a UCP session
             management request."
        ::= { serviceCentreEntry 130 }

    serviceCentreAoUcp60TimestampLongestResp OBJECT-TYPE
        SYNTAX  TimeStamp
        ACCESS  read-write
        STATUS  mandatory
        DESCRIPTION
            "Timestamp when longest response time of a UCP session
             management request occurred. The longest response time can
             be reset by setting longest response timestamp to zero."
        ::= { serviceCentreEntry 131 }

    serviceCentreCntAoUcpOtherRequest OBJECT-TYPE
        SYNTAX  Counter
        ACCESS  read-only
        STATUS  mandatory
        DESCRIPTION
            "Counts the total number of unknown UCP requests which were
             sent to the Service Centre."
        ::= { serviceCentreEntry 132 }

    serviceCentreCntAoUcpOtherAck OBJECT-TYPE
        SYNTAX  Counter
        ACCESS  read-only
        STATUS  mandatory
        DESCRIPTION
            "Counts the total number of positive unknown UCP responses
             which were received from the Service Centre."
        ::= { serviceCentreEntry 133 }

    serviceCentreCntAoUcpOtherNack OBJECT-TYPE
        SYNTAX  Counter
        ACCESS  read-only
        STATUS  mandatory
        DESCRIPTION
            "Counts the total number of negative unknown UCP responses
             which were received from the Service Centre."
        ::= { serviceCentreEntry 134 }

    serviceCentreAoUcpOtherTimeSpent OBJECT-TYPE
        SYNTAX  HighResTime
        ACCESS  read-only
        STATUS  mandatory
        DESCRIPTION
            "Total time spent in processing unknown UCP requests."
        ::= { serviceCentreEntry 135 }

    serviceCentreAoUcpOtherShortestRespTime OBJECT-TYPE
        SYNTAX  HighResTime
        ACCESS  read-only
        STATUS  mandatory
        DESCRIPTION
            "Shortest response time for processing an unknown UCP
             request."
        ::= { serviceCentreEntry 136 }

    serviceCentreAoUcpOtherTimestampShortestResp OBJECT-TYPE
        SYNTAX  TimeStamp
        ACCESS  read-write
        STATUS  mandatory
        DESCRIPTION
            "Timestamp when shortest response time of an unknown UCP
             request occurred. The shortest response time can be reset
             by setting shortest response timestamp to zero."
        ::= { serviceCentreEntry 137 }

    serviceCentreAoUcpOtherLongestRespTime OBJECT-TYPE
        SYNTAX  HighResTime
        ACCESS  read-only
        STATUS  mandatory
        DESCRIPTION
            "Longest response time for processing an unknown UCP
             request."
        ::= { serviceCentreEntry 138 }

    serviceCentreAoUcpOtherTimestampLongestResp OBJECT-TYPE
        SYNTAX  TimeStamp
        ACCESS  read-write
        STATUS  mandatory
        DESCRIPTION
            "Timestamp when longest response time of an unknown UCP
             request occurred. The longest response time can be reset by
             setting longest response timestamp to zero."
        ::= { serviceCentreEntry 139 }

    serviceCentreCntAoUcp55Request OBJECT-TYPE
        SYNTAX  Counter
        ACCESS  read-only
        STATUS  mandatory
        DESCRIPTION
            "Counts the total number of UCP inquiry message requests
             which were sent to the Service Centre."
        ::= { serviceCentreEntry 140 }

    serviceCentreCntAoUcp55Ack OBJECT-TYPE
        SYNTAX  Counter
        ACCESS  read-only
        STATUS  mandatory
        DESCRIPTION
            "Counts the total number of positive UCP inquiry message
             responses which were received from the Service Centre."
        ::= { serviceCentreEntry 141 }

    serviceCentreCntAoUcp55Nack OBJECT-TYPE
        SYNTAX  Counter
        ACCESS  read-only
        STATUS  mandatory
        DESCRIPTION
            "Counts the total number of negative UCP inquiry message
             responses which were received from the Service Centre."
        ::= { serviceCentreEntry 142 }

    serviceCentreAoUcp55TimeSpent OBJECT-TYPE
        SYNTAX  HighResTime
        ACCESS  read-only
        STATUS  mandatory
        DESCRIPTION
            "Total time spent in processing UCP inquiry message
             requests."
        ::= { serviceCentreEntry 143 }

    serviceCentreAoUcp55ShortestRespTime OBJECT-TYPE
        SYNTAX  HighResTime
        ACCESS  read-only
        STATUS  mandatory
        DESCRIPTION
            "Shortest response time for processing a UCP inquiry message
             request."
        ::= { serviceCentreEntry 144 }

    serviceCentreAoUcp55TimestampShortestResp OBJECT-TYPE
        SYNTAX  TimeStamp
        ACCESS  read-write
        STATUS  mandatory
        DESCRIPTION
            "Timestamp when shortest response time of a UCP inquiry
             message request occurred. The shortest response time can be
             reset by setting shortest response timestamp to zero."
        ::= { serviceCentreEntry 145 }

    serviceCentreAoUcp55LongestRespTime OBJECT-TYPE
        SYNTAX  HighResTime
        ACCESS  read-only
        STATUS  mandatory
        DESCRIPTION
            "Longest response time for processing a UCP inquiry message
             request."
        ::= { serviceCentreEntry 146 }

    serviceCentreAoUcp55TimestampLongestResp OBJECT-TYPE
        SYNTAX  TimeStamp
        ACCESS  read-write
        STATUS  mandatory
        DESCRIPTION
            "Timestamp when longest response time of a UCP inquiry
             message request occurred. The longest response time can be
             reset by setting longest response timestamp to zero."
        ::= { serviceCentreEntry 147 }

    serviceCentreCntAoUcp56Request OBJECT-TYPE
        SYNTAX  Counter
        ACCESS  read-only
        STATUS  mandatory
        DESCRIPTION
            "Counts the total number of UCP delete message requests
             which were sent to the Service Centre."
        ::= { serviceCentreEntry 148 }

    serviceCentreCntAoUcp56Ack OBJECT-TYPE
        SYNTAX  Counter
        ACCESS  read-only
        STATUS  mandatory
        DESCRIPTION
            "Counts the total number of positive UCP delete message
             responses which were received from the Service Centre."
        ::= { serviceCentreEntry 149 }

    serviceCentreCntAoUcp56Nack OBJECT-TYPE
        SYNTAX  Counter
        ACCESS  read-only
        STATUS  mandatory
        DESCRIPTION
            "Counts the total number of negative UCP delete message
             responses which were received from the Service Centre."
        ::= { serviceCentreEntry 150 }

    serviceCentreAoUcp56TimeSpent OBJECT-TYPE
        SYNTAX  HighResTime
        ACCESS  read-only
        STATUS  mandatory
        DESCRIPTION
            "Total time spent in processing UCP delete message
             requests."
        ::= { serviceCentreEntry 151 }

    serviceCentreAoUcp56ShortestRespTime OBJECT-TYPE
        SYNTAX  HighResTime
        ACCESS  read-only
        STATUS  mandatory
        DESCRIPTION
            "Shortest response time for processing a UCP delete message
             request."
        ::= { serviceCentreEntry 152 }

    serviceCentreAoUcp56TimestampShortestResp OBJECT-TYPE
        SYNTAX  TimeStamp
        ACCESS  read-write
        STATUS  mandatory
        DESCRIPTION
            "Timestamp when shortest response time of a UCP delete
             message request occurred. The shortest response time can be
             reset by setting shortest response timestamp to zero."
        ::= { serviceCentreEntry 153 }

    serviceCentreAoUcp56LongestRespTime OBJECT-TYPE
        SYNTAX  HighResTime
        ACCESS  read-only
        STATUS  mandatory
        DESCRIPTION
            "Longest response time for processing a UCP delete message
             request."
        ::= { serviceCentreEntry 154 }

    serviceCentreAoUcp56TimestampLongestResp OBJECT-TYPE
        SYNTAX  TimeStamp
        ACCESS  read-write
        STATUS  mandatory
        DESCRIPTION
            "Timestamp when longest response time of a UCP delete
             message request occurred. The longest response time can be
             reset by setting longest response timestamp to zero."
        ::= { serviceCentreEntry 155 }

    serviceCentreCntAoSmppSubmitSmRequest OBJECT-TYPE
        SYNTAX  Counter
        ACCESS  read-only
        STATUS  mandatory
        DESCRIPTION
            "Counts the total number of SMPP submit sm requests which
             were sent to the Service Centre."
        ::= { serviceCentreEntry 200 }

    serviceCentreCntAoSmppSubmitSmAck OBJECT-TYPE
        SYNTAX  Counter
        ACCESS  read-only
        STATUS  mandatory
        DESCRIPTION
            "Counts the total number of positive SMPP submit sm
             responses which were received from the Service Centre."
        ::= { serviceCentreEntry 201 }

    serviceCentreCntAoSmppSubmitSmNack OBJECT-TYPE
        SYNTAX  Counter
        ACCESS  read-only
        STATUS  mandatory
        DESCRIPTION
            "Counts the total number of negative SMPP submit sm
             responses which were received from the Service Centre."
        ::= { serviceCentreEntry 202 }

    serviceCentreAoSmppSubmitSmTimeSpent OBJECT-TYPE
        SYNTAX  HighResTime
        ACCESS  read-only
        STATUS  mandatory
        DESCRIPTION
            "Total time spent in processing SMPP submit sm requests."
        ::= { serviceCentreEntry 203 }

    serviceCentreAoSmppSubmitSmShortestRespTime OBJECT-TYPE
        SYNTAX  HighResTime
        ACCESS  read-only
        STATUS  mandatory
        DESCRIPTION
            "Shortest response time for processing an SMPP submit sm
             request."
        ::= { serviceCentreEntry 204 }

    serviceCentreAoSmppSubmitSmTimestampShortestResp OBJECT-TYPE
        SYNTAX  TimeStamp
        ACCESS  read-write
        STATUS  mandatory
        DESCRIPTION
            "Timestamp when shortest response time of an SMPP submit sm
             request occurred. The shortest response time can be reset
             by setting shortest response timestamp to zero."
        ::= { serviceCentreEntry 205 }

    serviceCentreAoSmppSubmitSmLongestRespTime OBJECT-TYPE
        SYNTAX  HighResTime
        ACCESS  read-only
        STATUS  mandatory
        DESCRIPTION
            "Longest response time for processing an SMPP submit sm
             requests."
        ::= { serviceCentreEntry 206 }

    serviceCentreAoSmppSubmitSmTimestampLongestResp OBJECT-TYPE
        SYNTAX  TimeStamp
        ACCESS  read-write
        STATUS  mandatory
        DESCRIPTION
            "Timestamp when longest response time of an SMPP submit sm
             request occurred. The longest response time can be reset by
             setting the related  timestamp to zero."
        ::= { serviceCentreEntry 207 }

    serviceCentreCntAoSmppDataSmRequest OBJECT-TYPE
        SYNTAX  Counter
        ACCESS  read-only
        STATUS  mandatory
        DESCRIPTION
            "Counts the total number of SMPP data sm requests which were
             sent to the Service Centre."
        ::= { serviceCentreEntry 208 }

    serviceCentreCntAoSmppDataSmAck OBJECT-TYPE
        SYNTAX  Counter
        ACCESS  read-only
        STATUS  mandatory
        DESCRIPTION
            "Counts the total number of positive SMPP data sm responses
             which were received from the Service Centre."
        ::= { serviceCentreEntry 209 }

    serviceCentreCntAoSmppDataSmNack OBJECT-TYPE
        SYNTAX  Counter
        ACCESS  read-only
        STATUS  mandatory
        DESCRIPTION
            "Counts the total number of negative SMPP data sm responses
             which were received from the Service Centre."
        ::= { serviceCentreEntry 210 }

    serviceCentreAoSmppDataSmTimeSpent OBJECT-TYPE
        SYNTAX  HighResTime
        ACCESS  read-only
        STATUS  mandatory
        DESCRIPTION
            "Total time spent in processing SMPP data sm requests."
        ::= { serviceCentreEntry 211 }

    serviceCentreAoSmppDataSmShortestRespTime OBJECT-TYPE
        SYNTAX  HighResTime
        ACCESS  read-only
        STATUS  mandatory
        DESCRIPTION
            "Shortest response time for processing an SMPP data sm
             request."
        ::= { serviceCentreEntry 212 }

    serviceCentreAoSmppDataSmTimestampShortestResp OBJECT-TYPE
        SYNTAX  TimeStamp
        ACCESS  read-write
        STATUS  mandatory
        DESCRIPTION
            "Timestamp when shortest response time of an SMPP data sm
             request occurred. The shortest response time can be reset
             by setting shortest response timestamp to zero."
        ::= { serviceCentreEntry 213 }

    serviceCentreAoSmppDataSmLongestRespTime OBJECT-TYPE
        SYNTAX  HighResTime
        ACCESS  read-only
        STATUS  mandatory
        DESCRIPTION
            "Longest response time for processing an SMPP data sm
             request."
        ::= { serviceCentreEntry 214 }

    serviceCentreAoSmppDataSmTimestampLongestResp OBJECT-TYPE
        SYNTAX  TimeStamp
        ACCESS  read-write
        STATUS  mandatory
        DESCRIPTION
            "Timestamp when longest response time of an SMPP data sm
             request occurred. The longest response time can be reset by
             setting longest response timestamp to zero."
        ::= { serviceCentreEntry 215 }

    serviceCentreCntAoSmppBindRxRequest OBJECT-TYPE
        SYNTAX  Counter
        ACCESS  read-only
        STATUS  mandatory
        DESCRIPTION
            "Counts the total number of SMPP bind receiver requests
             which were sent to the Service Centre."
        ::= { serviceCentreEntry 216 }

    serviceCentreCntAoSmppBindRxAck OBJECT-TYPE
        SYNTAX  Counter
        ACCESS  read-only
        STATUS  mandatory
        DESCRIPTION
            "Counts the total number of positive SMPP bind receiver
             responses which were received from the Service Centre."
        ::= { serviceCentreEntry 217 }

    serviceCentreCntAoSmppBindRxNack OBJECT-TYPE
        SYNTAX  Counter
        ACCESS  read-only
        STATUS  mandatory
        DESCRIPTION
            "Counts the total number of negative SMPP bind receiver
             responses which were received from the Service Centre."
        ::= { serviceCentreEntry 218 }

    serviceCentreAoSmppBindRxTimeSpent OBJECT-TYPE
        SYNTAX  HighResTime
        ACCESS  read-only
        STATUS  mandatory
        DESCRIPTION
            "Total time spent in processing SMPP bind receiver
             requests."
        ::= { serviceCentreEntry 219 }

    serviceCentreAoSmppBindRxShortestRespTime OBJECT-TYPE
        SYNTAX  HighResTime
        ACCESS  read-only
        STATUS  mandatory
        DESCRIPTION
            "Shortest response time for processing an SMPP bind receiver
             request."
        ::= { serviceCentreEntry 220 }

    serviceCentreAoSmppBindRxTimestampShortestResp OBJECT-TYPE
        SYNTAX  TimeStamp
        ACCESS  read-write
        STATUS  mandatory
        DESCRIPTION
            "Timestamp when shortest response time of an SMPP bind
             receiver request occurred. The shortest response time can
             be reset by setting shortest response timestamp to zero."
        ::= { serviceCentreEntry 221 }

    serviceCentreAoSmppBindRxLongestRespTime OBJECT-TYPE
        SYNTAX  HighResTime
        ACCESS  read-only
        STATUS  mandatory
        DESCRIPTION
            "Longest response time for processing an SMPP bind receiver
             request."
        ::= { serviceCentreEntry 222 }

    serviceCentreAoSmppBindRxTimestampLongestResp OBJECT-TYPE
        SYNTAX  TimeStamp
        ACCESS  read-write
        STATUS  mandatory
        DESCRIPTION
            "Timestamp when longest response time of an SMPP bind
             receiver request occurred. The longest response time can be
             reset by setting the related  timestamp to zero."
        ::= { serviceCentreEntry 223 }

    serviceCentreCntAoSmppBindTxRequest OBJECT-TYPE
        SYNTAX  Counter
        ACCESS  read-only
        STATUS  mandatory
        DESCRIPTION
            "Counts the total number of SMPP bind transmitter requests
             which were sent to the Service Centre."
        ::= { serviceCentreEntry 224 }

    serviceCentreCntAoSmppBindTxAck OBJECT-TYPE
        SYNTAX  Counter
        ACCESS  read-only
        STATUS  mandatory
        DESCRIPTION
            "Counts the total number of positive SMPP bind transmitter
             responses which were received from the Service Centre."
        ::= { serviceCentreEntry 225 }

    serviceCentreCntAoSmppBindTxNack OBJECT-TYPE
        SYNTAX  Counter
        ACCESS  read-only
        STATUS  mandatory
        DESCRIPTION
            "Counts the total number of negative SMPP bind transmitter
             responses which were received from the Service Centre."
        ::= { serviceCentreEntry 226 }

    serviceCentreAoSmppBindTxTimeSpent OBJECT-TYPE
        SYNTAX  HighResTime
        ACCESS  read-only
        STATUS  mandatory
        DESCRIPTION
            "Total time spent in processing SMPP bind transmitter
             requests."
        ::= { serviceCentreEntry 227 }

    serviceCentreAoSmppBindTxShortestRespTime OBJECT-TYPE
        SYNTAX  HighResTime
        ACCESS  read-only
        STATUS  mandatory
        DESCRIPTION
            "Shortest response time for processing an SMPP bind
             transmitter request."
        ::= { serviceCentreEntry 228 }

    serviceCentreAoSmppBindTxTimestampShortestResp OBJECT-TYPE
        SYNTAX  TimeStamp
        ACCESS  read-write
        STATUS  mandatory
        DESCRIPTION
            "Timestamp when shortest response time of an SMPP bind
             transmitter request occurred. The shortest response time
             can be reset by setting shortest response timestamp to
             zero."
        ::= { serviceCentreEntry 229 }

    serviceCentreAoSmppBindTxLongestRespTime OBJECT-TYPE
        SYNTAX  HighResTime
        ACCESS  read-only
        STATUS  mandatory
        DESCRIPTION
            "Longest response time for processing an SMPP bind
             transmitter request."
        ::= { serviceCentreEntry 230 }

    serviceCentreAoSmppBindTxTimestampLongestResp OBJECT-TYPE
        SYNTAX  TimeStamp
        ACCESS  read-write
        STATUS  mandatory
        DESCRIPTION
            "Timestamp when longest response time of an SMPP bind
             transmitter request occurred. The longest response time can
             be reset by setting longest response timestamp to zero."
        ::= { serviceCentreEntry 231 }

    serviceCentreCntAoSmppBindTrxRequest OBJECT-TYPE
        SYNTAX  Counter
        ACCESS  read-only
        STATUS  mandatory
        DESCRIPTION
            "Counts the total number of SMPP bind transceiver requests
             which were sent to the Service Centre."
        ::= { serviceCentreEntry 232 }

    serviceCentreCntAoSmppBindTrxAck OBJECT-TYPE
        SYNTAX  Counter
        ACCESS  read-only
        STATUS  mandatory
        DESCRIPTION
            "Counts the total number of positive SMPP bind transceiver 
             responses which were received from the Service Centre."
        ::= { serviceCentreEntry 233 }

    serviceCentreCntAoSmppBindTrxNack OBJECT-TYPE
        SYNTAX  Counter
        ACCESS  read-only
        STATUS  mandatory
        DESCRIPTION
            "Counts the total number of negative SMPP bind transceiver 
             responses which were received from the Service Centre."
        ::= { serviceCentreEntry 234 }

    serviceCentreAoSmppBindTrxTimeSpent OBJECT-TYPE
        SYNTAX  HighResTime
        ACCESS  read-only
        STATUS  mandatory
        DESCRIPTION
            "Total time spent in processing SMPP bind transceiver 
             requests."
        ::= { serviceCentreEntry 235 }

    serviceCentreAoSmppBindTrxShortestRespTime OBJECT-TYPE
        SYNTAX  HighResTime
        ACCESS  read-only
        STATUS  mandatory
        DESCRIPTION
            "Shortest response time for processing an SMPP bind
             transceiver request."
        ::= { serviceCentreEntry 236 }

    serviceCentreAoSmppBindTrxTimestampShortestResp OBJECT-TYPE
        SYNTAX  TimeStamp
        ACCESS  read-write
        STATUS  mandatory
        DESCRIPTION
            "Timestamp when shortest response time of an SMPP bind
             transceiver request occurred. The shortest response time
             can be reset by setting shortest response timestamp to
             zero."
        ::= { serviceCentreEntry 237 }

    serviceCentreAoSmppBindTrxLongestRespTime OBJECT-TYPE
        SYNTAX  HighResTime
        ACCESS  read-only
        STATUS  mandatory
        DESCRIPTION
            "Longest response time for processing an SMPP bind
             transceiver requests."
        ::= { serviceCentreEntry 238 }

    serviceCentreAoSmppBindTrxTimestampLongestResp OBJECT-TYPE
        SYNTAX  TimeStamp
        ACCESS  read-write
        STATUS  mandatory
        DESCRIPTION
            "Timestamp when longest response time of an SMPP bind
             transceiver request occurred. The longest response time can
             be reset by setting the related  timestamp to zero."
        ::= { serviceCentreEntry 239 }

    serviceCentreCntAoSmppUnbindRequest OBJECT-TYPE
        SYNTAX  Counter
        ACCESS  read-only
        STATUS  mandatory
        DESCRIPTION
            "Counts the total number of SMPP unbind request which were
             sent to the Service Centre."
        ::= { serviceCentreEntry 240 }

    serviceCentreCntAoSmppUnbindAck OBJECT-TYPE
        SYNTAX  Counter
        ACCESS  read-only
        STATUS  mandatory
        DESCRIPTION
            "Counts the total number of positive SMPP unbind responses
             which were received from the Service Centre."
        ::= { serviceCentreEntry 241 }

    serviceCentreCntAoSmppUnbindNack OBJECT-TYPE
        SYNTAX  Counter
        ACCESS  read-only
        STATUS  mandatory
        DESCRIPTION
            "Counts the total number of negative SMPP unbind responses
             which were received from the Service Centre."
        ::= { serviceCentreEntry 242 }

    serviceCentreAoSmppUnbindTimeSpent OBJECT-TYPE
        SYNTAX  HighResTime
        ACCESS  read-only
        STATUS  mandatory
        DESCRIPTION
            "Total time spent in processing SMPP unbind requests."
        ::= { serviceCentreEntry 243 }

    serviceCentreAoSmppUnbindShortestRespTime OBJECT-TYPE
        SYNTAX  HighResTime
        ACCESS  read-only
        STATUS  mandatory
        DESCRIPTION
            "Shortest response time for processing an SMPP unbind
             request."
        ::= { serviceCentreEntry 244 }

    serviceCentreAoSmppUnbindTimestampShortestResp OBJECT-TYPE
        SYNTAX  TimeStamp
        ACCESS  read-write
        STATUS  mandatory
        DESCRIPTION
            "Timestamp when shortest response time of an SMPP unbind
             request occurred. The shortest response time can be reset
             by setting shortest response timestamp to zero."
        ::= { serviceCentreEntry 245 }

    serviceCentreAoSmppUnbindLongestRespTime OBJECT-TYPE
        SYNTAX  HighResTime
        ACCESS  read-only
        STATUS  mandatory
        DESCRIPTION
            "Longest response time for processing an SMPP unbind
             request."
        ::= { serviceCentreEntry 246 }

    serviceCentreAoSmppUnbindTimestampLongestResp OBJECT-TYPE
        SYNTAX  TimeStamp
        ACCESS  read-write
        STATUS  mandatory
        DESCRIPTION
            "Timestamp when longest response time of an SMPP unbind
             request occurred. The longest response time can be reset by
             setting longest response timestamp to zero."
        ::= { serviceCentreEntry 247 }

    serviceCentreCntAoSmppQuerySmRequest OBJECT-TYPE
        SYNTAX  Counter
        ACCESS  read-only
        STATUS  mandatory
        DESCRIPTION
            "Counts the total number of SMPP query sm requests which were
             sent to the Service Centre."
        ::= { serviceCentreEntry 248 }

    serviceCentreCntAoSmppQuerySmAck OBJECT-TYPE
        SYNTAX  Counter
        ACCESS  read-only
        STATUS  mandatory
        DESCRIPTION
            "Counts the total number of positive SMPP query sm responses
             which were received from the Service Centre."
        ::= { serviceCentreEntry 249 }

    serviceCentreCntAoSmppQuerySmNack OBJECT-TYPE
        SYNTAX  Counter
        ACCESS  read-only
        STATUS  mandatory
        DESCRIPTION
            "Counts the total number of negative SMPP query sm responses
             which were received from the Service Centre."
        ::= { serviceCentreEntry 250 }

    serviceCentreAoSmppQuerySmTimeSpent OBJECT-TYPE
        SYNTAX  HighResTime
        ACCESS  read-only
        STATUS  mandatory
        DESCRIPTION
            "Total time spent in processing SMPP query sm requests."
        ::= { serviceCentreEntry 251 }

    serviceCentreAoSmppQuerySmShortestRespTime OBJECT-TYPE
        SYNTAX  HighResTime
        ACCESS  read-only
        STATUS  mandatory
        DESCRIPTION
            "Shortest response time for processing an SMPP query sm
             request."
        ::= { serviceCentreEntry 252 }

    serviceCentreAoSmppQuerySmTimestampShortestResp OBJECT-TYPE
        SYNTAX  TimeStamp
        ACCESS  read-write
        STATUS  mandatory
        DESCRIPTION
            "Timestamp when shortest response time of an SMPP query sm
             request occurred. The shortest response time can be reset
             by setting shortest response timestamp to zero."
        ::= { serviceCentreEntry 253 }

    serviceCentreAoSmppQuerySmLongestRespTime OBJECT-TYPE
        SYNTAX  HighResTime
        ACCESS  read-only
        STATUS  mandatory
        DESCRIPTION
            "Longest response time for processing an SMPP query sm
             request."
        ::= { serviceCentreEntry 254 }

    serviceCentreAoSmppQuerySmTimestampLongestResp OBJECT-TYPE
        SYNTAX  TimeStamp
        ACCESS  read-write
        STATUS  mandatory
        DESCRIPTION
            "Timestamp when longest response time of an SMPP query sm
             request occurred. The longest response time can be reset by
             setting the related  timestamp to zero."
        ::= { serviceCentreEntry 255 }

    serviceCentreCntAoSmppReplaceSmRequest OBJECT-TYPE
        SYNTAX  Counter
        ACCESS  read-only
        STATUS  mandatory
        DESCRIPTION
            "Counts the total number of SMPP replace sm requests which
             were sent to the Service Centre."
        ::= { serviceCentreEntry 256 }

    serviceCentreCntAoSmppReplaceSmAck OBJECT-TYPE
        SYNTAX  Counter
        ACCESS  read-only
        STATUS  mandatory
        DESCRIPTION
            "Counts the total number of positive SMPP replace sm
             responses which were received from the Service Centre."
        ::= { serviceCentreEntry 257 }

    serviceCentreCntAoSmppReplaceSmNack OBJECT-TYPE
        SYNTAX  Counter
        ACCESS  read-only
        STATUS  mandatory
        DESCRIPTION
            "Counts the total number of negative SMPP replace sm
             responses which were received from the Service Centre."
        ::= { serviceCentreEntry 258 }

    serviceCentreAoSmppReplaceSmTimeSpent OBJECT-TYPE
        SYNTAX  HighResTime
        ACCESS  read-only
        STATUS  mandatory
        DESCRIPTION
            "Total time spent in processing SMPP replace sm requests."
        ::= { serviceCentreEntry 259 }

    serviceCentreAoSmppReplaceSmShortestRespTime OBJECT-TYPE
        SYNTAX  HighResTime
        ACCESS  read-only
        STATUS  mandatory
        DESCRIPTION
            "Shortest response time for processing an SMPP replace sm
             request."
        ::= { serviceCentreEntry 260 }

    serviceCentreAoSmppReplaceSmTimestampShortestResp OBJECT-TYPE
        SYNTAX  TimeStamp
        ACCESS  read-write
        STATUS  mandatory
        DESCRIPTION
            "Timestamp when shortest response time of an SMPP replace sm
             request occurred. The shortest response time can be reset
             by setting shortest response timestamp to zero."
        ::= { serviceCentreEntry 261 }

    serviceCentreAoSmppReplaceSmLongestRespTime OBJECT-TYPE
        SYNTAX  HighResTime
        ACCESS  read-only
        STATUS  mandatory
        DESCRIPTION
            "Longest response time for processing an SMPP replace sm
             request."
        ::= { serviceCentreEntry 262 }

    serviceCentreAoSmppReplaceSmTimestampLongestResp OBJECT-TYPE
        SYNTAX  TimeStamp
        ACCESS  read-write
        STATUS  mandatory
        DESCRIPTION
            "Timestamp when longest response time of an SMPP replace sm
             request occurred. The longest response time can be reset by
             setting longest response timestamp to zero."
        ::= { serviceCentreEntry 263 }

    serviceCentreCntAoSmppCancelSmRequest OBJECT-TYPE
        SYNTAX  Counter
        ACCESS  read-only
        STATUS  mandatory
        DESCRIPTION
            "Counts the total number of SMPP cancel sm requests which
             were sent to the Service Centre."
        ::= { serviceCentreEntry 264 }

    serviceCentreCntAoSmppCancelSmAck OBJECT-TYPE
        SYNTAX  Counter
        ACCESS  read-only
        STATUS  mandatory
        DESCRIPTION
            "Counts the total number of positive SMPP cancel sm
             responses which were received from the Service Centre."
        ::= { serviceCentreEntry 265 }

    serviceCentreCntAoSmppCancelSmNack OBJECT-TYPE
        SYNTAX  Counter
        ACCESS  read-only
        STATUS  mandatory
        DESCRIPTION
            "Counts the total number of negative SMPP cancel sm
             responses which were received from the Service Centre."
        ::= { serviceCentreEntry 266 }

    serviceCentreAoSmppCancelSmTimeSpent OBJECT-TYPE
        SYNTAX  HighResTime
        ACCESS  read-only
        STATUS  mandatory
        DESCRIPTION
            "Total time spent in processing SMPP cancel sm requests."
        ::= { serviceCentreEntry 267 }

    serviceCentreAoSmppCancelSmShortestRespTime OBJECT-TYPE
        SYNTAX  HighResTime
        ACCESS  read-only
        STATUS  mandatory
        DESCRIPTION
            "Shortest response time for processing an SMPP cancel sm
             requests. "
        ::= { serviceCentreEntry 268 }

    serviceCentreAoSmppCancelSmTimestampShortestResp OBJECT-TYPE
        SYNTAX  TimeStamp
        ACCESS  read-write
        STATUS  mandatory
        DESCRIPTION
            "Timestamp when longest response time of an SMPP cancel sm
             request occurred. The shortest response time can be reset
             by setting shortest response timestamp to zero."
        ::= { serviceCentreEntry 269 }

    serviceCentreAoSmppCancelSmLongestRespTime OBJECT-TYPE
        SYNTAX  HighResTime
        ACCESS  read-only
        STATUS  mandatory
        DESCRIPTION
            "Longest response time for processing an SMPP cancel sm
             request."
        ::= { serviceCentreEntry 270 }

    serviceCentreAoSmppCancelSmTimestampLongestResp OBJECT-TYPE
        SYNTAX  TimeStamp
        ACCESS  read-write
        STATUS  mandatory
        DESCRIPTION
            "Timestamp when longest response time of an SMPP cancel sm
             request occurred. The longest response time can be reset by
             setting the related  timestamp to zero."
        ::= { serviceCentreEntry 271 }

    serviceCentreCntAoSmppEnquireLinkRequest OBJECT-TYPE
        SYNTAX  Counter
        ACCESS  read-only
        STATUS  mandatory
        DESCRIPTION
            "Counts the total number of SMPP enquire link requests which
             were sent to the Service Centre."
        ::= { serviceCentreEntry 272 }

    serviceCentreCntAoSmppEnquireLinkAck OBJECT-TYPE
        SYNTAX  Counter
        ACCESS  read-only
        STATUS  mandatory
        DESCRIPTION
            "Counts the total number of positive SMPP enquire link
             responses which were received from the Service Centre."
        ::= { serviceCentreEntry 273 }

    serviceCentreCntAoSmppEnquireLinkNack OBJECT-TYPE
        SYNTAX  Counter
        ACCESS  read-only
        STATUS  mandatory
        DESCRIPTION
            "Counts the total number of negative SMPP enquire link
             responses which were received from the Service Centre."
        ::= { serviceCentreEntry 274 }

    serviceCentreAoSmppEnquireLinkTimeSpent OBJECT-TYPE
        SYNTAX  HighResTime
        ACCESS  read-only
        STATUS  mandatory
        DESCRIPTION
            "Total time spent in processing SMPP enquire link requests."
        ::= { serviceCentreEntry 275 }

    serviceCentreAoSmppEnquireLinkShortestRespTime OBJECT-TYPE
        SYNTAX  HighResTime
        ACCESS  read-only
        STATUS  mandatory
        DESCRIPTION
            "Shortest response time for processing an SMPP enquire link
             requests. "
        ::= { serviceCentreEntry 276 }

    serviceCentreAoSmppEnquireLinkTimestampShortestResp OBJECT-TYPE
        SYNTAX  TimeStamp
        ACCESS  read-write
        STATUS  mandatory
        DESCRIPTION
            "Timestamp when longest response time of an SMPP enquire
             link request occurred. The shortest response time can be
             reset by setting shortest response timestamp to zero."
        ::= { serviceCentreEntry 277 }

    serviceCentreAoSmppEnquireLinkLongestRespTime OBJECT-TYPE
        SYNTAX  HighResTime
        ACCESS  read-only
        STATUS  mandatory
        DESCRIPTION
            "Longest response time for processing an SMPP enquire link
             request."
        ::= { serviceCentreEntry 278 }

    serviceCentreAoSmppEnquireLinkTimestampLongestResp OBJECT-TYPE
        SYNTAX  TimeStamp
        ACCESS  read-write
        STATUS  mandatory
        DESCRIPTION
            "Timestamp when longest response time of an SMPP enquire
             link request occurred. The longest response time can be
             reset by setting the related  timestamp to zero."
        ::= { serviceCentreEntry 279 }

    serviceCentreCntAoSmppOtherRequest OBJECT-TYPE
        SYNTAX  Counter
        ACCESS  read-only
        STATUS  mandatory
        DESCRIPTION
            "Counts the total number of SMPP unknown requests which were
             sent to the Service Centre."
        ::= { serviceCentreEntry 280 }

    serviceCentreCntAoSmppOtherAck OBJECT-TYPE
        SYNTAX  Counter
        ACCESS  read-only
        STATUS  mandatory
        DESCRIPTION
            "Counts the total number of positive SMPP unknown responses
             which were received from the Service Centre."
        ::= { serviceCentreEntry 281 }

    serviceCentreCntAoSmppOtherNack OBJECT-TYPE
        SYNTAX  Counter
        ACCESS  read-only
        STATUS  mandatory
        DESCRIPTION
            "Counts the total number of negative SMPP unknown responses
             which were received from the Service Centre."
        ::= { serviceCentreEntry 282 }

    serviceCentreAoSmppOtherTimeSpent OBJECT-TYPE
        SYNTAX  HighResTime
        ACCESS  read-only
        STATUS  mandatory
        DESCRIPTION
            "Total time spent in processing SMPP unknown requests."
        ::= { serviceCentreEntry 283 }

    serviceCentreAoSmppOtherShortestRespTime OBJECT-TYPE
        SYNTAX  HighResTime
        ACCESS  read-only
        STATUS  mandatory
        DESCRIPTION
            "Shortest response time for processing an SMPP unknown
             request."
        ::= { serviceCentreEntry 284 }

    serviceCentreAoSmppOtherTimestampShortestResp OBJECT-TYPE
        SYNTAX  TimeStamp
        ACCESS  read-write
        STATUS  mandatory
        DESCRIPTION
            "Timestamp when shortest response time of an SMPP unknown
             request occurred. The shortest response time can be reset
             by setting shortest response timestamp to zero."
        ::= { serviceCentreEntry 285 }

    serviceCentreAoSmppOtherLongestRespTime OBJECT-TYPE
        SYNTAX  HighResTime
        ACCESS  read-only
        STATUS  mandatory
        DESCRIPTION
            "Longest response time for processing an SMPP unknown
             request."
        ::= { serviceCentreEntry 286 }

    serviceCentreAoSmppOtherTimestampLongestResp OBJECT-TYPE
        SYNTAX  TimeStamp
        ACCESS  read-write
        STATUS  mandatory
        DESCRIPTION
            "Timestamp when longest response time of an SMPP unknown
             request occurred. The longest response time can be reset by
             setting longest response timestamp to zero."
        ::= { serviceCentreEntry 287 }

    serviceCentreAoSmppGenericNack OBJECT-TYPE
        SYNTAX  Counter
        ACCESS  read-only
        STATUS  mandatory
        DESCRIPTION
            "Counts the total number of SMPP generic nacks which were
             received from the Service Centre."
        ::= { serviceCentreEntry 288 }

    serviceCentreCntAoCimdLoginRequest OBJECT-TYPE
        SYNTAX  Counter
        ACCESS  read-only
        STATUS  mandatory
        DESCRIPTION
            "Counts the total number of CIMD login requests which were
             sent to the Service Centre."
        ::= { serviceCentreEntry 300 }

    serviceCentreCntAoCimdLoginAck OBJECT-TYPE
        SYNTAX  Counter
        ACCESS  read-only
        STATUS  mandatory
        DESCRIPTION
            "Counts the total number of positive CIMD login responses
             which were received from the Service Centre."
        ::= { serviceCentreEntry 301 }

    serviceCentreCntAoCimdLoginNack OBJECT-TYPE
        SYNTAX  Counter
        ACCESS  read-only
        STATUS  mandatory
        DESCRIPTION
            "Counts the total number of negative CIMD login responses
             which were received from the Service Centre."
        ::= { serviceCentreEntry 302 }

    serviceCentreAoCimdLoginTimeSpent OBJECT-TYPE
        SYNTAX  HighResTime
        ACCESS  read-only
        STATUS  mandatory
        DESCRIPTION
            "Total time spent in processing CIMD login requests."
        ::= { serviceCentreEntry 303 }

    serviceCentreAoCimdLoginShortestRespTime OBJECT-TYPE
        SYNTAX  HighResTime
        ACCESS  read-only
        STATUS  mandatory
        DESCRIPTION
            "Shortest response time for processing a CIMD login
             request."
        ::= { serviceCentreEntry 304 }

    serviceCentreAoCimdLoginTimestampShortestResp OBJECT-TYPE
        SYNTAX  TimeStamp
        ACCESS  read-write
        STATUS  mandatory
        DESCRIPTION
            "Timestamp when shortest response time of a CIMD login
             request occurred. The shortest response time can be reset
             by setting shortest response timestamp to zero."
        ::= { serviceCentreEntry 305 }

    serviceCentreAoCimdLoginLongestRespTime OBJECT-TYPE
        SYNTAX  HighResTime
        ACCESS  read-only
        STATUS  mandatory
        DESCRIPTION
            "Longest response time for processing a CIMD login
             request."
        ::= { serviceCentreEntry 306 }

    serviceCentreAoCimdLoginTimestampLongestResp OBJECT-TYPE
        SYNTAX  TimeStamp
        ACCESS  read-write
        STATUS  mandatory
        DESCRIPTION
            "Timestamp when longest response time of a CIMD login
             request occurred. The longest response time can be reset by
             setting the related  timestamp to zero."
        ::= { serviceCentreEntry 307 }

    serviceCentreCntAoCimdLogoutRequest OBJECT-TYPE
        SYNTAX  Counter
        ACCESS  read-only
        STATUS  mandatory
        DESCRIPTION
            "Counts the total number of CIMD logout requests which were
             sent to the Service Centre."
        ::= { serviceCentreEntry 308 }

    serviceCentreCntAoCimdLogoutAck OBJECT-TYPE
        SYNTAX  Counter
        ACCESS  read-only
        STATUS  mandatory
        DESCRIPTION
            "Counts the total number of positive CIMD logout responses
             which were received from the Service Centre."
        ::= { serviceCentreEntry 309 }

    serviceCentreCntAoCimdLogoutNack OBJECT-TYPE
        SYNTAX  Counter
        ACCESS  read-only
        STATUS  mandatory
        DESCRIPTION
            "Counts the total number of negative CIMD logout responses
             which were received from the Service Centre."
        ::= { serviceCentreEntry 310 }

    serviceCentreAoCimdLogoutTimeSpent OBJECT-TYPE
        SYNTAX  HighResTime
        ACCESS  read-only
        STATUS  mandatory
        DESCRIPTION
            "Total time spent in processing CIMD logout requests."
        ::= { serviceCentreEntry 311 }

    serviceCentreAoCimdLogoutShortestRespTime OBJECT-TYPE
        SYNTAX  HighResTime
        ACCESS  read-only
        STATUS  mandatory
        DESCRIPTION
            "Shortest response time for processing a CIMD logout
             request."
        ::= { serviceCentreEntry 312 }

    serviceCentreAoCimdLogoutTimestampShortestResp OBJECT-TYPE
        SYNTAX  TimeStamp
        ACCESS  read-write
        STATUS  mandatory
        DESCRIPTION
            "Timestamp when shortest response time of a CIMD logout
             request occurred. The shortest response time can be reset
             by setting shortest response timestamp to zero."
        ::= { serviceCentreEntry 313 }

    serviceCentreAoCimdLogoutLongestRespTime OBJECT-TYPE
        SYNTAX  HighResTime
        ACCESS  read-only
        STATUS  mandatory
        DESCRIPTION
            "Longest response time for processing a CIMD logout
             request."
        ::= { serviceCentreEntry 314 }

    serviceCentreAoCimdLogoutTimestampLongestResp OBJECT-TYPE
        SYNTAX  TimeStamp
        ACCESS  read-write
        STATUS  mandatory
        DESCRIPTION
            "Timestamp when longest response time of a CIMD logout
             request occurred. The longest response time can be reset by
             setting the related  timestamp to zero."
        ::= { serviceCentreEntry 315 }

    serviceCentreCntAoCimdSubmitRequest OBJECT-TYPE
        SYNTAX  Counter
        ACCESS  read-only
        STATUS  mandatory
        DESCRIPTION
            "Counts the total number of CIMD submit sm requests which
             were sent to the Service Centre."
        ::= { serviceCentreEntry 316 }

    serviceCentreCntAoCimdSubmitAck OBJECT-TYPE
        SYNTAX  Counter
        ACCESS  read-only
        STATUS  mandatory
        DESCRIPTION
            "Counts the total number of positive CIMD submit sm
             responses which were received from the Service Centre."
        ::= { serviceCentreEntry 317 }

    serviceCentreCntAoCimdSubmitNack OBJECT-TYPE
        SYNTAX  Counter
        ACCESS  read-only
        STATUS  mandatory
        DESCRIPTION
            "Counts the total number of negative CIMD submit sm
             responses which were received from the Service Centre."
        ::= { serviceCentreEntry 318 }

    serviceCentreAoCimdSubmitTimeSpent OBJECT-TYPE
        SYNTAX  HighResTime
        ACCESS  read-only
        STATUS  mandatory
        DESCRIPTION
            "Total time spent in processing CIMD submit sm requests."
        ::= { serviceCentreEntry 319 }

    serviceCentreAoCimdSubmitShortestRespTime OBJECT-TYPE
        SYNTAX  HighResTime
        ACCESS  read-only
        STATUS  mandatory
        DESCRIPTION
            "Shortest response time for processing a CIMD submit sm
             requests."
        ::= { serviceCentreEntry 320 }

    serviceCentreAoCimdSubmitTimestampShortestResp OBJECT-TYPE
        SYNTAX  TimeStamp
        ACCESS  read-write
        STATUS  mandatory
        DESCRIPTION
            "Timestamp when shortest response time of a CIMD submit sm
             request occurred. The shortest response time can be reset
             by setting shortest response timestamp to zero."
        ::= { serviceCentreEntry 321 }

    serviceCentreAoCimdSubmitLongestRespTime OBJECT-TYPE
        SYNTAX  HighResTime
        ACCESS  read-only
        STATUS  mandatory
        DESCRIPTION
            "Longest response time for processing a CIMD submit sm
             request."
        ::= { serviceCentreEntry 322 }

    serviceCentreAoCimdSubmitTimestampLongestResp OBJECT-TYPE
        SYNTAX  TimeStamp
        ACCESS  read-write
        STATUS  mandatory
        DESCRIPTION
            "Timestamp when longest response time of a CIMD submit sm
             request occurred. The longest response time can be reset by
             setting the related  timestamp to zero."
        ::= { serviceCentreEntry 323 }

    serviceCentreCntAoCimdEnquireRequest OBJECT-TYPE
        SYNTAX  Counter
        ACCESS  read-only
        STATUS  mandatory
        DESCRIPTION
            "Counts the total number of CIMD enquire message status
             requests which were sent to the Service Centre."
        ::= { serviceCentreEntry 324 }

    serviceCentreCntAoCimdEnquireAck OBJECT-TYPE
        SYNTAX  Counter
        ACCESS  read-only
        STATUS  mandatory
        DESCRIPTION
            "Counts the total number of positive CIMD enquire message
             status responses which were received from the service
             centre."
        ::= { serviceCentreEntry 325 }

    serviceCentreCntAoCimdEnquireNack OBJECT-TYPE
        SYNTAX  Counter
        ACCESS  read-only
        STATUS  mandatory
        DESCRIPTION
            "Counts the total number of negative CIMD enquire message
             status responses which were received from the service
             centre."
        ::= { serviceCentreEntry 326 }

    serviceCentreAoCimdEnquireTimeSpent OBJECT-TYPE
        SYNTAX  HighResTime
        ACCESS  read-only
        STATUS  mandatory
        DESCRIPTION
            "Total time spent in processing CIMD enquire message status
             requests."
        ::= { serviceCentreEntry 327 }

    serviceCentreAoCimdEnquireShortestRespTime OBJECT-TYPE
        SYNTAX  HighResTime
        ACCESS  read-only
        STATUS  mandatory
        DESCRIPTION
            "Shortest response time for processing a CIMD enquire
             message status request."
        ::= { serviceCentreEntry 328 }

    serviceCentreAoCimdEnquireTimestampShortestResp OBJECT-TYPE
        SYNTAX  TimeStamp
        ACCESS  read-write
        STATUS  mandatory
        DESCRIPTION
            "Timestamp when shortest response time of a CIMD enquire
             message status request occurred. The shortest response time
             can be reset by setting shortest response timestamp to
             zero."
        ::= { serviceCentreEntry 329 }

    serviceCentreAoCimdEnquireLongestRespTime OBJECT-TYPE
        SYNTAX  HighResTime
        ACCESS  read-only
        STATUS  mandatory
        DESCRIPTION
            "Longest response time for processing a CIMD enquire message
             status request."
        ::= { serviceCentreEntry 330 }

    serviceCentreAoCimdEnquireTimestampLongestResp OBJECT-TYPE
        SYNTAX  TimeStamp
        ACCESS  read-write
        STATUS  mandatory
        DESCRIPTION
            "Timestamp when longest response time of a CIMD enquire
             message status request occurred. The longest response time
             can be reset by setting the related  timestamp to zero."
        ::= { serviceCentreEntry 331 }

    serviceCentreCntAoCimdOtherRequest OBJECT-TYPE
        SYNTAX  Counter
        ACCESS  read-only
        STATUS  mandatory
        DESCRIPTION
            "Counts the total number of unknown CIMD requests which were
             sent to the Service Centre."
        ::= { serviceCentreEntry 332 }

    serviceCentreCntAoCimdOtherAck OBJECT-TYPE
        SYNTAX  Counter
        ACCESS  read-only
        STATUS  mandatory
        DESCRIPTION
            "Counts the total number of positive unknown CIMD responses
             which were received from the Service Centre."
        ::= { serviceCentreEntry 333 }

    serviceCentreCntAoCimdOtherNack OBJECT-TYPE
        SYNTAX  Counter
        ACCESS  read-only
        STATUS  mandatory
        DESCRIPTION
            "Counts the total number of negative unknown CIMD responses
             which were received from the Service Centre."
        ::= { serviceCentreEntry 334 }

    serviceCentreAoCimdOtherTimeSpent OBJECT-TYPE
        SYNTAX  HighResTime
        ACCESS  read-only
        STATUS  mandatory
        DESCRIPTION
            "Total time spent in processing unknown CIMD requests."
        ::= { serviceCentreEntry 335 }

    serviceCentreAoCimdOtherShortestRespTime OBJECT-TYPE
        SYNTAX  HighResTime
        ACCESS  read-only
        STATUS  mandatory
        DESCRIPTION
            "Shortest response time for processing an unknown CIMD
             request."
        ::= { serviceCentreEntry 336 }

    serviceCentreAoCimdOtherTimestampShortestResp OBJECT-TYPE
        SYNTAX  TimeStamp
        ACCESS  read-write
        STATUS  mandatory
        DESCRIPTION
            "Timestamp when shortest response time of an unknown CIMD
             request occurred. The shortest response time can be reset
             by setting shortest response timestamp to zero."
        ::= { serviceCentreEntry 337 }

    serviceCentreAoCimdOtherLongestRespTime OBJECT-TYPE
        SYNTAX  HighResTime
        ACCESS  read-only
        STATUS  mandatory
        DESCRIPTION
            "Longest response time for processing an unknown CIMD
             requests."
        ::= { serviceCentreEntry 338 }

    serviceCentreAoCimdOtherTimestampLongestResp OBJECT-TYPE
        SYNTAX  TimeStamp
        ACCESS  read-write
        STATUS  mandatory
        DESCRIPTION
            "Timestamp when longest response time of a unknown CIMD
             request occurred. The longest response time can be reset by
             setting the related  timestamp to zero."
        ::= { serviceCentreEntry 339 }

    serviceCentreCntAtUcp52Request OBJECT-TYPE
        SYNTAX  Counter
        ACCESS  read-only
        STATUS  mandatory
        DESCRIPTION
            "Counts the total number of UCP deliver sm requests which
             were received from the Service Centre."
        ::= { serviceCentreEntry 400 }

    serviceCentreCntAtUcp52Ack OBJECT-TYPE
        SYNTAX  Counter
        ACCESS  read-only
        STATUS  mandatory
        DESCRIPTION
            "Counts the total number of positive UCP deliver sm
             responses which were sent to the Service Centre."
        ::= { serviceCentreEntry 401 }

    serviceCentreCntAtUcp52Nack OBJECT-TYPE
        SYNTAX  Counter
        ACCESS  read-only
        STATUS  mandatory
        DESCRIPTION
            "Counts the total number of negative UCP deliver sm
             responses which were sent to the Service Centre."
        ::= { serviceCentreEntry 402 }

    serviceCentreCntAtUcp53Request OBJECT-TYPE
        SYNTAX  Counter
        ACCESS  read-only
        STATUS  mandatory
        DESCRIPTION
            "Counts the total number of UCP deliver notify requests which
             were received from the Service Centre."
        ::= { serviceCentreEntry 403 }

    serviceCentreCntAtUcp53Ack OBJECT-TYPE
        SYNTAX  Counter
        ACCESS  read-only
        STATUS  mandatory
        DESCRIPTION
            "Counts the total number of positive UCP deliver notify
             responses which were sent to the Service Centre."
        ::= { serviceCentreEntry 404 }

    serviceCentreCntAtUcp53Nack OBJECT-TYPE
        SYNTAX  Counter
        ACCESS  read-only
        STATUS  mandatory
        DESCRIPTION
            "Counts the total number of negative UCP deliver notify
             responses which were sent to the Service Centre."
        ::= { serviceCentreEntry 405 }

    serviceCentreCntAtUcpOtherRequest OBJECT-TYPE
        SYNTAX  Counter
        ACCESS  read-only
        STATUS  mandatory
        DESCRIPTION
            "Counts the total number of unknown UCP requests which were
             received from the Service Centre."
        ::= { serviceCentreEntry 406 }

    serviceCentreCntAtUcpOtherAck OBJECT-TYPE
        SYNTAX  Counter
        ACCESS  read-only
        STATUS  mandatory
        DESCRIPTION
            "Counts the total number of positive unknown UCP responses
             which were sent to the Service Centre."
        ::= { serviceCentreEntry 407 }

    serviceCentreCntAtUcpOtherNack OBJECT-TYPE
        SYNTAX  Counter
        ACCESS  read-only
        STATUS  mandatory
        DESCRIPTION
            "Counts the total number of negative unknown UCP responses
             which were sent to the Service Centre."
        ::= { serviceCentreEntry 408 }

    serviceCentreCntAtUcp57Request OBJECT-TYPE
        SYNTAX  Counter
        ACCESS  read-only
        STATUS  mandatory
        DESCRIPTION
            "Counts the total number of UCP response inquiry message
             requests which were received from the Service Centre."
        ::= { serviceCentreEntry 409 }

    serviceCentreCntAtUcp57Ack OBJECT-TYPE
        SYNTAX  Counter
        ACCESS  read-only
        STATUS  mandatory
        DESCRIPTION
            "Counts the total number of positive UCP response inquiry
             message responses which were sent to the Service Centre."
        ::= { serviceCentreEntry 410 }

    serviceCentreCntAtUcp57Nack OBJECT-TYPE
        SYNTAX  Counter
        ACCESS  read-only
        STATUS  mandatory
        DESCRIPTION
            "Counts the total number of negative UCP response inquiry
             message responses which were sent to the Service Centre."
        ::= { serviceCentreEntry 411 }

    serviceCentreCntAtUcp58Request OBJECT-TYPE
        SYNTAX  Counter
        ACCESS  read-only
        STATUS  mandatory
        DESCRIPTION
            "Counts the total number of UCP response delete message
             requests which were received from the Service Centre."
        ::= { serviceCentreEntry 412 }

    serviceCentreCntAtUcp58Ack OBJECT-TYPE
        SYNTAX  Counter
        ACCESS  read-only
        STATUS  mandatory
        DESCRIPTION
            "Counts the total number of positive UCP response delete
             message responses which were sent to the Service Centre."
        ::= { serviceCentreEntry 413 }

    serviceCentreCntAtUcp58Nack OBJECT-TYPE
        SYNTAX  Counter
        ACCESS  read-only
        STATUS  mandatory
        DESCRIPTION
            "Counts the total number of negative UCP response delete
             message responses which were sent to the Service Centre."
        ::= { serviceCentreEntry 414 }

    serviceCentreCntAtSmppDeliverSmRequest OBJECT-TYPE
        SYNTAX  Counter
        ACCESS  read-only
        STATUS  mandatory
        DESCRIPTION
            "Counts the total number of SMPP deliver sm requests which
             were received from the Service Centre."
        ::= { serviceCentreEntry 420 }

    serviceCentreCntAtSmppDeliverSmAck OBJECT-TYPE
        SYNTAX  Counter
        ACCESS  read-only
        STATUS  mandatory
        DESCRIPTION
            "Counts the total number of positive SMPP deliver sm
             responses which were sent to the Service Centre."
        ::= { serviceCentreEntry 421 }

    serviceCentreCntAtSmppDeliverSmNack OBJECT-TYPE
        SYNTAX  Counter
        ACCESS  read-only
        STATUS  mandatory
        DESCRIPTION
            "Counts the total number of negative SMPP deliver sm
             responses which were sent to the Service Centre."
        ::= { serviceCentreEntry 422 }

    serviceCentreCntAtSmppDataSmRequest OBJECT-TYPE
        SYNTAX  Counter
        ACCESS  read-only
        STATUS  mandatory
        DESCRIPTION
            "Counts the total number of SMPP data sm requests which were
             received from the Service Centre."
        ::= { serviceCentreEntry 423 }

    serviceCentreCntAtSmppDataSmAck OBJECT-TYPE
        SYNTAX  Counter
        ACCESS  read-only
        STATUS  mandatory
        DESCRIPTION
            "Counts the total number of positive SMPP data sm responses
             which were sent to the Service Centre."
        ::= { serviceCentreEntry 424 }

    serviceCentreCntAtSmppDataSmNack OBJECT-TYPE
        SYNTAX  Counter
        ACCESS  read-only
        STATUS  mandatory
        DESCRIPTION
            "Counts the total number of negative SMPP data sm responses
             which were sent to the Service Centre."
        ::= { serviceCentreEntry 425 }

    serviceCentreCntAtSmppOtherRequest OBJECT-TYPE
        SYNTAX  Counter
        ACCESS  read-only
        STATUS  mandatory
        DESCRIPTION
            "Counts the total number of unknown SMPP requests which were
             received from the Service Centre."
        ::= { serviceCentreEntry 426 }

    serviceCentreCntAtSmppOtherAck OBJECT-TYPE
        SYNTAX  Counter
        ACCESS  read-only
        STATUS  mandatory
        DESCRIPTION
            "Counts the total number of positive unknown SMPP responses
             which were sent to the Service Centre."
        ::= { serviceCentreEntry 427 }

    serviceCentreCntAtSmppOtherNack OBJECT-TYPE
        SYNTAX  Counter
        ACCESS  read-only
        STATUS  mandatory
        DESCRIPTION
            "Counts the total number of negative unknown SMPP responses
             which were sent to the Service Centre."
        ::= { serviceCentreEntry 428 }

    serviceCentreCntAtCimdDeliverRequest OBJECT-TYPE
        SYNTAX  Counter
        ACCESS  read-only
        STATUS  mandatory
        DESCRIPTION
            "Counts the total number of CIMD deliver sm requests which
             were received from the Service Centre."
        ::= { serviceCentreEntry 440 }

    serviceCentreCntAtCimdDeliverAck OBJECT-TYPE
        SYNTAX  Counter
        ACCESS  read-only
        STATUS  mandatory
        DESCRIPTION
            "Counts the total number of positive CIMD deliver sm
             responses which were sent to the Service Centre."
        ::= { serviceCentreEntry 441 }

    serviceCentreCntAtCimdDeliverNack OBJECT-TYPE
        SYNTAX  Counter
        ACCESS  read-only
        STATUS  mandatory
        DESCRIPTION
            "Counts the total number of negative CIMD deliver sm
             responses which were sent to the Service Centre."
        ::= { serviceCentreEntry 442 }

    serviceCentreCntAtCimdDeliverStatusRequest OBJECT-TYPE
        SYNTAX  Counter
        ACCESS  read-only
        STATUS  mandatory
        DESCRIPTION
            "Counts the total number of CIMD deliver status requests
             which were received from the Service Centre."
        ::= { serviceCentreEntry 443 }

    serviceCentreCntAtCimdDeliverStatusAck OBJECT-TYPE
        SYNTAX  Counter
        ACCESS  read-only
        STATUS  mandatory
        DESCRIPTION
            "Counts the total number of positive CIMD deliver status
             responses which were sent to the Service Centre."
        ::= { serviceCentreEntry 444 }

    serviceCentreCntAtCimdDeliverStatusNack OBJECT-TYPE
        SYNTAX  Counter
        ACCESS  read-only
        STATUS  mandatory
        DESCRIPTION
            "Counts the total number of negative CIMD deliver status
             responses which were sent to the Service Centre."
        ::= { serviceCentreEntry 445 }

    serviceCentreCntAtCimdAliveRequest OBJECT-TYPE
        SYNTAX  Counter
        ACCESS  read-only
        STATUS  mandatory
        DESCRIPTION
            "Counts the total number of CIMD alive message requests which
             were received from the Service Centre."
        ::= { serviceCentreEntry 446 }

    serviceCentreCntAtCimdAliveAck OBJECT-TYPE
        SYNTAX  Counter
        ACCESS  read-only
        STATUS  mandatory
        DESCRIPTION
            "Counts the total number of positive CIMD alive message
             responses which were sent to the Service Centre."
        ::= { serviceCentreEntry 447 }

    serviceCentreCntAtCimdAliveNack OBJECT-TYPE
        SYNTAX  Counter
        ACCESS  read-only
        STATUS  mandatory
        DESCRIPTION
            "Counts the total number of negative CIMD alive message
             responses which were sent to the Service Centre."
        ::= { serviceCentreEntry 448 }

    serviceCentreCntAtCimdOtherRequest OBJECT-TYPE
        SYNTAX  Counter
        ACCESS  read-only
        STATUS  mandatory
        DESCRIPTION
            "Counts the total number of unknown CIMD requests which were
             received from the Service Centre."
        ::= { serviceCentreEntry 449 }

    serviceCentreCntAtCimdOtherAck OBJECT-TYPE
        SYNTAX  Counter
        ACCESS  read-only
        STATUS  mandatory
        DESCRIPTION
            "Counts the total number of positive unknown CIMD responses
             which were sent to the Service Centre."
        ::= { serviceCentreEntry 450 }

    serviceCentreCntAtCimdOtherNack OBJECT-TYPE
        SYNTAX  Counter
        ACCESS  read-only
        STATUS  mandatory
        DESCRIPTION
            "Counts the total number of negative unknown CIMD responses
             which were sent to the Service Centre."
        ::= { serviceCentreEntry 451 }


    -- the SC Node Entity

    scNodeTable OBJECT-TYPE
        SYNTAX  SEQUENCE OF ScNodeEntry
        ACCESS  not-accessible
        STATUS  mandatory
        DESCRIPTION
            "A table containing properties for each SC Node."
        ::= { apc 22 }

    scNodeEntry OBJECT-TYPE
        SYNTAX  ScNodeEntry
        ACCESS  not-accessible
        STATUS  mandatory
        DESCRIPTION
            "Table entry defining a single SC Node."
        INDEX   { scNodeIndex }
        ::= { scNodeTable 1 }

    ScNodeEntry ::=
        SEQUENCE {
            scNodeIndex                            ScNodeTableIndex,
            scNodeAdminState                       AdminState,
            scNodeServiceCentreIndex               ServiceCentreTableIndex,
            scNodeName                             NameString,
            scNodeOperationalState                 OperationalState,
            scNodeIpAddress                        IpAddress,
            scNodeThroughputAo                     Throughput,
            scNodeThroughputAt                     Throughput,
            scNodeSessionsCounter                  Gauge,
            scNodeCntAoThroughputLimitHit          Counter,
            scNodeCntAoUcp01Request                        Counter,
            scNodeCntAoUcp01Ack                            Counter,
            scNodeCntAoUcp01Nack                           Counter,
            scNodeAoUcp01TimeSpent                         HighResTime,
            scNodeAoUcp01ShortestRespTime                  HighResTime,
            scNodeAoUcp01TimestampShortestResp             TimeStamp,
            scNodeAoUcp01LongestRespTime                   HighResTime,
            scNodeAoUcp01TimestampLongestResp              TimeStamp,
            scNodeCntAoUcp30Request                        Counter,
            scNodeCntAoUcp30Ack                            Counter,
            scNodeCntAoUcp30Nack                           Counter,
            scNodeAoUcp30TimeSpent                         HighResTime,
            scNodeAoUcp30ShortestRespTime                  HighResTime,
            scNodeAoUcp30TimestampShortestResp             TimeStamp,
            scNodeAoUcp30LongestRespTime                   HighResTime,
            scNodeAoUcp30TimestampLongestResp              TimeStamp,
            scNodeCntAoUcp31Request                        Counter,
            scNodeCntAoUcp31Ack                            Counter,
            scNodeCntAoUcp31Nack                           Counter,
            scNodeAoUcp31TimeSpent                         HighResTime,
            scNodeAoUcp31ShortestRespTime                  HighResTime,
            scNodeAoUcp31TimestampShortestResp             TimeStamp,
            scNodeAoUcp31LongestRespTime                   HighResTime,
            scNodeAoUcp31TimestampLongestResp              TimeStamp,
            scNodeCntAoUcp51Request                        Counter,
            scNodeCntAoUcp51Ack                            Counter,
            scNodeCntAoUcp51Nack                           Counter,
            scNodeAoUcp51TimeSpent                         HighResTime,
            scNodeAoUcp51ShortestRespTime                  HighResTime,
            scNodeAoUcp51TimestampShortestResp             TimeStamp,
            scNodeAoUcp51LongestRespTime                   HighResTime,
            scNodeAoUcp51TimestampLongestResp              TimeStamp,
            scNodeCntAoUcp54Request                        Counter,
            scNodeCntAoUcp54Ack                            Counter,
            scNodeCntAoUcp54Nack                           Counter,
            scNodeAoUcp54TimeSpent                         HighResTime,
            scNodeAoUcp54ShortestRespTime                  HighResTime,
            scNodeAoUcp54TimestampShortestResp             TimeStamp,
            scNodeAoUcp54LongestRespTime                   HighResTime,
            scNodeAoUcp54TimestampLongestResp              TimeStamp,
            scNodeCntAoUcp60Request                        Counter,
            scNodeCntAoUcp60Ack                            Counter,
            scNodeCntAoUcp60Nack                           Counter,
            scNodeAoUcp60TimeSpent                         HighResTime,
            scNodeAoUcp60ShortestRespTime                  HighResTime,
            scNodeAoUcp60TimestampShortestResp             TimeStamp,
            scNodeAoUcp60LongestRespTime                   HighResTime,
            scNodeAoUcp60TimestampLongestResp              TimeStamp,
            scNodeCntAoUcpOtherRequest                     Counter,
            scNodeCntAoUcpOtherAck                         Counter,
            scNodeCntAoUcpOtherNack                        Counter,
            scNodeAoUcpOtherTimeSpent                      HighResTime,
            scNodeAoUcpOtherShortestRespTime               HighResTime,
            scNodeAoUcpOtherTimestampShortestResp          TimeStamp,
            scNodeAoUcpOtherLongestRespTime                HighResTime,
            scNodeAoUcpOtherTimestampLongestResp           TimeStamp,
            scNodeCntAoUcp55Request                        Counter,
            scNodeCntAoUcp55Ack                            Counter,
            scNodeCntAoUcp55Nack                           Counter,
            scNodeAoUcp55TimeSpent                         HighResTime,
            scNodeAoUcp55ShortestRespTime                  HighResTime,
            scNodeAoUcp55TimestampShortestResp             TimeStamp,
            scNodeAoUcp55LongestRespTime                   HighResTime,
            scNodeAoUcp55TimestampLongestResp              TimeStamp,
            scNodeCntAoUcp56Request                        Counter,
            scNodeCntAoUcp56Ack                            Counter,
            scNodeCntAoUcp56Nack                           Counter,
            scNodeAoUcp56TimeSpent                         HighResTime,
            scNodeAoUcp56ShortestRespTime                  HighResTime,
            scNodeAoUcp56TimestampShortestResp             TimeStamp,
            scNodeAoUcp56LongestRespTime                   HighResTime,
            scNodeAoUcp56TimestampLongestResp              TimeStamp,
            scNodeCntAoSmppSubmitSmRequest                 Counter,
            scNodeCntAoSmppSubmitSmAck                     Counter,
            scNodeCntAoSmppSubmitSmNack                    Counter,
            scNodeAoSmppSubmitSmTimeSpent                  HighResTime,
            scNodeAoSmppSubmitSmShortestRespTime           HighResTime,
            scNodeAoSmppSubmitSmTimestampShortestResp      TimeStamp,
            scNodeAoSmppSubmitSmLongestRespTime            HighResTime,
            scNodeAoSmppSubmitSmTimestampLongestResp       TimeStamp,
            scNodeCntAoSmppDataSmRequest                   Counter,
            scNodeCntAoSmppDataSmAck                       Counter,
            scNodeCntAoSmppDataSmNack                      Counter,
            scNodeAoSmppDataSmTimeSpent                    HighResTime,
            scNodeAoSmppDataSmShortestRespTime             HighResTime,
            scNodeAoSmppDataSmTimestampShortestResp        TimeStamp,
            scNodeAoSmppDataSmLongestRespTime              HighResTime,
            scNodeAoSmppDataSmTimestampLongestResp         TimeStamp,
            scNodeCntAoSmppBindRxRequest                   Counter,
            scNodeCntAoSmppBindRxAck                       Counter,
            scNodeCntAoSmppBindRxNack                      Counter,
            scNodeAoSmppBindRxTimeSpent                    HighResTime,
            scNodeAoSmppBindRxShortestRespTime             HighResTime,
            scNodeAoSmppBindRxTimestampShortestResp        TimeStamp,
            scNodeAoSmppBindRxLongestRespTime              HighResTime,
            scNodeAoSmppBindRxTimestampLongestResp         TimeStamp,
            scNodeCntAoSmppBindTxRequest                   Counter,
            scNodeCntAoSmppBindTxAck                       Counter,
            scNodeCntAoSmppBindTxNack                      Counter,
            scNodeAoSmppBindTxTimeSpent                    HighResTime,
            scNodeAoSmppBindTxShortestRespTime             HighResTime,
            scNodeAoSmppBindTxTimestampShortestResp        TimeStamp,
            scNodeAoSmppBindTxLongestRespTime              HighResTime,
            scNodeAoSmppBindTxTimestampLongestResp         TimeStamp,
            scNodeCntAoSmppBindTrxRequest                  Counter,
            scNodeCntAoSmppBindTrxAck                      Counter,
            scNodeCntAoSmppBindTrxNack                     Counter,
            scNodeAoSmppBindTrxTimeSpent                   HighResTime,
            scNodeAoSmppBindTrxShortestRespTime            HighResTime,
            scNodeAoSmppBindTrxTimestampShortestResp       TimeStamp,
            scNodeAoSmppBindTrxLongestRespTime             HighResTime,
            scNodeAoSmppBindTrxTimestampLongestResp        TimeStamp,
            scNodeCntAoSmppUnbindRequest                   Counter,
            scNodeCntAoSmppUnbindAck                       Counter,
            scNodeCntAoSmppUnbindNack                      Counter,
            scNodeAoSmppUnbindTimeSpent                    HighResTime,
            scNodeAoSmppUnbindShortestRespTime             HighResTime,
            scNodeAoSmppUnbindTimestampShortestResp        TimeStamp,
            scNodeAoSmppUnbindLongestRespTime              HighResTime,
            scNodeAoSmppUnbindTimestampLongestResp         TimeStamp,
            scNodeCntAoSmppQuerySmRequest                  Counter,
            scNodeCntAoSmppQuerySmAck                      Counter,
            scNodeCntAoSmppQuerySmNack                     Counter,
            scNodeAoSmppQuerySmTimeSpent                   HighResTime,
            scNodeAoSmppQuerySmShortestRespTime            HighResTime,
            scNodeAoSmppQuerySmTimestampShortestResp       TimeStamp,
            scNodeAoSmppQuerySmLongestRespTime             HighResTime,
            scNodeAoSmppQuerySmTimestampLongestResp        TimeStamp,
            scNodeCntAoSmppReplaceSmRequest                Counter,
            scNodeCntAoSmppReplaceSmAck                    Counter,
            scNodeCntAoSmppReplaceSmNack                   Counter,
            scNodeAoSmppReplaceSmTimeSpent                 HighResTime,
            scNodeAoSmppReplaceSmShortestRespTime          HighResTime,
            scNodeAoSmppReplaceSmTimestampShortestResp     TimeStamp,
            scNodeAoSmppReplaceSmLongestRespTime           HighResTime,
            scNodeAoSmppReplaceSmTimestampLongestResp      TimeStamp,
            scNodeCntAoSmppCancelSmRequest                 Counter,
            scNodeCntAoSmppCancelSmAck                     Counter,
            scNodeCntAoSmppCancelSmNack                    Counter,
            scNodeAoSmppCancelSmTimeSpent                  HighResTime,
            scNodeAoSmppCancelSmShortestRespTime           HighResTime,
            scNodeAoSmppCancelSmTimestampShortestResp      TimeStamp,
            scNodeAoSmppCancelSmLongestRespTime            HighResTime,
            scNodeAoSmppCancelSmTimestampLongestResp       TimeStamp,
            scNodeCntAoSmppEnquireLinkRequest              Counter,
            scNodeCntAoSmppEnquireLinkAck                  Counter,
            scNodeCntAoSmppEnquireLinkNack                 Counter,
            scNodeAoSmppEnquireLinkTimeSpent               HighResTime,
            scNodeAoSmppEnquireLinkShortestRespTime        HighResTime,
            scNodeAoSmppEnquireLinkTimestampShortestResp   TimeStamp,
            scNodeAoSmppEnquireLinkLongestRespTime         HighResTime,
            scNodeAoSmppEnquireLinkTimestampLongestResp    TimeStamp,
            scNodeCntAoSmppOtherRequest                    Counter,
            scNodeCntAoSmppOtherAck                        Counter,
            scNodeCntAoSmppOtherNack                       Counter,
            scNodeAoSmppOtherTimeSpent                     HighResTime,
            scNodeAoSmppOtherShortestRespTime              HighResTime,
            scNodeAoSmppOtherTimestampShortestResp         TimeStamp,
            scNodeAoSmppOtherLongestRespTime               HighResTime,
            scNodeAoSmppOtherTimestampLongestResp          TimeStamp,
            scNodeAoSmppGenericNack                        Counter,
            scNodeCntAoCimdLoginRequest                    Counter,
            scNodeCntAoCimdLoginAck                        Counter,
            scNodeCntAoCimdLoginNack                       Counter,
            scNodeAoCimdLoginTimeSpent                     HighResTime,
            scNodeAoCimdLoginShortestRespTime              HighResTime,
            scNodeAoCimdLoginTimestampShortestResp         TimeStamp,
            scNodeAoCimdLoginLongestRespTime               HighResTime,
            scNodeAoCimdLoginTimestampLongestResp          TimeStamp,
            scNodeCntAoCimdLogoutRequest                   Counter,
            scNodeCntAoCimdLogoutAck                       Counter,
            scNodeCntAoCimdLogoutNack                      Counter,
            scNodeAoCimdLogoutTimeSpent                    HighResTime,
            scNodeAoCimdLogoutShortestRespTime             HighResTime,
            scNodeAoCimdLogoutTimestampShortestResp        TimeStamp,
            scNodeAoCimdLogoutLongestRespTime              HighResTime,
            scNodeAoCimdLogoutTimestampLongestResp         TimeStamp,
            scNodeCntAoCimdSubmitRequest                   Counter,
            scNodeCntAoCimdSubmitAck                       Counter,
            scNodeCntAoCimdSubmitNack                      Counter,
            scNodeAoCimdSubmitTimeSpent                    HighResTime,
            scNodeAoCimdSubmitShortestRespTime             HighResTime,
            scNodeAoCimdSubmitTimestampShortestResp        TimeStamp,
            scNodeAoCimdSubmitLongestRespTime              HighResTime,
            scNodeAoCimdSubmitTimestampLongestResp         TimeStamp,
            scNodeCntAoCimdEnquireRequest                  Counter,
            scNodeCntAoCimdEnquireAck                      Counter,
            scNodeCntAoCimdEnquireNack                     Counter,
            scNodeAoCimdEnquireTimeSpent                   HighResTime,
            scNodeAoCimdEnquireShortestRespTime            HighResTime,
            scNodeAoCimdEnquireTimestampShortestResp       TimeStamp,
            scNodeAoCimdEnquireLongestRespTime             HighResTime,
            scNodeAoCimdEnquireTimestampLongestResp        TimeStamp,
            scNodeCntAoCimdOtherRequest                    Counter,
            scNodeCntAoCimdOtherAck                        Counter,
            scNodeCntAoCimdOtherNack                       Counter,
            scNodeAoCimdOtherTimeSpent                     HighResTime,
            scNodeAoCimdOtherShortestRespTime              HighResTime,
            scNodeAoCimdOtherTimestampShortestResp         TimeStamp,
            scNodeAoCimdOtherLongestRespTime               HighResTime,
            scNodeAoCimdOtherTimestampLongestResp          TimeStamp,
            scNodeCntAtUcp52Request                        Counter,
            scNodeCntAtUcp52Ack                            Counter,
            scNodeCntAtUcp52Nack                           Counter,
            scNodeCntAtUcp53Request                        Counter,
            scNodeCntAtUcp53Ack                            Counter,
            scNodeCntAtUcp53Nack                           Counter,
            scNodeCntAtUcpOtherRequest                     Counter,
            scNodeCntAtUcpOtherAck                         Counter,
            scNodeCntAtUcpOtherNack                        Counter,
            scNodeCntAtUcp57Request                        Counter,
            scNodeCntAtUcp57Ack                            Counter,
            scNodeCntAtUcp57Nack                           Counter,
            scNodeCntAtUcp58Request                        Counter,
            scNodeCntAtUcp58Ack                            Counter,
            scNodeCntAtUcp58Nack                           Counter,
            scNodeCntAtSmppDeliverSmRequest                Counter,
            scNodeCntAtSmppDeliverSmAck                    Counter,
            scNodeCntAtSmppDeliverSmNack                   Counter,
            scNodeCntAtSmppDataSmRequest                   Counter,
            scNodeCntAtSmppDataSmAck                       Counter,
            scNodeCntAtSmppDataSmNack                      Counter,
            scNodeCntAtSmppOtherRequest                    Counter,
            scNodeCntAtSmppOtherAck                        Counter,
            scNodeCntAtSmppOtherNack                       Counter,
            scNodeCntAtCimdDeliverRequest                  Counter,
            scNodeCntAtCimdDeliverAck                      Counter,
            scNodeCntAtCimdDeliverNack                     Counter,
            scNodeCntAtCimdDeliverStatusRequest            Counter,
            scNodeCntAtCimdDeliverStatusAck                Counter,
            scNodeCntAtCimdDeliverStatusNack               Counter,
            scNodeCntAtCimdAliveRequest                    Counter,
            scNodeCntAtCimdAliveAck                        Counter,
            scNodeCntAtCimdAliveNack                       Counter,
            scNodeCntAtCimdOtherRequest                    Counter,
            scNodeCntAtCimdOtherAck                        Counter,
            scNodeCntAtCimdOtherNack                       Counter

        }

    scNodeIndex OBJECT-TYPE
        SYNTAX  ScNodeTableIndex
        ACCESS  not-accessible
        STATUS  mandatory
        DESCRIPTION
            "Index of entry in sc node table."
        ::= { scNodeEntry 1 }

    scNodeAdminState OBJECT-TYPE
        SYNTAX  AdminState
        ACCESS  read-write
        STATUS  mandatory
        DESCRIPTION
            "Administrative state of the SC Node.

            Transition from 'inactive' to 'active' is only possible when:
            1) name supplied and not already in use by another SC Node;
            2) Service Centre index supplied and exists;
            3) IP address supplied

            Transition from 'active' to 'inactive' is always possible but will
            result in a graceful shutdown of all inside sessions towards the
            Termination Points of this node.

            Transition to 'destroy' is only possible when:
            1) SC Node is not being referred.

            For details, refer to the comment on the AdminState type."
        ::= { scNodeEntry 2 }

    scNodeServiceCentreIndex OBJECT-TYPE
        SYNTAX  ServiceCentreTableIndex
        ACCESS  read-write
        STATUS  mandatory
        DESCRIPTION
            "Index referring to an entry in the Service Centre table."
        ::= { scNodeEntry 3 }

    scNodeName OBJECT-TYPE
        SYNTAX  NameString
        ACCESS  read-write
        STATUS  mandatory
        DESCRIPTION
            "The name of the sc node entity."
        ::= { scNodeEntry 4 }

    scNodeOperationalState OBJECT-TYPE
        SYNTAX  OperationalState
        ACCESS  read-only
        STATUS  mandatory
        DESCRIPTION
            "The operational state of the sc node entity."
        ::= { scNodeEntry 5 }

    scNodeIpAddress OBJECT-TYPE
        SYNTAX  IpAddress
        ACCESS  read-write
        STATUS  mandatory
        DESCRIPTION
            "The IP Address of the sc node entity."
        ::= { scNodeEntry 6 }

    scNodeThroughputAo OBJECT-TYPE
        SYNTAX  Throughput
        ACCESS  read-write
        STATUS  mandatory
        DESCRIPTION
            "Maximum incoming throughput the SC Node can handle from
            external entities like the TextPassHub in terms of SM's per
            second."
        ::= { scNodeEntry 11 }

    scNodeThroughputAt OBJECT-TYPE
        SYNTAX  Throughput
        ACCESS  read-write
        STATUS  mandatory
        DESCRIPTION
            "Maximum outgoing throughput the SC Node can send towards
            external entities like the TextPassHub in terms of SM's per
            second."
        ::= { scNodeEntry 12 }

    scNodeSessionsCounter OBJECT-TYPE
        SYNTAX  Gauge
        ACCESS  read-write
        STATUS  mandatory
        DESCRIPTION
            "Number of total sessions currently established towards the SC
            Node."
        ::= { scNodeEntry 21 }
  
    scNodeCntAoThroughputLimitHit OBJECT-TYPE
        SYNTAX  Counter
        ACCESS  read-write
        STATUS  mandatory
        DESCRIPTION
            "Counter specifying the number of times that the AO throughput
            limit as set for the SC Node has been hit."
        ::= { scNodeEntry 22 }

    scNodeCntAoUcp01Request OBJECT-TYPE
        SYNTAX  Counter
        ACCESS  read-only
        STATUS  mandatory
        DESCRIPTION
            "Counts the total number of UCP call input request which
             were sent to the SC node."
        ::= { scNodeEntry 70 }

    scNodeCntAoUcp01Ack OBJECT-TYPE
        SYNTAX  Counter
        ACCESS  read-only
        STATUS  mandatory
        DESCRIPTION
            "Counts the total number of positive UCP call input
             responses which were received from the SC node."
        ::= { scNodeEntry 71 }

    scNodeCntAoUcp01Nack OBJECT-TYPE
        SYNTAX  Counter
        ACCESS  read-only
        STATUS  mandatory
        DESCRIPTION
            "Counts the total number of negative UCP call input
             responses which were received from the SC node."
        ::= { scNodeEntry 72 }

    scNodeAoUcp01TimeSpent OBJECT-TYPE
        SYNTAX  HighResTime
        ACCESS  read-only
        STATUS  mandatory
        DESCRIPTION
            "Total time spent in processing UCP call input requests."
        ::= { scNodeEntry 73 }

    scNodeAoUcp01ShortestRespTime OBJECT-TYPE
        SYNTAX  HighResTime
        ACCESS  read-only
        STATUS  mandatory
        DESCRIPTION
            "Shortest response time for processing a UCP call input
             requests."
        ::= { scNodeEntry 74 }

    scNodeAoUcp01TimestampShortestResp OBJECT-TYPE
        SYNTAX  TimeStamp
        ACCESS  read-write
        STATUS  mandatory
        DESCRIPTION
            "Time stamp when shortest response time of a UCP call input
             request occurred. The shortest response time can be reset
             by setting shortest response time stamp to zero."
        ::= { scNodeEntry 75 }

    scNodeAoUcp01LongestRespTime OBJECT-TYPE
        SYNTAX  HighResTime
        ACCESS  read-only
        STATUS  mandatory
        DESCRIPTION
            "Longest response time for processing a UCP call input
             requests."
        ::= { scNodeEntry 76 }

    scNodeAoUcp01TimestampLongestResp OBJECT-TYPE
        SYNTAX  TimeStamp
        ACCESS  read-write
        STATUS  mandatory
        DESCRIPTION
            "Time stamp when longest response time of a UCP call input
             request occurred. The longest response time can be reset by
             setting longtest response time stamp to zero."
        ::= { scNodeEntry 77 }

    scNodeCntAoUcp30Request OBJECT-TYPE
        SYNTAX  Counter
        ACCESS  read-only
        STATUS  mandatory
        DESCRIPTION
            "Counts the total number of UCP message transfer requests which
             were sent to the SC node."
        ::= { scNodeEntry 90 }

    scNodeCntAoUcp30Ack OBJECT-TYPE
        SYNTAX  Counter
        ACCESS  read-only
        STATUS  mandatory
        DESCRIPTION
            "Counts the total number of positive UCP message transfer 
             responses which were received from the SC node."
        ::= { scNodeEntry 91 }

    scNodeCntAoUcp30Nack OBJECT-TYPE
        SYNTAX  Counter
        ACCESS  read-only
        STATUS  mandatory
        DESCRIPTION
            "Counts the total number of negative UCP message transfer 
             responses which were received from the SC node."
        ::= { scNodeEntry 92 }

    scNodeAoUcp30TimeSpent OBJECT-TYPE
        SYNTAX  HighResTime
        ACCESS  read-only
        STATUS  mandatory
        DESCRIPTION
            "Total time spent in processing UCP message transfer requests."
        ::= { scNodeEntry 93 }

    scNodeAoUcp30ShortestRespTime OBJECT-TYPE
        SYNTAX  HighResTime
        ACCESS  read-only
        STATUS  mandatory
        DESCRIPTION
            "Shortest response time for processing a UCP message transfer
             request."
        ::= { scNodeEntry 94 }

    scNodeAoUcp30TimestampShortestResp OBJECT-TYPE
        SYNTAX  TimeStamp
        ACCESS  read-write
        STATUS  mandatory
        DESCRIPTION
            "Timestamp when shortest response time of a UCP message transfer
             request occurred. The shortest response time can be reset
             by setting shortest response timestamp to zero."
        ::= { scNodeEntry 95 }

    scNodeAoUcp30LongestRespTime OBJECT-TYPE
        SYNTAX  HighResTime
        ACCESS  read-only
        STATUS  mandatory
        DESCRIPTION
            "Longest response time for processing a UCP message transfer
             request."
        ::= { scNodeEntry 96 }

    scNodeAoUcp30TimestampLongestResp OBJECT-TYPE
        SYNTAX  TimeStamp
        ACCESS  read-write
        STATUS  mandatory
        DESCRIPTION
            "Timestamp when longest response time of a UCP message transfer
             request occurred. The longest response time can be reset by
             setting longest response timestamp to zero."
        ::= { scNodeEntry 97 }

    scNodeCntAoUcp31Request OBJECT-TYPE
        SYNTAX  Counter
        ACCESS  read-only
        STATUS  mandatory
        DESCRIPTION
            "Counts the total number of UCP alert requests which were
             sent to the SC node."
        ::= { scNodeEntry 100 }

    scNodeCntAoUcp31Ack OBJECT-TYPE
        SYNTAX  Counter
        ACCESS  read-only
        STATUS  mandatory
        DESCRIPTION
            "Counts the total number of positive UCP alert responses
             which were received from the SC node."
        ::= { scNodeEntry 101 }

    scNodeCntAoUcp31Nack OBJECT-TYPE
        SYNTAX  Counter
        ACCESS  read-only
        STATUS  mandatory
        DESCRIPTION
            "Counts the total number of negative UCP alert responses
             which were received from the SC node."
        ::= { scNodeEntry 102 }

    scNodeAoUcp31TimeSpent OBJECT-TYPE
        SYNTAX  HighResTime
        ACCESS  read-only
        STATUS  mandatory
        DESCRIPTION
            "Total time spent in processing UCP alert requests."
        ::= { scNodeEntry 103 }

    scNodeAoUcp31ShortestRespTime OBJECT-TYPE
        SYNTAX  HighResTime
        ACCESS  read-only
        STATUS  mandatory
        DESCRIPTION
            "Shortest response time for processing a UCP alert
             requests."
        ::= { scNodeEntry 104 }

    scNodeAoUcp31TimestampShortestResp OBJECT-TYPE
        SYNTAX  TimeStamp
        ACCESS  read-write
        STATUS  mandatory
        DESCRIPTION
            "Timestamp when shortest response time of a UCP alert
             request occurred. The shortest response time can be reset
             by setting shortest response timestamp to zero."
        ::= { scNodeEntry 105 }

    scNodeAoUcp31LongestRespTime OBJECT-TYPE
        SYNTAX  HighResTime
        ACCESS  read-only
        STATUS  mandatory
        DESCRIPTION
            "Longest response time for processing a UCP alert request."
        ::= { scNodeEntry 106 }

    scNodeAoUcp31TimestampLongestResp OBJECT-TYPE
        SYNTAX  TimeStamp
        ACCESS  read-write
        STATUS  mandatory
        DESCRIPTION
            "Timestamp when longest response time of a UCP alert
             request occurred. The longest response time can be reset by
             setting longest response timestamp to zero."
        ::= { scNodeEntry 107 }

    scNodeCntAoUcp51Request OBJECT-TYPE
        SYNTAX  Counter
        ACCESS  read-only
        STATUS  mandatory
        DESCRIPTION
            "Counts the total number of UCP submit sm requests which were
             sent to the SC node."
        ::= { scNodeEntry 108 }

    scNodeCntAoUcp51Ack OBJECT-TYPE
        SYNTAX  Counter
        ACCESS  read-only
        STATUS  mandatory
        DESCRIPTION
            "Counts the total number of positive UCP submit sm responses
             which were received from the SC node."
        ::= { scNodeEntry 109 }

    scNodeCntAoUcp51Nack OBJECT-TYPE
        SYNTAX  Counter
        ACCESS  read-only
        STATUS  mandatory
        DESCRIPTION
            "Counts the total number of negative UCP submit sm responses
             which were received from the SC node."
        ::= { scNodeEntry 110 }

    scNodeAoUcp51TimeSpent OBJECT-TYPE
        SYNTAX  HighResTime
        ACCESS  read-only
        STATUS  mandatory
        DESCRIPTION
            "Total time spent in processing UCP submit sm requests."
        ::= { scNodeEntry 111 }

    scNodeAoUcp51ShortestRespTime OBJECT-TYPE
        SYNTAX  HighResTime
        ACCESS  read-only
        STATUS  mandatory
        DESCRIPTION
            "Shortest response time for processing a UCP submit sm
             request."
        ::= { scNodeEntry 112 }

    scNodeAoUcp51TimestampShortestResp OBJECT-TYPE
        SYNTAX  TimeStamp
        ACCESS  read-write
        STATUS  mandatory
        DESCRIPTION
            "Timestamp when shortest response time of a UCP submit sm
             request occurred. The shortest response time can be reset
             by setting shortest response timestamp to zero."
        ::= { scNodeEntry 113 }

    scNodeAoUcp51LongestRespTime OBJECT-TYPE
        SYNTAX  HighResTime
        ACCESS  read-only
        STATUS  mandatory
        DESCRIPTION
            "Longest response time for processing a UCP submit sm
             request."
        ::= { scNodeEntry 114 }

    scNodeAoUcp51TimestampLongestResp OBJECT-TYPE
        SYNTAX  TimeStamp
        ACCESS  read-write
        STATUS  mandatory
        DESCRIPTION
            "Timestamp when longest response time of a UCP submit sm
             request occurred. The longest response time can be reset by
             setting longest response timestamp to zero."
        ::= { scNodeEntry 115 }

    scNodeCntAoUcp54Request OBJECT-TYPE
        SYNTAX  Counter
        ACCESS  read-only
        STATUS  mandatory
        DESCRIPTION
            "Counts the total number of UCP modify requests which were
             sent to the SC node."
        ::= { scNodeEntry 116 }

    scNodeCntAoUcp54Ack OBJECT-TYPE
        SYNTAX  Counter
        ACCESS  read-only
        STATUS  mandatory
        DESCRIPTION
            "Counts the total number of positive UCP modify responses
             which were received from the SC node."
        ::= { scNodeEntry 117 }

    scNodeCntAoUcp54Nack OBJECT-TYPE
        SYNTAX  Counter
        ACCESS  read-only
        STATUS  mandatory
        DESCRIPTION
            "Counts the total number of negative UCP modify responses
             which were received from the SC node."
        ::= { scNodeEntry 118 }

    scNodeAoUcp54TimeSpent OBJECT-TYPE
        SYNTAX  HighResTime
        ACCESS  read-only
        STATUS  mandatory
        DESCRIPTION
            "Total time spent in processing UCP modify requests."
        ::= { scNodeEntry 119 }

    scNodeAoUcp54ShortestRespTime OBJECT-TYPE
        SYNTAX  HighResTime
        ACCESS  read-only
        STATUS  mandatory
        DESCRIPTION
            "Shortest response time for processing a UCP modify
             request."
        ::= { scNodeEntry 120 }

    scNodeAoUcp54TimestampShortestResp OBJECT-TYPE
        SYNTAX  TimeStamp
        ACCESS  read-write
        STATUS  mandatory
        DESCRIPTION
            "Timestamp when shortest response time of a UCP modify
             request occurred. The shortest response time can be reset
             by setting shortest response timestamp to zero."
        ::= { scNodeEntry 121 }

    scNodeAoUcp54LongestRespTime OBJECT-TYPE
        SYNTAX  HighResTime
        ACCESS  read-only
        STATUS  mandatory
        DESCRIPTION
            "Longest response time for processing a UCP modify
             request."
        ::= { scNodeEntry 122 }

    scNodeAoUcp54TimestampLongestResp OBJECT-TYPE
        SYNTAX  TimeStamp
        ACCESS  read-write
        STATUS  mandatory
        DESCRIPTION
            "Timestamp when longest response time of a UCP modify
             request occurred. The longest response time can be reset by
             setting longest response timestamp to zero."
        ::= { scNodeEntry 123 }

    scNodeCntAoUcp60Request OBJECT-TYPE
        SYNTAX  Counter
        ACCESS  read-only
        STATUS  mandatory
        DESCRIPTION
            "Counts the total number of UCP session management requests
             which were sent to the SC node."
        ::= { scNodeEntry 124 }

    scNodeCntAoUcp60Ack OBJECT-TYPE
        SYNTAX  Counter
        ACCESS  read-only
        STATUS  mandatory
        DESCRIPTION
            "Counts the total number of positive UCP session management
             responses which were received from the SC node."
        ::= { scNodeEntry 125 }

    scNodeCntAoUcp60Nack OBJECT-TYPE
        SYNTAX  Counter
        ACCESS  read-only
        STATUS  mandatory
        DESCRIPTION
            "Counts the total number of negative UCP session management
             responses which were received from the SC node."
        ::= { scNodeEntry 126 }

    scNodeAoUcp60TimeSpent OBJECT-TYPE
        SYNTAX  HighResTime
        ACCESS  read-only
        STATUS  mandatory
        DESCRIPTION
            "Total time spent in processing UCP session management
             requests."
        ::= { scNodeEntry 127 }

    scNodeAoUcp60ShortestRespTime OBJECT-TYPE
        SYNTAX  HighResTime
        ACCESS  read-only
        STATUS  mandatory
        DESCRIPTION
            "Shortest response time for processing a UCP session
             management request."
        ::= { scNodeEntry 128 }

    scNodeAoUcp60TimestampShortestResp OBJECT-TYPE
        SYNTAX  TimeStamp
        ACCESS  read-write
        STATUS  mandatory
        DESCRIPTION
            "Timestamp when shortest response time of a UCP session
             management request occurred. The shortest response time can
             be reset by setting shortest response timestamp to zero."
        ::= { scNodeEntry 129 }

    scNodeAoUcp60LongestRespTime OBJECT-TYPE
        SYNTAX  HighResTime
        ACCESS  read-only
        STATUS  mandatory
        DESCRIPTION
            "Longest response time for processing a UCP session
             management request."
        ::= { scNodeEntry 130 }

    scNodeAoUcp60TimestampLongestResp OBJECT-TYPE
        SYNTAX  TimeStamp
        ACCESS  read-write
        STATUS  mandatory
        DESCRIPTION
            "Timestamp when longest response time of a UCP session
             management request occurred. The longest response time can
             be reset by setting longest response timestamp to zero."
        ::= { scNodeEntry 131 }

    scNodeCntAoUcpOtherRequest OBJECT-TYPE
        SYNTAX  Counter
        ACCESS  read-only
        STATUS  mandatory
        DESCRIPTION
            "Counts the total number of unknown UCP requests which were
             sent to the SC node."
        ::= { scNodeEntry 132 }

    scNodeCntAoUcpOtherAck OBJECT-TYPE
        SYNTAX  Counter
        ACCESS  read-only
        STATUS  mandatory
        DESCRIPTION
            "Counts the total number of positive unknown UCP responses
             which were received from the SC node."
        ::= { scNodeEntry 133 }

    scNodeCntAoUcpOtherNack OBJECT-TYPE
        SYNTAX  Counter
        ACCESS  read-only
        STATUS  mandatory
        DESCRIPTION
            "Counts the total number of negative unknown UCP responses
             which were received from the SC node."
        ::= { scNodeEntry 134 }

    scNodeAoUcpOtherTimeSpent OBJECT-TYPE
        SYNTAX  HighResTime
        ACCESS  read-only
        STATUS  mandatory
        DESCRIPTION
            "Total time spent in processing unknown UCP requests."
        ::= { scNodeEntry 135 }

    scNodeAoUcpOtherShortestRespTime OBJECT-TYPE
        SYNTAX  HighResTime
        ACCESS  read-only
        STATUS  mandatory
        DESCRIPTION
            "Shortest response time for processing an unknown UCP
             request."
        ::= { scNodeEntry 136 }

    scNodeAoUcpOtherTimestampShortestResp OBJECT-TYPE
        SYNTAX  TimeStamp
        ACCESS  read-write
        STATUS  mandatory
        DESCRIPTION
            "Timestamp when shortest response time of an unknown UCP
             request occurred. The shortest response time can be reset
             by setting shortest response timestamp to zero."
        ::= { scNodeEntry 137 }

    scNodeAoUcpOtherLongestRespTime OBJECT-TYPE
        SYNTAX  HighResTime
        ACCESS  read-only
        STATUS  mandatory
        DESCRIPTION
            "Longest response time for processing an unknown UCP
             request."
        ::= { scNodeEntry 138 }

    scNodeAoUcpOtherTimestampLongestResp OBJECT-TYPE
        SYNTAX  TimeStamp
        ACCESS  read-write
        STATUS  mandatory
        DESCRIPTION
            "Timestamp when longest response time of an unknown UCP
             request occurred. The longest response time can be reset by
             setting longest response timestamp to zero."
        ::= { scNodeEntry 139 }

    scNodeCntAoUcp55Request OBJECT-TYPE
        SYNTAX  Counter
        ACCESS  read-only
        STATUS  mandatory
        DESCRIPTION
            "Counts the total number of UCP inquiry message requests
             which were sent to the SC node."
        ::= { scNodeEntry 140 }

    scNodeCntAoUcp55Ack OBJECT-TYPE
        SYNTAX  Counter
        ACCESS  read-only
        STATUS  mandatory
        DESCRIPTION
            "Counts the total number of positive UCP inquiry message
             responses which were received from the SC node."
        ::= { scNodeEntry 141 }

    scNodeCntAoUcp55Nack OBJECT-TYPE
        SYNTAX  Counter
        ACCESS  read-only
        STATUS  mandatory
        DESCRIPTION
            "Counts the total number of negative UCP inquiry message
             responses which were received from the SC node."
        ::= { scNodeEntry 142 }

    scNodeAoUcp55TimeSpent OBJECT-TYPE
        SYNTAX  HighResTime
        ACCESS  read-only
        STATUS  mandatory
        DESCRIPTION
            "Total time spent in processing UCP inquiry message
             requests."
        ::= { scNodeEntry 143 }

    scNodeAoUcp55ShortestRespTime OBJECT-TYPE
        SYNTAX  HighResTime
        ACCESS  read-only
        STATUS  mandatory
        DESCRIPTION
            "Shortest response time for processing a UCP inquiry message
             request."
        ::= { scNodeEntry 144 }

    scNodeAoUcp55TimestampShortestResp OBJECT-TYPE
        SYNTAX  TimeStamp
        ACCESS  read-write
        STATUS  mandatory
        DESCRIPTION
            "Timestamp when shortest response time of a UCP inquiry
             message request occurred. The shortest response time can be
             reset by setting shortest response timestamp to zero."
        ::= { scNodeEntry 145 }

    scNodeAoUcp55LongestRespTime OBJECT-TYPE
        SYNTAX  HighResTime
        ACCESS  read-only
        STATUS  mandatory
        DESCRIPTION
            "Longest response time for processing a UCP inquiry message
             request."
        ::= { scNodeEntry 146 }

    scNodeAoUcp55TimestampLongestResp OBJECT-TYPE
        SYNTAX  TimeStamp
        ACCESS  read-write
        STATUS  mandatory
        DESCRIPTION
            "Timestamp when longest response time of a UCP inquiry
             message request occurred. The longest response time can be
             reset by setting longest response timestamp to zero."
        ::= { scNodeEntry 147 }

    scNodeCntAoUcp56Request OBJECT-TYPE
        SYNTAX  Counter
        ACCESS  read-only
        STATUS  mandatory
        DESCRIPTION
            "Counts the total number of UCP delete message requests
             which were sent to the SC node."
        ::= { scNodeEntry 148 }

    scNodeCntAoUcp56Ack OBJECT-TYPE
        SYNTAX  Counter
        ACCESS  read-only
        STATUS  mandatory
        DESCRIPTION
            "Counts the total number of positive UCP delete message
             responses which were received from the SC node."
        ::= { scNodeEntry 149 }

    scNodeCntAoUcp56Nack OBJECT-TYPE
        SYNTAX  Counter
        ACCESS  read-only
        STATUS  mandatory
        DESCRIPTION
            "Counts the total number of negative UCP delete message
             responses which were received from the SC node."
        ::= { scNodeEntry 150 }

    scNodeAoUcp56TimeSpent OBJECT-TYPE
        SYNTAX  HighResTime
        ACCESS  read-only
        STATUS  mandatory
        DESCRIPTION
            "Total time spent in processing UCP delete message
             requests."
        ::= { scNodeEntry 151 }

    scNodeAoUcp56ShortestRespTime OBJECT-TYPE
        SYNTAX  HighResTime
        ACCESS  read-only
        STATUS  mandatory
        DESCRIPTION
            "Shortest response time for processing a UCP delete message
             request."
        ::= { scNodeEntry 152 }

    scNodeAoUcp56TimestampShortestResp OBJECT-TYPE
        SYNTAX  TimeStamp
        ACCESS  read-write
        STATUS  mandatory
        DESCRIPTION
            "Timestamp when shortest response time of a UCP delete
             message request occurred. The shortest response time can be
             reset by setting shortest response timestamp to zero."
        ::= { scNodeEntry 153 }

    scNodeAoUcp56LongestRespTime OBJECT-TYPE
        SYNTAX  HighResTime
        ACCESS  read-only
        STATUS  mandatory
        DESCRIPTION
            "Longest response time for processing a UCP delete message
             request."
        ::= { scNodeEntry 154 }

    scNodeAoUcp56TimestampLongestResp OBJECT-TYPE
        SYNTAX  TimeStamp
        ACCESS  read-write
        STATUS  mandatory
        DESCRIPTION
            "Timestamp when longest response time of a UCP delete
             message request occurred. The longest response time can be
             reset by setting longest response timestamp to zero."
        ::= { scNodeEntry 155 }

    scNodeCntAoSmppSubmitSmRequest OBJECT-TYPE
        SYNTAX  Counter
        ACCESS  read-only
        STATUS  mandatory
        DESCRIPTION
            "Counts the total number of SMPP submit sm requests which
             were sent to the SC node."
        ::= { scNodeEntry 200 }

    scNodeCntAoSmppSubmitSmAck OBJECT-TYPE
        SYNTAX  Counter
        ACCESS  read-only
        STATUS  mandatory
        DESCRIPTION
            "Counts the total number of positive SMPP submit sm
             responses which were received from the SC node."
        ::= { scNodeEntry 201 }

    scNodeCntAoSmppSubmitSmNack OBJECT-TYPE
        SYNTAX  Counter
        ACCESS  read-only
        STATUS  mandatory
        DESCRIPTION
            "Counts the total number of negative SMPP submit sm
             responses which were received from the SC node."
        ::= { scNodeEntry 202 }

    scNodeAoSmppSubmitSmTimeSpent OBJECT-TYPE
        SYNTAX  HighResTime
        ACCESS  read-only
        STATUS  mandatory
        DESCRIPTION
            "Total time spent in processing SMPP submit sm requests."
        ::= { scNodeEntry 203 }

    scNodeAoSmppSubmitSmShortestRespTime OBJECT-TYPE
        SYNTAX  HighResTime
        ACCESS  read-only
        STATUS  mandatory
        DESCRIPTION
            "Shortest response time for processing an SMPP submit sm
             request."
        ::= { scNodeEntry 204 }

    scNodeAoSmppSubmitSmTimestampShortestResp OBJECT-TYPE
        SYNTAX  TimeStamp
        ACCESS  read-write
        STATUS  mandatory
        DESCRIPTION
            "Timestamp when shortest response time of an SMPP submit sm
             request occurred. The shortest response time can be reset
             by setting shortest response timestamp to zero."
        ::= { scNodeEntry 205 }

    scNodeAoSmppSubmitSmLongestRespTime OBJECT-TYPE
        SYNTAX  HighResTime
        ACCESS  read-only
        STATUS  mandatory
        DESCRIPTION
            "Longest response time for processing an SMPP submit sm
             request."
        ::= { scNodeEntry 206 }

    scNodeAoSmppSubmitSmTimestampLongestResp OBJECT-TYPE
        SYNTAX  TimeStamp
        ACCESS  read-write
        STATUS  mandatory
        DESCRIPTION
            "Timestamp when longest response time of an SMPP submit sm
             request occurred. The longest response time can be reset by
             setting the related  timestamp to zero."
        ::= { scNodeEntry 207 }

    scNodeCntAoSmppDataSmRequest OBJECT-TYPE
        SYNTAX  Counter
        ACCESS  read-only
        STATUS  mandatory
        DESCRIPTION
            "Counts the total number of SMPP data sm requests which were
             sent to the SC node."
        ::= { scNodeEntry 208 }

    scNodeCntAoSmppDataSmAck OBJECT-TYPE
        SYNTAX  Counter
        ACCESS  read-only
        STATUS  mandatory
        DESCRIPTION
            "Counts the total number of positive SMPP data sm responses
             which were received from the SC node."
        ::= { scNodeEntry 209 }

    scNodeCntAoSmppDataSmNack OBJECT-TYPE
        SYNTAX  Counter
        ACCESS  read-only
        STATUS  mandatory
        DESCRIPTION
            "Counts the total number of negative SMPP data sm responses
             which were received from the SC node."
        ::= { scNodeEntry 210 }

    scNodeAoSmppDataSmTimeSpent OBJECT-TYPE
        SYNTAX  HighResTime
        ACCESS  read-only
        STATUS  mandatory
        DESCRIPTION
            "Total time spent in processing SMPP data sm requests."
        ::= { scNodeEntry 211 }

    scNodeAoSmppDataSmShortestRespTime OBJECT-TYPE
        SYNTAX  HighResTime
        ACCESS  read-only
        STATUS  mandatory
        DESCRIPTION
            "Shortest response time for processing an SMPP data sm
             request."
        ::= { scNodeEntry 212 }

    scNodeAoSmppDataSmTimestampShortestResp OBJECT-TYPE
        SYNTAX  TimeStamp
        ACCESS  read-write
        STATUS  mandatory
        DESCRIPTION
            "Timestamp when shortest response time of an SMPP data sm
             request occurred. The shortest response time can be reset
             by setting shortest response timestamp to zero."
        ::= { scNodeEntry 213 }

    scNodeAoSmppDataSmLongestRespTime OBJECT-TYPE
        SYNTAX  HighResTime
        ACCESS  read-only
        STATUS  mandatory
        DESCRIPTION
            "Longest response time for processing an SMPP data sm
             request."
        ::= { scNodeEntry 214 }

    scNodeAoSmppDataSmTimestampLongestResp OBJECT-TYPE
        SYNTAX  TimeStamp
        ACCESS  read-write
        STATUS  mandatory
        DESCRIPTION
            "Timestamp when longest response time of an SMPP data sm
             request occurred. The longest response time can be reset by
             setting longest response timestamp to zero."
        ::= { scNodeEntry 215 }

    scNodeCntAoSmppBindRxRequest OBJECT-TYPE
        SYNTAX  Counter
        ACCESS  read-only
        STATUS  mandatory
        DESCRIPTION
            "Counts the total number of SMPP bind receiver requests
             which were sent to the SC node."
        ::= { scNodeEntry 216 }

    scNodeCntAoSmppBindRxAck OBJECT-TYPE
        SYNTAX  Counter
        ACCESS  read-only
        STATUS  mandatory
        DESCRIPTION
            "Counts the total number of positive SMPP bind receiver
             responses which were received from the SC node."
        ::= { scNodeEntry 217 }

    scNodeCntAoSmppBindRxNack OBJECT-TYPE
        SYNTAX  Counter
        ACCESS  read-only
        STATUS  mandatory
        DESCRIPTION
            "Counts the total number of negative SMPP bind receiver
             responses which were received from the SC node."
        ::= { scNodeEntry 218 }

    scNodeAoSmppBindRxTimeSpent OBJECT-TYPE
        SYNTAX  HighResTime
        ACCESS  read-only
        STATUS  mandatory
        DESCRIPTION
            "Total time spent in processing SMPP bind receiver
             requests."
        ::= { scNodeEntry 219 }

    scNodeAoSmppBindRxShortestRespTime OBJECT-TYPE
        SYNTAX  HighResTime
        ACCESS  read-only
        STATUS  mandatory
        DESCRIPTION
            "Shortest response time for processing an SMPP bind receiver
             request."
        ::= { scNodeEntry 220 }

    scNodeAoSmppBindRxTimestampShortestResp OBJECT-TYPE
        SYNTAX  TimeStamp
        ACCESS  read-write
        STATUS  mandatory
        DESCRIPTION
            "Timestamp when shortest response time of an SMPP bind
             receiver request occurred. The shortest response time can
             be reset by setting shortest response timestamp to zero."
        ::= { scNodeEntry 221 }

    scNodeAoSmppBindRxLongestRespTime OBJECT-TYPE
        SYNTAX  HighResTime
        ACCESS  read-only
        STATUS  mandatory
        DESCRIPTION
            "Longest response time for processing an SMPP bind receiver
             request."
        ::= { scNodeEntry 222 }

    scNodeAoSmppBindRxTimestampLongestResp OBJECT-TYPE
        SYNTAX  TimeStamp
        ACCESS  read-write
        STATUS  mandatory
        DESCRIPTION
            "Timestamp when longest response time of an SMPP bind
             receiver request occurred. The longest response time can be
             reset by setting the related  timestamp to zero."
        ::= { scNodeEntry 223 }

    scNodeCntAoSmppBindTxRequest OBJECT-TYPE
        SYNTAX  Counter
        ACCESS  read-only
        STATUS  mandatory
        DESCRIPTION
            "Counts the total number of SMPP bind transmitter requests
             which were sent to the SC node."
        ::= { scNodeEntry 224 }

    scNodeCntAoSmppBindTxAck OBJECT-TYPE
        SYNTAX  Counter
        ACCESS  read-only
        STATUS  mandatory
        DESCRIPTION
            "Counts the total number of positive SMPP bind transmitter
             responses which were received from the SC node."
        ::= { scNodeEntry 225 }

    scNodeCntAoSmppBindTxNack OBJECT-TYPE
        SYNTAX  Counter
        ACCESS  read-only
        STATUS  mandatory
        DESCRIPTION
            "Counts the total number of negative SMPP bind transmitter
             responses which were received from the SC node."
        ::= { scNodeEntry 226 }

    scNodeAoSmppBindTxTimeSpent OBJECT-TYPE
        SYNTAX  HighResTime
        ACCESS  read-only
        STATUS  mandatory
        DESCRIPTION
            "Total time spent in processing SMPP bind transmitter
             requests."
        ::= { scNodeEntry 227 }

    scNodeAoSmppBindTxShortestRespTime OBJECT-TYPE
        SYNTAX  HighResTime
        ACCESS  read-only
        STATUS  mandatory
        DESCRIPTION
            "Shortest response time for processing an SMPP bind
             transmitter request."
        ::= { scNodeEntry 228 }

    scNodeAoSmppBindTxTimestampShortestResp OBJECT-TYPE
        SYNTAX  TimeStamp
        ACCESS  read-write
        STATUS  mandatory
        DESCRIPTION
            "Timestamp when shortest response time of an SMPP bind
             transmitter request occurred. The shortest response time
             can be reset by setting shortest response timestamp to
             zero."
        ::= { scNodeEntry 229 }

    scNodeAoSmppBindTxLongestRespTime OBJECT-TYPE
        SYNTAX  HighResTime
        ACCESS  read-only
        STATUS  mandatory
        DESCRIPTION
            "Longest response time for processing an SMPP bind
             transmitter request."
        ::= { scNodeEntry 230 }

    scNodeAoSmppBindTxTimestampLongestResp OBJECT-TYPE
        SYNTAX  TimeStamp
        ACCESS  read-write
        STATUS  mandatory
        DESCRIPTION
            "Timestamp when longest response time of an SMPP bind
             transmitter request occurred. The longest response time can
             be reset by setting longest response timestamp to zero."
        ::= { scNodeEntry 231 }

    scNodeCntAoSmppBindTrxRequest OBJECT-TYPE
        SYNTAX  Counter
        ACCESS  read-only
        STATUS  mandatory
        DESCRIPTION
            "Counts the total number of SMPP bind transceiver requests
             which were sent to the SC node."
        ::= { scNodeEntry 232 }

    scNodeCntAoSmppBindTrxAck OBJECT-TYPE
        SYNTAX  Counter
        ACCESS  read-only
        STATUS  mandatory
        DESCRIPTION
            "Counts the total number of positive SMPP bind transceiver 
             responses which were received from the SC node."
        ::= { scNodeEntry 233 }

    scNodeCntAoSmppBindTrxNack OBJECT-TYPE
        SYNTAX  Counter
        ACCESS  read-only
        STATUS  mandatory
        DESCRIPTION
            "Counts the total number of negative SMPP bind transceiver 
             responses which were received from the SC node."
        ::= { scNodeEntry 234 }

    scNodeAoSmppBindTrxTimeSpent OBJECT-TYPE
        SYNTAX  HighResTime
        ACCESS  read-only
        STATUS  mandatory
        DESCRIPTION
            "Total time spent in processing SMPP bind transceiver 
             requests."
        ::= { scNodeEntry 235 }

    scNodeAoSmppBindTrxShortestRespTime OBJECT-TYPE
        SYNTAX  HighResTime
        ACCESS  read-only
        STATUS  mandatory
        DESCRIPTION
            "Shortest response time for processing an SMPP bind
             transceiver request."
        ::= { scNodeEntry 236 }

    scNodeAoSmppBindTrxTimestampShortestResp OBJECT-TYPE
        SYNTAX  TimeStamp
        ACCESS  read-write
        STATUS  mandatory
        DESCRIPTION
            "Timestamp when shortest response time of an SMPP bind
             transceiver request occurred. The shortest response time
             can be reset by setting shortest response timestamp to
             zero."
        ::= { scNodeEntry 237 }

    scNodeAoSmppBindTrxLongestRespTime OBJECT-TYPE
        SYNTAX  HighResTime
        ACCESS  read-only
        STATUS  mandatory
        DESCRIPTION
            "Longest response time for processing an SMPP bind
             transceiver request."
        ::= { scNodeEntry 238 }

    scNodeAoSmppBindTrxTimestampLongestResp OBJECT-TYPE
        SYNTAX  TimeStamp
        ACCESS  read-write
        STATUS  mandatory
        DESCRIPTION
            "Timestamp when longest response time of an SMPP bind
             transceiver request occurred. The longest response time can
             be reset by setting the related  timestamp to zero."
        ::= { scNodeEntry 239 }

    scNodeCntAoSmppUnbindRequest OBJECT-TYPE
        SYNTAX  Counter
        ACCESS  read-only
        STATUS  mandatory
        DESCRIPTION
            "Counts the total number of SMPP unbind requests which were
             sent to the SC node."
        ::= { scNodeEntry 240 }

    scNodeCntAoSmppUnbindAck OBJECT-TYPE
        SYNTAX  Counter
        ACCESS  read-only
        STATUS  mandatory
        DESCRIPTION
            "Counts the total number of positive SMPP unbind responses
             which were received from the SC node."
        ::= { scNodeEntry 241 }

    scNodeCntAoSmppUnbindNack OBJECT-TYPE
        SYNTAX  Counter
        ACCESS  read-only
        STATUS  mandatory
        DESCRIPTION
            "Counts the total number of negative SMPP unbind responses
             which were received from the SC node."
        ::= { scNodeEntry 242 }

    scNodeAoSmppUnbindTimeSpent OBJECT-TYPE
        SYNTAX  HighResTime
        ACCESS  read-only
        STATUS  mandatory
        DESCRIPTION
            "Total time spent in processing SMPP unbind requests."
        ::= { scNodeEntry 243 }

    scNodeAoSmppUnbindShortestRespTime OBJECT-TYPE
        SYNTAX  HighResTime
        ACCESS  read-only
        STATUS  mandatory
        DESCRIPTION
            "Shortest response time for processing an SMPP unbind
             requests."
        ::= { scNodeEntry 244 }

    scNodeAoSmppUnbindTimestampShortestResp OBJECT-TYPE
        SYNTAX  TimeStamp
        ACCESS  read-write
        STATUS  mandatory
        DESCRIPTION
            "Timestamp when shortest response time of an SMPP unbind
             request occurred. The shortest response time can be reset
             by setting shortest response timestamp to zero."
        ::= { scNodeEntry 245 }

    scNodeAoSmppUnbindLongestRespTime OBJECT-TYPE
        SYNTAX  HighResTime
        ACCESS  read-only
        STATUS  mandatory
        DESCRIPTION
            "Longest response time for processing an SMPP unbind
             requests."
        ::= { scNodeEntry 246 }

    scNodeAoSmppUnbindTimestampLongestResp OBJECT-TYPE
        SYNTAX  TimeStamp
        ACCESS  read-write
        STATUS  mandatory
        DESCRIPTION
            "Timestamp when longest response time of an SMPP unbind
             request occurred. The longest response time can be reset by
             setting longest response timestamp to zero."
        ::= { scNodeEntry 247 }

    scNodeCntAoSmppQuerySmRequest OBJECT-TYPE
        SYNTAX  Counter
        ACCESS  read-only
        STATUS  mandatory
        DESCRIPTION
            "Counts the total number of SMPP query sm requests which were
             sent to the SC node."
        ::= { scNodeEntry 248 }

    scNodeCntAoSmppQuerySmAck OBJECT-TYPE
        SYNTAX  Counter
        ACCESS  read-only
        STATUS  mandatory
        DESCRIPTION
            "Counts the total number of positive SMPP query sm responses
             which were received from the SC node."
        ::= { scNodeEntry 249 }

    scNodeCntAoSmppQuerySmNack OBJECT-TYPE
        SYNTAX  Counter
        ACCESS  read-only
        STATUS  mandatory
        DESCRIPTION
            "Counts the total number of negative SMPP query sm responses
             which were received from the SC node."
        ::= { scNodeEntry 250 }

    scNodeAoSmppQuerySmTimeSpent OBJECT-TYPE
        SYNTAX  HighResTime
        ACCESS  read-only
        STATUS  mandatory
        DESCRIPTION
            "Total time spent in processing SMPP query sm requests."
        ::= { scNodeEntry 251 }

    scNodeAoSmppQuerySmShortestRespTime OBJECT-TYPE
        SYNTAX  HighResTime
        ACCESS  read-only
        STATUS  mandatory
        DESCRIPTION
            "Shortest response time for processing an SMPP query sm
             request."
        ::= { scNodeEntry 252 }

    scNodeAoSmppQuerySmTimestampShortestResp OBJECT-TYPE
        SYNTAX  TimeStamp
        ACCESS  read-write
        STATUS  mandatory
        DESCRIPTION
            "Timestamp when shortest response time of an SMPP query sm
             request occurred. The shortest response time can be reset
             by setting shortest response timestamp to zero."
        ::= { scNodeEntry 253 }

    scNodeAoSmppQuerySmLongestRespTime OBJECT-TYPE
        SYNTAX  HighResTime
        ACCESS  read-only
        STATUS  mandatory
        DESCRIPTION
            "Longest response time for processing an SMPP query sm
             request."
        ::= { scNodeEntry 254 }

    scNodeAoSmppQuerySmTimestampLongestResp OBJECT-TYPE
        SYNTAX  TimeStamp
        ACCESS  read-write
        STATUS  mandatory
        DESCRIPTION
            "Timestamp when longest response time of an SMPP query sm
             request occurred. The longest response time can be reset by
             setting the related  timestamp to zero."
        ::= { scNodeEntry 255 }

    scNodeCntAoSmppReplaceSmRequest OBJECT-TYPE
        SYNTAX  Counter
        ACCESS  read-only
        STATUS  mandatory
        DESCRIPTION
            "Counts the total number of SMPP replace sm requests which
             were sent to the SC node."
        ::= { scNodeEntry 256 }

    scNodeCntAoSmppReplaceSmAck OBJECT-TYPE
        SYNTAX  Counter
        ACCESS  read-only
        STATUS  mandatory
        DESCRIPTION
            "Counts the total number of positive SMPP replace sm
             responses which were received from the SC node."
        ::= { scNodeEntry 257 }

    scNodeCntAoSmppReplaceSmNack OBJECT-TYPE
        SYNTAX  Counter
        ACCESS  read-only
        STATUS  mandatory
        DESCRIPTION
            "Counts the total number of negative SMPP replace sm
             responses which were received from the SC node."
        ::= { scNodeEntry 258 }

    scNodeAoSmppReplaceSmTimeSpent OBJECT-TYPE
        SYNTAX  HighResTime
        ACCESS  read-only
        STATUS  mandatory
        DESCRIPTION
            "Total time spent in processing SMPP replace sm requests."
        ::= { scNodeEntry 259 }

    scNodeAoSmppReplaceSmShortestRespTime OBJECT-TYPE
        SYNTAX  HighResTime
        ACCESS  read-only
        STATUS  mandatory
        DESCRIPTION
            "Shortest response time for processing an SMPP replace sm
             request."
        ::= { scNodeEntry 260 }

    scNodeAoSmppReplaceSmTimestampShortestResp OBJECT-TYPE
        SYNTAX  TimeStamp
        ACCESS  read-write
        STATUS  mandatory
        DESCRIPTION
            "Timestamp when shortest response time of an SMPP replace sm
             request occurred. The shortest response time can be reset
             by setting shortest response timestamp to zero."
        ::= { scNodeEntry 261 }

    scNodeAoSmppReplaceSmLongestRespTime OBJECT-TYPE
        SYNTAX  HighResTime
        ACCESS  read-only
        STATUS  mandatory
        DESCRIPTION
            "Longest response time for processing an SMPP replace sm
             request."
        ::= { scNodeEntry 262 }

    scNodeAoSmppReplaceSmTimestampLongestResp OBJECT-TYPE
        SYNTAX  TimeStamp
        ACCESS  read-write
        STATUS  mandatory
        DESCRIPTION
            "Timestamp when longest response time of an SMPP replace sm
             request occurred. The longest response time can be reset by
             setting longest response timestamp to zero."
        ::= { scNodeEntry 263 }

    scNodeCntAoSmppCancelSmRequest OBJECT-TYPE
        SYNTAX  Counter
        ACCESS  read-only
        STATUS  mandatory
        DESCRIPTION
            "Counts the total number of SMPP cancel sm requests which
             were sent to the SC node."
        ::= { scNodeEntry 264 }

    scNodeCntAoSmppCancelSmAck OBJECT-TYPE
        SYNTAX  Counter
        ACCESS  read-only
        STATUS  mandatory
        DESCRIPTION
            "Counts the total number of positive SMPP cancel sm
             responses which were received from the SC node."
        ::= { scNodeEntry 265 }

    scNodeCntAoSmppCancelSmNack OBJECT-TYPE
        SYNTAX  Counter
        ACCESS  read-only
        STATUS  mandatory
        DESCRIPTION
            "Counts the total number of negative SMPP cancel sm
             responses which were received from the SC node."
        ::= { scNodeEntry 266 }

    scNodeAoSmppCancelSmTimeSpent OBJECT-TYPE
        SYNTAX  HighResTime
        ACCESS  read-only
        STATUS  mandatory
        DESCRIPTION
            "Total time spent in processing SMPP cancel sm requests."
        ::= { scNodeEntry 267 }

    scNodeAoSmppCancelSmShortestRespTime OBJECT-TYPE
        SYNTAX  HighResTime
        ACCESS  read-only
        STATUS  mandatory
        DESCRIPTION
            "Shortest response time for processing an SMPP cancel sm
             request."
        ::= { scNodeEntry 268 }

    scNodeAoSmppCancelSmTimestampShortestResp OBJECT-TYPE
        SYNTAX  TimeStamp
        ACCESS  read-write
        STATUS  mandatory
        DESCRIPTION
            "Timestamp when longest response time of an SMPP cancel sm
             request occurred. The shortest response time can be reset
             by setting shortest response timestamp to zero."
        ::= { scNodeEntry 269 }

    scNodeAoSmppCancelSmLongestRespTime OBJECT-TYPE
        SYNTAX  HighResTime
        ACCESS  read-only
        STATUS  mandatory
        DESCRIPTION
            "Longest response time for processing an SMPP cancel sm
             request."
        ::= { scNodeEntry 270 }

    scNodeAoSmppCancelSmTimestampLongestResp OBJECT-TYPE
        SYNTAX  TimeStamp
        ACCESS  read-write
        STATUS  mandatory
        DESCRIPTION
            "Timestamp when longest response time of an SMPP cancel sm
             request occurred. The longest response time can be reset by
             setting the related  timestamp to zero."
        ::= { scNodeEntry 271 }

    scNodeCntAoSmppEnquireLinkRequest OBJECT-TYPE
        SYNTAX  Counter
        ACCESS  read-only
        STATUS  mandatory
        DESCRIPTION
            "Counts the total number of SMPP enquire link requests which
             were sent to the SC node."
        ::= { scNodeEntry 272 }

    scNodeCntAoSmppEnquireLinkAck OBJECT-TYPE
        SYNTAX  Counter
        ACCESS  read-only
        STATUS  mandatory
        DESCRIPTION
            "Counts the total number of positive SMPP enquire link
             responses which were received from the SC node."
        ::= { scNodeEntry 273 }

    scNodeCntAoSmppEnquireLinkNack OBJECT-TYPE
        SYNTAX  Counter
        ACCESS  read-only
        STATUS  mandatory
        DESCRIPTION
            "Counts the total number of negative SMPP enquire link
             responses which were received from the SC node."
        ::= { scNodeEntry 274 }

    scNodeAoSmppEnquireLinkTimeSpent OBJECT-TYPE
        SYNTAX  HighResTime
        ACCESS  read-only
        STATUS  mandatory
        DESCRIPTION
            "Total time spent in processing SMPP enquire link requests."
        ::= { scNodeEntry 275 }

    scNodeAoSmppEnquireLinkShortestRespTime OBJECT-TYPE
        SYNTAX  HighResTime
        ACCESS  read-only
        STATUS  mandatory
        DESCRIPTION
            "Shortest response time for processing an SMPP enquire link
             requests."
        ::= { scNodeEntry 276 }

    scNodeAoSmppEnquireLinkTimestampShortestResp OBJECT-TYPE
        SYNTAX  TimeStamp
        ACCESS  read-write
        STATUS  mandatory
        DESCRIPTION
            "Timestamp when longest response time of an SMPP enquire
             link request occurred. The shortest response time can be
             reset by setting shortest response timestamp to zero."
        ::= { scNodeEntry 277 }

    scNodeAoSmppEnquireLinkLongestRespTime OBJECT-TYPE
        SYNTAX  HighResTime
        ACCESS  read-only
        STATUS  mandatory
        DESCRIPTION
            "Longest response time for processing an SMPP enquire link
             request."
        ::= { scNodeEntry 278 }

    scNodeAoSmppEnquireLinkTimestampLongestResp OBJECT-TYPE
        SYNTAX  TimeStamp
        ACCESS  read-write
        STATUS  mandatory
        DESCRIPTION
            "Timestamp when longest response time of an SMPP enquire
             link request occurred. The longest response time can be
             reset by setting the related  timestamp to zero."
        ::= { scNodeEntry 279 }

    scNodeCntAoSmppOtherRequest OBJECT-TYPE
        SYNTAX  Counter
        ACCESS  read-only
        STATUS  mandatory
        DESCRIPTION
            "Counts the total number of SMPP unknown requests which were
             sent to the SC node."
        ::= { scNodeEntry 280 }

    scNodeCntAoSmppOtherAck OBJECT-TYPE
        SYNTAX  Counter
        ACCESS  read-only
        STATUS  mandatory
        DESCRIPTION
            "Counts the total number of positive SMPP unknown responses
             which were received from the SC node."
        ::= { scNodeEntry 281 }

    scNodeCntAoSmppOtherNack OBJECT-TYPE
        SYNTAX  Counter
        ACCESS  read-only
        STATUS  mandatory
        DESCRIPTION
            "Counts the total number of negative SMPP unknown responses
             which were received from the SC node."
        ::= { scNodeEntry 282 }

    scNodeAoSmppOtherTimeSpent OBJECT-TYPE
        SYNTAX  HighResTime
        ACCESS  read-only
        STATUS  mandatory
        DESCRIPTION
            "Total time spent in processing SMPP unknown requests."
        ::= { scNodeEntry 283 }

    scNodeAoSmppOtherShortestRespTime OBJECT-TYPE
        SYNTAX  HighResTime
        ACCESS  read-only
        STATUS  mandatory
        DESCRIPTION
            "Shortest response time for processing an SMPP unknown
             request."
        ::= { scNodeEntry 284 }

    scNodeAoSmppOtherTimestampShortestResp OBJECT-TYPE
        SYNTAX  TimeStamp
        ACCESS  read-write
        STATUS  mandatory
        DESCRIPTION
            "Timestamp when shortest response time of an SMPP unknown
             request occurred. The shortest response time can be reset
             by setting shortest response timestamp to zero."
        ::= { scNodeEntry 285 }

    scNodeAoSmppOtherLongestRespTime OBJECT-TYPE
        SYNTAX  HighResTime
        ACCESS  read-only
        STATUS  mandatory
        DESCRIPTION
            "Longest response time for processing an SMPP unknown
             request."
        ::= { scNodeEntry 286 }

    scNodeAoSmppOtherTimestampLongestResp OBJECT-TYPE
        SYNTAX  TimeStamp
        ACCESS  read-write
        STATUS  mandatory
        DESCRIPTION
            "Timestamp when longest response time of an SMPP unknown
             request occurred. The longest response time can be reset by
             setting longest response timestamp to zero."
        ::= { scNodeEntry 287 }

    scNodeAoSmppGenericNack OBJECT-TYPE
        SYNTAX  Counter
        ACCESS  read-only
        STATUS  mandatory
        DESCRIPTION
            "Counts the total number of SMPP generic nacks which were
             received from the SC node."
        ::= { scNodeEntry 288 }

    scNodeCntAoCimdLoginRequest OBJECT-TYPE
        SYNTAX  Counter
        ACCESS  read-only
        STATUS  mandatory
        DESCRIPTION
            "Counts the total number of CIMD login requests which were
             sent to the SC node."
        ::= { scNodeEntry 300 }

    scNodeCntAoCimdLoginAck OBJECT-TYPE
        SYNTAX  Counter
        ACCESS  read-only
        STATUS  mandatory
        DESCRIPTION
            "Counts the total number of positive CIMD login responses
             which were received from the SC node."
        ::= { scNodeEntry 301 }

    scNodeCntAoCimdLoginNack OBJECT-TYPE
        SYNTAX  Counter
        ACCESS  read-only
        STATUS  mandatory
        DESCRIPTION
            "Counts the total number of negative CIMD login responses
             which were received from the SC node."
        ::= { scNodeEntry 302 }

    scNodeAoCimdLoginTimeSpent OBJECT-TYPE
        SYNTAX  HighResTime
        ACCESS  read-only
        STATUS  mandatory
        DESCRIPTION
            "Total time spent in processing CIMD login requests."
        ::= { scNodeEntry 303 }

    scNodeAoCimdLoginShortestRespTime OBJECT-TYPE
        SYNTAX  HighResTime
        ACCESS  read-only
        STATUS  mandatory
        DESCRIPTION
            "Shortest response time for processing a CIMD login
             requests."
        ::= { scNodeEntry 304 }

    scNodeAoCimdLoginTimestampShortestResp OBJECT-TYPE
        SYNTAX  TimeStamp
        ACCESS  read-write
        STATUS  mandatory
        DESCRIPTION
            "Timestamp when shortest response time of a CIMD login
             request occurred. The shortest response time can be reset
             by setting shortest response timestamp to zero."
        ::= { scNodeEntry 305 }

    scNodeAoCimdLoginLongestRespTime OBJECT-TYPE
        SYNTAX  HighResTime
        ACCESS  read-only
        STATUS  mandatory
        DESCRIPTION
            "Longest response time for processing a CIMD login
             request."
        ::= { scNodeEntry 306 }

    scNodeAoCimdLoginTimestampLongestResp OBJECT-TYPE
        SYNTAX  TimeStamp
        ACCESS  read-write
        STATUS  mandatory
        DESCRIPTION
            "Timestamp when longest response time of a CIMD login
             request occurred. The longest response time can be reset by
             setting the related  timestamp to zero."
        ::= { scNodeEntry 307 }

    scNodeCntAoCimdLogoutRequest OBJECT-TYPE
        SYNTAX  Counter
        ACCESS  read-only
        STATUS  mandatory
        DESCRIPTION
            "Counts the total number of CIMD logout requests which were
             sent to the SC node."
        ::= { scNodeEntry 308 }

    scNodeCntAoCimdLogoutAck OBJECT-TYPE
        SYNTAX  Counter
        ACCESS  read-only
        STATUS  mandatory
        DESCRIPTION
            "Counts the total number of positive CIMD logout responses
             which were received from the SC node."
        ::= { scNodeEntry 309 }

    scNodeCntAoCimdLogoutNack OBJECT-TYPE
        SYNTAX  Counter
        ACCESS  read-only
        STATUS  mandatory
        DESCRIPTION
            "Counts the total number of negative CIMD logout responses
             which were received from the SC node."
        ::= { scNodeEntry 310 }

    scNodeAoCimdLogoutTimeSpent OBJECT-TYPE
        SYNTAX  HighResTime
        ACCESS  read-only
        STATUS  mandatory
        DESCRIPTION
            "Total time spent in processing CIMD logout requests."
        ::= { scNodeEntry 311 }

    scNodeAoCimdLogoutShortestRespTime OBJECT-TYPE
        SYNTAX  HighResTime
        ACCESS  read-only
        STATUS  mandatory
        DESCRIPTION
            "Shortest response time for processing a CIMD logout
             request."
        ::= { scNodeEntry 312 }

    scNodeAoCimdLogoutTimestampShortestResp OBJECT-TYPE
        SYNTAX  TimeStamp
        ACCESS  read-write
        STATUS  mandatory
        DESCRIPTION
            "Timestamp when shortest response time of a CIMD logout
             request occurred. The shortest response time can be reset
             by setting shortest response timestamp to zero."
        ::= { scNodeEntry 313 }

    scNodeAoCimdLogoutLongestRespTime OBJECT-TYPE
        SYNTAX  HighResTime
        ACCESS  read-only
        STATUS  mandatory
        DESCRIPTION
            "Longest response time for processing a CIMD logout
             request."
        ::= { scNodeEntry 314 }

    scNodeAoCimdLogoutTimestampLongestResp OBJECT-TYPE
        SYNTAX  TimeStamp
        ACCESS  read-write
        STATUS  mandatory
        DESCRIPTION
            "Timestamp when longest response time of a CIMD logout
             request occurred. The longest response time can be reset by
             setting the related  timestamp to zero."
        ::= { scNodeEntry 315 }

    scNodeCntAoCimdSubmitRequest OBJECT-TYPE
        SYNTAX  Counter
        ACCESS  read-only
        STATUS  mandatory
        DESCRIPTION
            "Counts the total number of CIMD submit sm requests which
             were sent to the SC node."
        ::= { scNodeEntry 316 }

    scNodeCntAoCimdSubmitAck OBJECT-TYPE
        SYNTAX  Counter
        ACCESS  read-only
        STATUS  mandatory
        DESCRIPTION
            "Counts the total number of positive CIMD submit sm
             responses which were received from the SC node."
        ::= { scNodeEntry 317 }

    scNodeCntAoCimdSubmitNack OBJECT-TYPE
        SYNTAX  Counter
        ACCESS  read-only
        STATUS  mandatory
        DESCRIPTION
            "Counts the total number of negative CIMD submit sm
             responses which were received from the SC node."
        ::= { scNodeEntry 318 }

    scNodeAoCimdSubmitTimeSpent OBJECT-TYPE
        SYNTAX  HighResTime
        ACCESS  read-only
        STATUS  mandatory
        DESCRIPTION
            "Total time spent in processing CIMD submit sm requests."
        ::= { scNodeEntry 319 }

    scNodeAoCimdSubmitShortestRespTime OBJECT-TYPE
        SYNTAX  HighResTime
        ACCESS  read-only
        STATUS  mandatory
        DESCRIPTION
            "Shortest response time for processing a CIMD submit sm
             request."
        ::= { scNodeEntry 320 }

    scNodeAoCimdSubmitTimestampShortestResp OBJECT-TYPE
        SYNTAX  TimeStamp
        ACCESS  read-write
        STATUS  mandatory
        DESCRIPTION
            "Timestamp when shortest response time of a CIMD submit sm
             request occurred. The shortest response time can be reset
             by setting shortest response timestamp to zero."
        ::= { scNodeEntry 321 }

    scNodeAoCimdSubmitLongestRespTime OBJECT-TYPE
        SYNTAX  HighResTime
        ACCESS  read-only
        STATUS  mandatory
        DESCRIPTION
            "Longest response time for processing a CIMD submit sm
             request."
        ::= { scNodeEntry 322 }

    scNodeAoCimdSubmitTimestampLongestResp OBJECT-TYPE
        SYNTAX  TimeStamp
        ACCESS  read-write
        STATUS  mandatory
        DESCRIPTION
            "Timestamp when longest response time of a CIMD submit sm
             request occurred. The longest response time can be reset by
             setting the related  timestamp to zero."
        ::= { scNodeEntry 323 }

    scNodeCntAoCimdEnquireRequest OBJECT-TYPE
        SYNTAX  Counter
        ACCESS  read-only
        STATUS  mandatory
        DESCRIPTION
            "Counts the total number of CIMD enquire message status
             requests which were sent to the SC node."
        ::= { scNodeEntry 324 }

    scNodeCntAoCimdEnquireAck OBJECT-TYPE
        SYNTAX  Counter
        ACCESS  read-only
        STATUS  mandatory
        DESCRIPTION
            "Counts the total number of positive CIMD enquire message
             status responses which were received from the SC node."
        ::= { scNodeEntry 325 }

    scNodeCntAoCimdEnquireNack OBJECT-TYPE
        SYNTAX  Counter
        ACCESS  read-only
        STATUS  mandatory
        DESCRIPTION
            "Counts the total number of negative CIMD enquire message
             status responses which were received from the SC node."
        ::= { scNodeEntry 326 }

    scNodeAoCimdEnquireTimeSpent OBJECT-TYPE
        SYNTAX  HighResTime
        ACCESS  read-only
        STATUS  mandatory
        DESCRIPTION
            "Total time spent in processing CIMD enquire message status
             requests."
        ::= { scNodeEntry 327 }

    scNodeAoCimdEnquireShortestRespTime OBJECT-TYPE
        SYNTAX  HighResTime
        ACCESS  read-only
        STATUS  mandatory
        DESCRIPTION
            "Shortest response time for processing a CIMD enquire
             message status request."
        ::= { scNodeEntry 328 }

    scNodeAoCimdEnquireTimestampShortestResp OBJECT-TYPE
        SYNTAX  TimeStamp
        ACCESS  read-write
        STATUS  mandatory
        DESCRIPTION
            "Timestamp when shortest response time of a CIMD enquire
             message status request occurred. The shortest response time
             can be reset by setting shortest response timestamp to
             zero."
        ::= { scNodeEntry 329 }

    scNodeAoCimdEnquireLongestRespTime OBJECT-TYPE
        SYNTAX  HighResTime
        ACCESS  read-only
        STATUS  mandatory
        DESCRIPTION
            "Longest response time for processing a CIMD enquire message
             status request."
        ::= { scNodeEntry 330 }

    scNodeAoCimdEnquireTimestampLongestResp OBJECT-TYPE
        SYNTAX  TimeStamp
        ACCESS  read-write
        STATUS  mandatory
        DESCRIPTION
            "Timestamp when longest response time of a CIMD enquire
             message status request occurred. The longest response time
             can be reset by setting the related  timestamp to zero."
        ::= { scNodeEntry 331 }

    scNodeCntAoCimdOtherRequest OBJECT-TYPE
        SYNTAX  Counter
        ACCESS  read-only
        STATUS  mandatory
        DESCRIPTION
            "Counts the total number of unknown CIMD requests which were
             sent to the SC node."
        ::= { scNodeEntry 332 }

    scNodeCntAoCimdOtherAck OBJECT-TYPE
        SYNTAX  Counter
        ACCESS  read-only
        STATUS  mandatory
        DESCRIPTION
            "Counts the total number of positive unknown CIMD responses
             which were received from the SC node."
        ::= { scNodeEntry 333 }

    scNodeCntAoCimdOtherNack OBJECT-TYPE
        SYNTAX  Counter
        ACCESS  read-only
        STATUS  mandatory
        DESCRIPTION
            "Counts the total number of negative unknown CIMD responses
             which were received from the SC node."
        ::= { scNodeEntry 334 }

    scNodeAoCimdOtherTimeSpent OBJECT-TYPE
        SYNTAX  HighResTime
        ACCESS  read-only
        STATUS  mandatory
        DESCRIPTION
            "Total time spent in processing unknown CIMD requests."
        ::= { scNodeEntry 335 }

    scNodeAoCimdOtherShortestRespTime OBJECT-TYPE
        SYNTAX  HighResTime
        ACCESS  read-only
        STATUS  mandatory
        DESCRIPTION
            "Shortest response time for processing an unknown CIMD
             requests."
        ::= { scNodeEntry 336 }

    scNodeAoCimdOtherTimestampShortestResp OBJECT-TYPE
        SYNTAX  TimeStamp
        ACCESS  read-write
        STATUS  mandatory
        DESCRIPTION
            "Timestamp when shortest response time of a unknown CIMD
             request occurred. The shortest response time can be reset
             by setting shortest response timestamp to zero."
        ::= { scNodeEntry 337 }

    scNodeAoCimdOtherLongestRespTime OBJECT-TYPE
        SYNTAX  HighResTime
        ACCESS  read-only
        STATUS  mandatory
        DESCRIPTION
            "Longest response time for processing an unknown CIMD
             requests."
        ::= { scNodeEntry 338 }

    scNodeAoCimdOtherTimestampLongestResp OBJECT-TYPE
        SYNTAX  TimeStamp
        ACCESS  read-write
        STATUS  mandatory
        DESCRIPTION
            "Timestamp when longest response time of an unknown CIMD
             request occurred. The longest response time can be reset by
             setting the related  timestamp to zero."
        ::= { scNodeEntry 339 }

    scNodeCntAtUcp52Request OBJECT-TYPE
        SYNTAX  Counter
        ACCESS  read-only
        STATUS  mandatory
        DESCRIPTION
            "Counts the total number of UCP deliver sm requests which
             were received from the SC node."
        ::= { scNodeEntry 400 }

    scNodeCntAtUcp52Ack OBJECT-TYPE
        SYNTAX  Counter
        ACCESS  read-only
        STATUS  mandatory
        DESCRIPTION
            "Counts the total number of positive UCP deliver sm
             responses which were sent to the SC node."
        ::= { scNodeEntry 401 }

    scNodeCntAtUcp52Nack OBJECT-TYPE
        SYNTAX  Counter
        ACCESS  read-only
        STATUS  mandatory
        DESCRIPTION
            "Counts the total number of negative UCP deliver sm
             responses which were sent to the SC node."
        ::= { scNodeEntry 402 }

    scNodeCntAtUcp53Request OBJECT-TYPE
        SYNTAX  Counter
        ACCESS  read-only
        STATUS  mandatory
        DESCRIPTION
            "Counts the total number of UCP deliver notify requests which
             were received from the SC node."
        ::= { scNodeEntry 403 }

    scNodeCntAtUcp53Ack OBJECT-TYPE
        SYNTAX  Counter
        ACCESS  read-only
        STATUS  mandatory
        DESCRIPTION
            "Counts the total number of positive UCP deliver notify
             responses which were sent to the SC node."
        ::= { scNodeEntry 404 }

    scNodeCntAtUcp53Nack OBJECT-TYPE
        SYNTAX  Counter
        ACCESS  read-only
        STATUS  mandatory
        DESCRIPTION
            "Counts the total number of negative UCP deliver notify
             responses which were sent to the SC node."
        ::= { scNodeEntry 405 }

    scNodeCntAtUcpOtherRequest OBJECT-TYPE
        SYNTAX  Counter
        ACCESS  read-only
        STATUS  mandatory
        DESCRIPTION
            "Counts the total number of unknown UCP requests which were
             received from the SC node."
        ::= { scNodeEntry 406 }

    scNodeCntAtUcpOtherAck OBJECT-TYPE
        SYNTAX  Counter
        ACCESS  read-only
        STATUS  mandatory
        DESCRIPTION
            "Counts the total number of positive unknown UCP responses
             which were sent to the SC node."
        ::= { scNodeEntry 407 }

    scNodeCntAtUcpOtherNack OBJECT-TYPE
        SYNTAX  Counter
        ACCESS  read-only
        STATUS  mandatory
        DESCRIPTION
            "Counts the total number of negative unknown UCP responses
             which were sent to the SC node."
        ::= { scNodeEntry 408 }

    scNodeCntAtUcp57Request OBJECT-TYPE
        SYNTAX  Counter
        ACCESS  read-only
        STATUS  mandatory
        DESCRIPTION
            "Counts the total number of UCP response inquiry message
             requests which were received from the SC node."
        ::= { scNodeEntry 409 }

    scNodeCntAtUcp57Ack OBJECT-TYPE
        SYNTAX  Counter
        ACCESS  read-only
        STATUS  mandatory
        DESCRIPTION
            "Counts the total number of positive UCP response inquiry
             message responses which were sent to the SC node."
        ::= { scNodeEntry 410 }

    scNodeCntAtUcp57Nack OBJECT-TYPE
        SYNTAX  Counter
        ACCESS  read-only
        STATUS  mandatory
        DESCRIPTION
            "Counts the total number of negative UCP response inquiry
             message responses which were sent to the SC node."
        ::= { scNodeEntry 411 }

    scNodeCntAtUcp58Request OBJECT-TYPE
        SYNTAX  Counter
        ACCESS  read-only
        STATUS  mandatory
        DESCRIPTION
            "Counts the total number of UCP response delete message
             requests which were received from the SC node."
        ::= { scNodeEntry 412 }

    scNodeCntAtUcp58Ack OBJECT-TYPE
        SYNTAX  Counter
        ACCESS  read-only
        STATUS  mandatory
        DESCRIPTION
            "Counts the total number of positive UCP response delete
             message responses which were sent to the SC node."
        ::= { scNodeEntry 413 }

    scNodeCntAtUcp58Nack OBJECT-TYPE
        SYNTAX  Counter
        ACCESS  read-only
        STATUS  mandatory
        DESCRIPTION
            "Counts the total number of negative UCP response delete
             message responses which were sent to the SC node."
        ::= { scNodeEntry 414 }

    scNodeCntAtSmppDeliverSmRequest OBJECT-TYPE
        SYNTAX  Counter
        ACCESS  read-only
        STATUS  mandatory
        DESCRIPTION
            "Counts the total number of SMPP deliver sm requests which
             were received from the SC node."
        ::= { scNodeEntry 420 }

    scNodeCntAtSmppDeliverSmAck OBJECT-TYPE
        SYNTAX  Counter
        ACCESS  read-only
        STATUS  mandatory
        DESCRIPTION
            "Counts the total number of positive SMPP deliver sm
             responses which were sent to the SC node."
        ::= { scNodeEntry 421 }

    scNodeCntAtSmppDeliverSmNack OBJECT-TYPE
        SYNTAX  Counter
        ACCESS  read-only
        STATUS  mandatory
        DESCRIPTION
            "Counts the total number of negative SMPP deliver sm
             responses which were sent to the SC node."
        ::= { scNodeEntry 422 }

    scNodeCntAtSmppDataSmRequest OBJECT-TYPE
        SYNTAX  Counter
        ACCESS  read-only
        STATUS  mandatory
        DESCRIPTION
            "Counts the total number of SMPP data sm requests which were
             received from the SC node."
        ::= { scNodeEntry 423 }

    scNodeCntAtSmppDataSmAck OBJECT-TYPE
        SYNTAX  Counter
        ACCESS  read-only
        STATUS  mandatory
        DESCRIPTION
            "Counts the total number of positive SMPP data sm responses
             which were sent to the SC node."
        ::= { scNodeEntry 424 }

    scNodeCntAtSmppDataSmNack OBJECT-TYPE
        SYNTAX  Counter
        ACCESS  read-only
        STATUS  mandatory
        DESCRIPTION
            "Counts the total number of negative SMPP data sm responses
             which were sent to the SC node."
        ::= { scNodeEntry 425 }

    scNodeCntAtSmppOtherRequest OBJECT-TYPE
        SYNTAX  Counter
        ACCESS  read-only
        STATUS  mandatory
        DESCRIPTION
            "Counts the total number of unknown SMPP requests which were
             received from the SC node."
        ::= { scNodeEntry 426 }

    scNodeCntAtSmppOtherAck OBJECT-TYPE
        SYNTAX  Counter
        ACCESS  read-only
        STATUS  mandatory
        DESCRIPTION
            "Counts the total number of positive unknown SMPP responses
             which were sent to the SC node."
        ::= { scNodeEntry 427 }

    scNodeCntAtSmppOtherNack OBJECT-TYPE
        SYNTAX  Counter
        ACCESS  read-only
        STATUS  mandatory
        DESCRIPTION
            "Counts the total number of negative unknown SMPP responses
             which were sent to the SC node."
        ::= { scNodeEntry 428 }

    scNodeCntAtCimdDeliverRequest OBJECT-TYPE
        SYNTAX  Counter
        ACCESS  read-only
        STATUS  mandatory
        DESCRIPTION
            "Counts the total number of CIMD deliver sm requests which
             were received from the SC node."
        ::= { scNodeEntry 440 }

    scNodeCntAtCimdDeliverAck OBJECT-TYPE
        SYNTAX  Counter
        ACCESS  read-only
        STATUS  mandatory
        DESCRIPTION
            "Counts the total number of positive CIMD deliver sm
             responses which were sent to the SC node."
        ::= { scNodeEntry 441 }

    scNodeCntAtCimdDeliverNack OBJECT-TYPE
        SYNTAX  Counter
        ACCESS  read-only
        STATUS  mandatory
        DESCRIPTION
            "Counts the total number of negative CIMD deliver sm
             responses which were sent to the SC node."
        ::= { scNodeEntry 442 }

    scNodeCntAtCimdDeliverStatusRequest OBJECT-TYPE
        SYNTAX  Counter
        ACCESS  read-only
        STATUS  mandatory
        DESCRIPTION
            "Counts the total number of CIMD deliver status requests
             which were received from the SC node."
        ::= { scNodeEntry 443 }

    scNodeCntAtCimdDeliverStatusAck OBJECT-TYPE
        SYNTAX  Counter
        ACCESS  read-only
        STATUS  mandatory
        DESCRIPTION
            "Counts the total number of positive CIMD deliver status
             responses which were sent to the SC node."
        ::= { scNodeEntry 444 }

    scNodeCntAtCimdDeliverStatusNack OBJECT-TYPE
        SYNTAX  Counter
        ACCESS  read-only
        STATUS  mandatory
        DESCRIPTION
            "Counts the total number of negative CIMD deliver status
             responses which were sent to the SC node."
        ::= { scNodeEntry 445 }

    scNodeCntAtCimdAliveRequest OBJECT-TYPE
        SYNTAX  Counter
        ACCESS  read-only
        STATUS  mandatory
        DESCRIPTION
            "Counts the total number of CIMD alive message requests which
             were received from the SC node."
        ::= { scNodeEntry 446 }

    scNodeCntAtCimdAliveAck OBJECT-TYPE
        SYNTAX  Counter
        ACCESS  read-only
        STATUS  mandatory
        DESCRIPTION
            "Counts the total number of positive CIMD alive message
             responses which were sent to the SC node."
        ::= { scNodeEntry 447 }

    scNodeCntAtCimdAliveNack OBJECT-TYPE
        SYNTAX  Counter
        ACCESS  read-only
        STATUS  mandatory
        DESCRIPTION
            "Counts the total number of negative CIMD alive message
             responses which were sent to the SC node."
        ::= { scNodeEntry 448 }

    scNodeCntAtCimdOtherRequest OBJECT-TYPE
        SYNTAX  Counter
        ACCESS  read-only
        STATUS  mandatory
        DESCRIPTION
            "Counts the total number of unknown CIMD requests which were
             received from the SC node."
        ::= { scNodeEntry 449 }

    scNodeCntAtCimdOtherAck OBJECT-TYPE
        SYNTAX  Counter
        ACCESS  read-only
        STATUS  mandatory
        DESCRIPTION
            "Counts the total number of positive unknown CIMD responses
             which were sent to the SC node."
        ::= { scNodeEntry 450 }

    scNodeCntAtCimdOtherNack OBJECT-TYPE
        SYNTAX  Counter
        ACCESS  read-only
        STATUS  mandatory
        DESCRIPTION
            "Counts the total number of negative unknown CIMD responses
             which were sent to the SC node."
        ::= { scNodeEntry 451 }



    -- the SC TerminationPoint Entity

    scTerminationPointTable OBJECT-TYPE
        SYNTAX  SEQUENCE OF ScTerminationPointEntry
        ACCESS  not-accessible
        STATUS  mandatory
        DESCRIPTION
            "A table containing properties for each SC Termination Point."
        ::= { apc 23 }

    scTerminationPointEntry OBJECT-TYPE
        SYNTAX  ScTerminationPointEntry
        ACCESS  not-accessible
        STATUS  mandatory
        DESCRIPTION
            "Table entry defining a single SC Termination Point."
        INDEX   { scTerminationPointIndex }
        ::= { scTerminationPointTable 1 }

    ScTerminationPointEntry ::=
        SEQUENCE {
            scTerminationPointIndex                     ScTerminationPointTableIndex,
            scTerminationPointAdminState                AdminState,
            scTerminationPointScNodeIndex               ScNodeTableIndex,
            scTerminationPointName                      NameString,
            scTerminationPointOperationalState          OperationalState,
            scTerminationPointProtocol                  ApplicationProtocol,
            scTerminationPointRemoteTcpPort             TcpPort,
            scTerminationPointServiceClassIndex         ServiceClassTableIndex,
            scTerminationPointThroughputAo              Throughput,
            scTerminationPointThroughputAt              Throughput,
            scTerminationPointMaxSessions               TerminationPointConnections,
            scTerminationPointMaxInactivityTime         ApplicationTimer,
            scTerminationPointMaxResponseTime           ApplicationTimer,
            scTerminationPointTcpKeepAlive              Boolean,
            scTerminationPointSessionsCounter           Gauge,
            scTerminationPointCntAoThroughputLimitHit   Counter,
            scTerminationPointCntInsideAtRejected       Counter,
            scTerminationPointCntInsideAoTotal          Counter,
            scTerminationPointCntInsideAoSuccess        Counter,
            scTerminationPointCntInsideAoSourceError    Counter,
            scTerminationPointCntInsideAoRoutingError   Counter,
            scTerminationPointCntInsideAoDestinationTemporaryError Counter,
            scTerminationPointCntInsideAoDestinationPermanentRecipientError Counter,
            scTerminationPointCntInsideAoDestinationPermanentMessageError Counter,
            scTerminationPointCntInsideAtTotal          Counter,
            scTerminationPointCntInsideAtSuccess        Counter,
            scTerminationPointCntInsideAtSourceError    Counter,
            scTerminationPointCntInsideAtRoutingError   Counter,
            scTerminationPointCntInsideAtDestinationTemporaryError Counter,
            scTerminationPointCntInsideAtDestinationPermanentRecipientError Counter,
            scTerminationPointCntInsideAtDestinationPermanentMessageError Counter,
            scTerminationPointCntAoUcp01Request            Counter,
            scTerminationPointCntAoUcp01Ack                Counter,
            scTerminationPointCntAoUcp01Nack               Counter,
            scTerminationPointAoUcp01TimeSpent             HighResTime,
            scTerminationPointAoUcp01ShortestRespTime      HighResTime,
            scTerminationPointAoUcp01TimestampShortestResp TimeStamp,
            scTerminationPointAoUcp01LongestRespTime       HighResTime,
            scTerminationPointAoUcp01TimestampLongestResp  TimeStamp,
            scTerminationPointCntAoUcp30Request            Counter,
            scTerminationPointCntAoUcp30Ack                Counter,
            scTerminationPointCntAoUcp30Nack               Counter,
            scTerminationPointAoUcp30TimeSpent             HighResTime,
            scTerminationPointAoUcp30ShortestRespTime      HighResTime,
            scTerminationPointAoUcp30TimestampShortestResp TimeStamp,
            scTerminationPointAoUcp30LongestRespTime       HighResTime,
            scTerminationPointAoUcp30TimestampLongestResp  TimeStamp,
            scTerminationPointCntAoUcp31Request            Counter,
            scTerminationPointCntAoUcp31Ack                Counter,
            scTerminationPointCntAoUcp31Nack               Counter,
            scTerminationPointAoUcp31TimeSpent             HighResTime,
            scTerminationPointAoUcp31ShortestRespTime      HighResTime,
            scTerminationPointAoUcp31TimestampShortestResp TimeStamp,
            scTerminationPointAoUcp31LongestRespTime       HighResTime,
            scTerminationPointAoUcp31TimestampLongestResp  TimeStamp,
            scTerminationPointCntAoUcp51Request            Counter,
            scTerminationPointCntAoUcp51Ack                Counter,
            scTerminationPointCntAoUcp51Nack               Counter,
            scTerminationPointAoUcp51TimeSpent             HighResTime,
            scTerminationPointAoUcp51ShortestRespTime      HighResTime,
            scTerminationPointAoUcp51TimestampShortestResp TimeStamp,
            scTerminationPointAoUcp51LongestRespTime       HighResTime,
            scTerminationPointAoUcp51TimestampLongestResp  TimeStamp,
            scTerminationPointCntAoUcp54Request            Counter,
            scTerminationPointCntAoUcp54Ack                Counter,
            scTerminationPointCntAoUcp54Nack               Counter,
            scTerminationPointAoUcp54TimeSpent             HighResTime,
            scTerminationPointAoUcp54ShortestRespTime      HighResTime,
            scTerminationPointAoUcp54TimestampShortestResp TimeStamp,
            scTerminationPointAoUcp54LongestRespTime       HighResTime,
            scTerminationPointAoUcp54TimestampLongestResp  TimeStamp,
            scTerminationPointCntAoUcp60Request            Counter,
            scTerminationPointCntAoUcp60Ack                Counter,
            scTerminationPointCntAoUcp60Nack               Counter,
            scTerminationPointAoUcp60TimeSpent             HighResTime,
            scTerminationPointAoUcp60ShortestRespTime      HighResTime,
            scTerminationPointAoUcp60TimestampShortestResp TimeStamp,
            scTerminationPointAoUcp60LongestRespTime       HighResTime,
            scTerminationPointAoUcp60TimestampLongestResp  TimeStamp,
            scTerminationPointCntAoUcpOtherRequest         Counter,
            scTerminationPointCntAoUcpOtherAck             Counter,
            scTerminationPointCntAoUcpOtherNack            Counter,
            scTerminationPointAoUcpOtherTimeSpent          HighResTime,
            scTerminationPointAoUcpOtherShortestRespTime   HighResTime,
            scTerminationPointAoUcpOtherTimestampShortestResp   TimeStamp,
            scTerminationPointAoUcpOtherLongestRespTime    HighResTime,
            scTerminationPointAoUcpOtherTimestampLongestResp    TimeStamp,
            scTerminationPointCntAoUcp55Request            Counter,
            scTerminationPointCntAoUcp55Ack                Counter,
            scTerminationPointCntAoUcp55Nack               Counter,
            scTerminationPointAoUcp55TimeSpent             HighResTime,
            scTerminationPointAoUcp55ShortestRespTime      HighResTime,
            scTerminationPointAoUcp55TimestampShortestResp TimeStamp,
            scTerminationPointAoUcp55LongestRespTime       HighResTime,
            scTerminationPointAoUcp55TimestampLongestResp  TimeStamp,
            scTerminationPointCntAoUcp56Request            Counter,
            scTerminationPointCntAoUcp56Ack                Counter,
            scTerminationPointCntAoUcp56Nack               Counter,
            scTerminationPointAoUcp56TimeSpent             HighResTime,
            scTerminationPointAoUcp56ShortestRespTime      HighResTime,
            scTerminationPointAoUcp56TimestampShortestResp TimeStamp,
            scTerminationPointAoUcp56LongestRespTime       HighResTime,
            scTerminationPointAoUcp56TimestampLongestResp  TimeStamp,
            scTerminationPointCntAoSmppSubmitSmRequest     Counter,
            scTerminationPointCntAoSmppSubmitSmAck         Counter,
            scTerminationPointCntAoSmppSubmitSmNack        Counter,
            scTerminationPointAoSmppSubmitSmTimeSpent      HighResTime,
            scTerminationPointAoSmppSubmitSmShortestRespTime        HighResTime,
            scTerminationPointAoSmppSubmitSmTimestampShortestResp   TimeStamp,
            scTerminationPointAoSmppSubmitSmLongestRespTime         HighResTime,
            scTerminationPointAoSmppSubmitSmTimestampLongestResp    TimeStamp,
            scTerminationPointCntAoSmppDataSmRequest       Counter,
            scTerminationPointCntAoSmppDataSmAck           Counter,
            scTerminationPointCntAoSmppDataSmNack          Counter,
            scTerminationPointAoSmppDataSmTimeSpent        HighResTime,
            scTerminationPointAoSmppDataSmShortestRespTime HighResTime,
            scTerminationPointAoSmppDataSmTimestampShortestResp TimeStamp,
            scTerminationPointAoSmppDataSmLongestRespTime       HighResTime,
            scTerminationPointAoSmppDataSmTimestampLongestResp  TimeStamp,
            scTerminationPointCntAoSmppBindRxRequest       Counter,
            scTerminationPointCntAoSmppBindRxAck           Counter,
            scTerminationPointCntAoSmppBindRxNack          Counter,
            scTerminationPointAoSmppBindRxTimeSpent        HighResTime,
            scTerminationPointAoSmppBindRxShortestRespTime      HighResTime,
            scTerminationPointAoSmppBindRxTimestampShortestResp TimeStamp,
            scTerminationPointAoSmppBindRxLongestRespTime       HighResTime,
            scTerminationPointAoSmppBindRxTimestampLongestResp  TimeStamp,
            scTerminationPointCntAoSmppBindTxRequest       Counter,
            scTerminationPointCntAoSmppBindTxAck           Counter,
            scTerminationPointCntAoSmppBindTxNack          Counter,
            scTerminationPointAoSmppBindTxTimeSpent        HighResTime,
            scTerminationPointAoSmppBindTxShortestRespTime      HighResTime,
            scTerminationPointAoSmppBindTxTimestampShortestResp TimeStamp,
            scTerminationPointAoSmppBindTxLongestRespTime       HighResTime,
            scTerminationPointAoSmppBindTxTimestampLongestResp  TimeStamp,
            scTerminationPointCntAoSmppBindTrxRequest      Counter,
            scTerminationPointCntAoSmppBindTrxAck          Counter,
            scTerminationPointCntAoSmppBindTrxNack         Counter,
            scTerminationPointAoSmppBindTrxTimeSpent       HighResTime,
            scTerminationPointAoSmppBindTrxShortestRespTime      HighResTime,
            scTerminationPointAoSmppBindTrxTimestampShortestResp TimeStamp,
            scTerminationPointAoSmppBindTrxLongestRespTime       HighResTime,
            scTerminationPointAoSmppBindTrxTimestampLongestResp  TimeStamp,
            scTerminationPointCntAoSmppUnbindRequest       Counter,
            scTerminationPointCntAoSmppUnbindAck           Counter,
            scTerminationPointCntAoSmppUnbindNack          Counter,
            scTerminationPointAoSmppUnbindTimeSpent        HighResTime,
            scTerminationPointAoSmppUnbindShortestRespTime      HighResTime,
            scTerminationPointAoSmppUnbindTimestampShortestResp TimeStamp,
            scTerminationPointAoSmppUnbindLongestRespTime       HighResTime,
            scTerminationPointAoSmppUnbindTimestampLongestResp  TimeStamp,
            scTerminationPointCntAoSmppQuerySmRequest      Counter,
            scTerminationPointCntAoSmppQuerySmAck          Counter,
            scTerminationPointCntAoSmppQuerySmNack         Counter,
            scTerminationPointAoSmppQuerySmTimeSpent       HighResTime,
            scTerminationPointAoSmppQuerySmShortestRespTime         HighResTime,
            scTerminationPointAoSmppQuerySmTimestampShortestResp    TimeStamp,
            scTerminationPointAoSmppQuerySmLongestRespTime          HighResTime,
            scTerminationPointAoSmppQuerySmTimestampLongestResp     TimeStamp,
            scTerminationPointCntAoSmppReplaceSmRequest    Counter,
            scTerminationPointCntAoSmppReplaceSmAck        Counter,
            scTerminationPointCntAoSmppReplaceSmNack       Counter,
            scTerminationPointAoSmppReplaceSmTimeSpent              HighResTime,
            scTerminationPointAoSmppReplaceSmShortestRespTime       HighResTime,
            scTerminationPointAoSmppReplaceSmTimestampShortestResp  TimeStamp,
            scTerminationPointAoSmppReplaceSmLongestRespTime        HighResTime,
            scTerminationPointAoSmppReplaceSmTimestampLongestResp   TimeStamp,
            scTerminationPointCntAoSmppCancelSmRequest     Counter,
            scTerminationPointCntAoSmppCancelSmAck         Counter,
            scTerminationPointCntAoSmppCancelSmNack        Counter,
            scTerminationPointAoSmppCancelSmTimeSpent      HighResTime,
            scTerminationPointAoSmppCancelSmShortestRespTime        HighResTime,
            scTerminationPointAoSmppCancelSmTimestampShortestResp   TimeStamp,
            scTerminationPointAoSmppCancelSmLongestRespTime         HighResTime,
            scTerminationPointAoSmppCancelSmTimestampLongestResp    TimeStamp,
            scTerminationPointCntAoSmppEnquireLinkRequest  Counter,
            scTerminationPointCntAoSmppEnquireLinkAck      Counter,
            scTerminationPointCntAoSmppEnquireLinkNack     Counter,
            scTerminationPointAoSmppEnquireLinkTimeSpent   HighResTime,
            scTerminationPointAoSmppEnquireLinkShortestRespTime      HighResTime,
            scTerminationPointAoSmppEnquireLinkTimestampShortestResp TimeStamp,
            scTerminationPointAoSmppEnquireLinkLongestRespTime       HighResTime,
            scTerminationPointAoSmppEnquireLinkTimestampLongestResp  TimeStamp,
            scTerminationPointCntAoSmppOtherRequest        Counter,
            scTerminationPointCntAoSmppOtherAck            Counter,
            scTerminationPointCntAoSmppOtherNack           Counter,
            scTerminationPointAoSmppOtherTimeSpent         HighResTime,
            scTerminationPointAoSmppOtherShortestRespTime       HighResTime,
            scTerminationPointAoSmppOtherTimestampShortestResp  TimeStamp,
            scTerminationPointAoSmppOtherLongestRespTime        HighResTime,
            scTerminationPointAoSmppOtherTimestampLongestResp   TimeStamp,
            scTerminationPointAoSmppGenericNack            Counter,
            scTerminationPointCntAoCimdLoginRequest        Counter,
            scTerminationPointCntAoCimdLoginAck            Counter,
            scTerminationPointCntAoCimdLoginNack           Counter,
            scTerminationPointAoCimdLoginTimeSpent         HighResTime,
            scTerminationPointAoCimdLoginShortestRespTime       HighResTime,
            scTerminationPointAoCimdLoginTimestampShortestResp  TimeStamp,
            scTerminationPointAoCimdLoginLongestRespTime        HighResTime,
            scTerminationPointAoCimdLoginTimestampLongestResp   TimeStamp,
            scTerminationPointCntAoCimdLogoutRequest       Counter,
            scTerminationPointCntAoCimdLogoutAck           Counter,
            scTerminationPointCntAoCimdLogoutNack          Counter,
            scTerminationPointAoCimdLogoutTimeSpent        HighResTime,
            scTerminationPointAoCimdLogoutShortestRespTime      HighResTime,
            scTerminationPointAoCimdLogoutTimestampShortestResp TimeStamp,
            scTerminationPointAoCimdLogoutLongestRespTime       HighResTime,
            scTerminationPointAoCimdLogoutTimestampLongestResp  TimeStamp,
            scTerminationPointCntAoCimdSubmitRequest       Counter,
            scTerminationPointCntAoCimdSubmitAck           Counter,
            scTerminationPointCntAoCimdSubmitNack          Counter,
            scTerminationPointAoCimdSubmitTimeSpent        HighResTime,
            scTerminationPointAoCimdSubmitShortestRespTime      HighResTime,
            scTerminationPointAoCimdSubmitTimestampShortestResp TimeStamp,
            scTerminationPointAoCimdSubmitLongestRespTime       HighResTime,
            scTerminationPointAoCimdSubmitTimestampLongestResp  TimeStamp,
            scTerminationPointCntAoCimdEnquireRequest      Counter,
            scTerminationPointCntAoCimdEnquireAck          Counter,
            scTerminationPointCntAoCimdEnquireNack         Counter,
            scTerminationPointAoCimdEnquireTimeSpent       HighResTime,
            scTerminationPointAoCimdEnquireShortestRespTime      HighResTime,
            scTerminationPointAoCimdEnquireTimestampShortestResp TimeStamp,
            scTerminationPointAoCimdEnquireLongestRespTime       HighResTime,
            scTerminationPointAoCimdEnquireTimestampLongestResp  TimeStamp,
            scTerminationPointCntAoCimdOtherRequest        Counter,
            scTerminationPointCntAoCimdOtherAck            Counter,
            scTerminationPointCntAoCimdOtherNack           Counter,
            scTerminationPointAoCimdOtherTimeSpent         HighResTime,
            scTerminationPointAoCimdOtherShortestRespTime           HighResTime,
            scTerminationPointAoCimdOtherTimestampShortestResp      TimeStamp,
            scTerminationPointAoCimdOtherLongestRespTime            HighResTime,
            scTerminationPointAoCimdOtherTimestampLongestResp       TimeStamp,
            scTerminationPointCntAtUcp52Request            Counter,
            scTerminationPointCntAtUcp52Ack                Counter,
            scTerminationPointCntAtUcp52Nack               Counter,
            scTerminationPointCntAtUcp53Request            Counter,
            scTerminationPointCntAtUcp53Ack                Counter,
            scTerminationPointCntAtUcp53Nack               Counter,
            scTerminationPointCntAtUcpOtherRequest         Counter,
            scTerminationPointCntAtUcpOtherAck             Counter,
            scTerminationPointCntAtUcpOtherNack            Counter,
            scTerminationPointCntAtUcp57Request            Counter,
            scTerminationPointCntAtUcp57Ack                Counter,
            scTerminationPointCntAtUcp57Nack               Counter,
            scTerminationPointCntAtUcp58Request            Counter,
            scTerminationPointCntAtUcp58Ack                Counter,
            scTerminationPointCntAtUcp58Nack               Counter,
            scTerminationPointCntAtSmppDeliverSmRequest    Counter,
            scTerminationPointCntAtSmppDeliverSmAck        Counter,
            scTerminationPointCntAtSmppDeliverSmNack       Counter,
            scTerminationPointCntAtSmppDataSmRequest       Counter,
            scTerminationPointCntAtSmppDataSmAck           Counter,
            scTerminationPointCntAtSmppDataSmNack          Counter,
            scTerminationPointCntAtSmppOtherRequest        Counter,
            scTerminationPointCntAtSmppOtherAck            Counter,
            scTerminationPointCntAtSmppOtherNack           Counter,
            scTerminationPointCntAtCimdDeliverRequest      Counter,
            scTerminationPointCntAtCimdDeliverAck          Counter,
            scTerminationPointCntAtCimdDeliverNack         Counter,
            scTerminationPointCntAtCimdDeliverStatusRequest      Counter,
            scTerminationPointCntAtCimdDeliverStatusAck    Counter,
            scTerminationPointCntAtCimdDeliverStatusNack   Counter,
            scTerminationPointCntAtCimdAliveRequest        Counter,
            scTerminationPointCntAtCimdAliveAck            Counter,
            scTerminationPointCntAtCimdAliveNack           Counter,
            scTerminationPointCntAtCimdOtherRequest        Counter,
            scTerminationPointCntAtCimdOtherAck            Counter,
            scTerminationPointCntAtCimdOtherNack           Counter
        }

    scTerminationPointIndex OBJECT-TYPE
        SYNTAX  ScTerminationPointTableIndex
        ACCESS  not-accessible
        STATUS  mandatory
        DESCRIPTION
            "Index of entry in sc Termination Point table."
        ::= { scTerminationPointEntry 1 }

    scTerminationPointAdminState OBJECT-TYPE
        SYNTAX  AdminState
        ACCESS  read-write
        STATUS  mandatory
        DESCRIPTION
            "Administrative state of the SC Termination Point.

            Transition from 'inactive' to 'active' is only possible when:
            1) name supplied and not already in use by another SC
               Termination Point;
            2) sc node index supplied and exists;
            3) sc node refers to an existing Service Centre;
            4) Service Class index supplied and exists;
            5) TCP port supplied;
            6) protocol type is UCP, SMPP or CIMD;

            Transition from 'active' to 'inactive' is always possible but will
            result in a graceful shutdown of all inside sessions towards this
            Termination Point.

            Transition to 'destroy' is always possible.

            For details, refer to the comment on the AdminState type."
        ::= { scTerminationPointEntry 2 }


    scTerminationPointScNodeIndex OBJECT-TYPE
        SYNTAX  ScNodeTableIndex
        ACCESS  read-write
        STATUS  mandatory
        DESCRIPTION
            "Index referring to an entry in the sc node table."
        ::= { scTerminationPointEntry 3 }

    scTerminationPointName OBJECT-TYPE
        SYNTAX  NameString
        ACCESS  read-write
        STATUS  mandatory
        DESCRIPTION
            "The name of the sc Termination Point entity."
        ::= { scTerminationPointEntry 4 }

    scTerminationPointOperationalState OBJECT-TYPE
        SYNTAX  OperationalState
        ACCESS  read-only
        STATUS  mandatory
        DESCRIPTION
            "The operational state of the sc Termination Point entity."
        ::= { scTerminationPointEntry 5 }

    scTerminationPointProtocol OBJECT-TYPE
        SYNTAX  ApplicationProtocol
        ACCESS  read-write
        STATUS  mandatory
        DESCRIPTION
            "Interface protocol describing how TextPass interacts with the
            Termination Point.
            For details, refer to the comment on the ApplicationProtocol
            type."
        ::= { scTerminationPointEntry 6 }

    scTerminationPointRemoteTcpPort OBJECT-TYPE
        SYNTAX  TcpPort
        ACCESS  read-write
        STATUS  mandatory
        DESCRIPTION
            "The remote TCP/IP port where the Termination Point is listening
            on."
        ::= { scTerminationPointEntry 7 }

    scTerminationPointServiceClassIndex OBJECT-TYPE
        SYNTAX  ServiceClassTableIndex
        ACCESS  read-write
        STATUS  mandatory
        DESCRIPTION
            "Index referring to an entry in the Service Class table."
        ::= { scTerminationPointEntry 8 }

    scTerminationPointThroughputAo OBJECT-TYPE
        SYNTAX  Throughput
        ACCESS  read-write
        STATUS  mandatory
        DESCRIPTION
            "Maximum incoming throughput the SC Termination Point can handle
            from external entities like the TextPassHub in terms of SM's per
            second."
        ::= { scTerminationPointEntry 11 }

    scTerminationPointThroughputAt OBJECT-TYPE
        SYNTAX  Throughput
        ACCESS  read-write
        STATUS  mandatory
        DESCRIPTION
            "Maximum outgoing throughput the SC Termination Point can send
            towards external entities like the TextPassHub in terms of SM's
            per second."
        ::= { scTerminationPointEntry 12 }

    scTerminationPointMaxSessions OBJECT-TYPE
        SYNTAX  TerminationPointConnections
        ACCESS  read-write
        STATUS  mandatory
        DESCRIPTION
            "The maximum of sessions which may be setup towards this
            Termination Point."
        ::= { scTerminationPointEntry 13 }

    scTerminationPointMaxInactivityTime OBJECT-TYPE
        SYNTAX  ApplicationTimer
        ACCESS  read-write
        STATUS  mandatory
        DESCRIPTION
            "Maximum time span, expressed in seconds, that a link to a
            Termination Point is idle before TextPass disconnects it."
        ::= { scTerminationPointEntry 14 }

    scTerminationPointMaxResponseTime OBJECT-TYPE
        SYNTAX  ApplicationTimer
        ACCESS  read-write
        STATUS  mandatory
        DESCRIPTION
            "Maximum time span, expressed in seconds, that TextPass waits for
            a response from a Termination Point before it considers the
            relating request as timed out."
        ::= { scTerminationPointEntry 15 }

    scTerminationPointTcpKeepAlive OBJECT-TYPE
        SYNTAX  Boolean
        ACCESS  read-write
        STATUS  mandatory
        DESCRIPTION
            "Controls the TCP Keep-Alive functionality on connections towards 
            this scTerminationPoint. When enabled the functionality will be 
            activated for all connections started thereafter. For the inside 
            sessions and outside dial-out sessions the feature will be enabled 
            as soon as the connection is started. When disabled the feature 
            will be disabled on all newer connections.
            Default: FALSE."
        ::= { scTerminationPointEntry 16 }

    scTerminationPointSessionsCounter OBJECT-TYPE
        SYNTAX  Gauge
        ACCESS  read-only
        STATUS  mandatory
        DESCRIPTION
            "Number of total sessions currently established towards the
            SC Termination Point."
        ::= { scTerminationPointEntry 21 }

    scTerminationPointCntAoThroughputLimitHit OBJECT-TYPE
        SYNTAX  Counter
        ACCESS  read-write
        STATUS  mandatory
        DESCRIPTION
            "Counter specifying the number of times that the AO throughput
            limit as set for the SC Termination Point has been hit."
        ::= { scTerminationPointEntry 22 }

    scTerminationPointCntInsideAtRejected OBJECT-TYPE
        SYNTAX  Counter
        ACCESS  read-write
        STATUS  mandatory
        DESCRIPTION
            "Counter specifying the number of times an AT/SM was
            rejected from a Service Centre."
        ::= { scTerminationPointEntry 23 }

    scTerminationPointCntInsideAoTotal OBJECT-TYPE
        SYNTAX  Counter
        ACCESS  read-write
        STATUS  mandatory
        DESCRIPTION
            "Counter specifying the total number of times an AO/SM was
            sent towards a Service Centre."
        ::= { scTerminationPointEntry 111 }

    scTerminationPointCntInsideAoSuccess OBJECT-TYPE
        SYNTAX  Counter
        ACCESS  read-write
        STATUS  mandatory
        DESCRIPTION
            "Counter specifying the number of times an AO/SM was
            successfully routed to its destination."

        ::= { scTerminationPointEntry 112 }

    scTerminationPointCntInsideAoSourceError OBJECT-TYPE
        SYNTAX  Counter
        ACCESS  read-write
        STATUS  mandatory
        DESCRIPTION
            "Counter specifying the number of times an AO/SM towards
             a Service Centre resulted in a source error
             (like a syntax error). The error mapping
             table is used to identify a source error. With a correct
             error mapping table it is not possible that this counter
             increases."
        ::= { scTerminationPointEntry 113 }

    scTerminationPointCntInsideAoRoutingError OBJECT-TYPE
        SYNTAX  Counter
        ACCESS  read-write
        STATUS  mandatory
        DESCRIPTION
            "Counter specifying the number of times an AO/SM towards
            a Service Centre resulted in a routing error. The error
            mapping table is used to identify a routing error."
        ::= { scTerminationPointEntry 114 }

    scTerminationPointCntInsideAoDestinationTemporaryError OBJECT-TYPE
        SYNTAX  Counter
        ACCESS  read-write
        STATUS  mandatory
        DESCRIPTION
            "Counter specifying the number of times an AO/SM towards
            a Service Centre resulted in a temporary error. The error
            mapping table is used to identify a temporary error."
        ::= { scTerminationPointEntry 115 }

    scTerminationPointCntInsideAoDestinationPermanentRecipientError OBJECT-TYPE
        SYNTAX  Counter
        ACCESS  read-write
        STATUS  mandatory
        DESCRIPTION
            "Counter specifying the number of times an AO/SM towards
            a Service Centre resulted in a permanent recipient error. 
            The error mapping table is used to identify a permanent 
            recipient error."
        ::= { scTerminationPointEntry 116 }

    scTerminationPointCntInsideAoDestinationPermanentMessageError OBJECT-TYPE
        SYNTAX  Counter
        ACCESS  read-write
        STATUS  mandatory
        DESCRIPTION
            "Counter specifying the number of times an AO/SM towards
            a Service Centre resulted in a permanent message error. The 
            error mapping table is used to identify a permanent message 
            error."
        ::= { scTerminationPointEntry 117 }

    scTerminationPointCntInsideAtTotal OBJECT-TYPE
        SYNTAX  Counter
        ACCESS  read-write
        STATUS  mandatory
        DESCRIPTION
            "Counter specifying the total number of times an AT/SM was
            received from a Service Centre."
        ::= { scTerminationPointEntry 118 }

    scTerminationPointCntInsideAtSuccess OBJECT-TYPE
        SYNTAX  Counter
        ACCESS  read-write
        STATUS  mandatory
        DESCRIPTION
            "Counter specifying the number of times an AT/SM was
            successfully routed to its destination."
        ::= { scTerminationPointEntry 119 }

    scTerminationPointCntInsideAtSourceError OBJECT-TYPE
        SYNTAX  Counter
        ACCESS  read-write
        STATUS  mandatory
        DESCRIPTION
            "Counter specifying the number of times an AT/SM from
             a Service Centre resulted in a source error
             (like a syntax error). The error mapping
             table is used to identify a source error."
        ::= { scTerminationPointEntry 120 }

    scTerminationPointCntInsideAtRoutingError OBJECT-TYPE
        SYNTAX  Counter
        ACCESS  read-write
        STATUS  mandatory
        DESCRIPTION
            "Counter specifying the number of times an AT/SM from
            a Service Centre resulted in a routing error. The error
            mapping table is used to identify a routing error."
        ::= { scTerminationPointEntry 121 }

    scTerminationPointCntInsideAtDestinationTemporaryError OBJECT-TYPE
        SYNTAX  Counter
        ACCESS  read-write
        STATUS  mandatory
        DESCRIPTION
            "Counter specifying the number of times an AT/SM from
            a Service Centre resulted in a temporary error. The error
            mapping table is used to identify a temporary error."
        ::= { scTerminationPointEntry 122 }

    scTerminationPointCntInsideAtDestinationPermanentRecipientError OBJECT-TYPE
        SYNTAX  Counter
        ACCESS  read-write
        STATUS  mandatory
        DESCRIPTION
            "Counter specifying the number of times an AT/SM from
            a Service Centre resulted in a permanent recipient error. 
            The error mapping table is used to identify a permanent 
            recipient error."
        ::= { scTerminationPointEntry 123 }

    scTerminationPointCntInsideAtDestinationPermanentMessageError OBJECT-TYPE
        SYNTAX  Counter
        ACCESS  read-write
        STATUS  mandatory
        DESCRIPTION
            "Counter specifying the number of times an AT/SM from
            a Service Centre resulted in a permanent message error. The 
            error mapping table is used to identify a permanent message 
            error."
        ::= { scTerminationPointEntry 124 }

    scTerminationPointCntAoUcp01Request OBJECT-TYPE
        SYNTAX  Counter
        ACCESS  read-only
        STATUS  mandatory
        DESCRIPTION
            "Counts the total number of UCP call input request which
             were sent to the SC termination point."
        ::= { scTerminationPointEntry 170 }

    scTerminationPointCntAoUcp01Ack OBJECT-TYPE
        SYNTAX  Counter
        ACCESS  read-only
        STATUS  mandatory
        DESCRIPTION
            "Counts the total number of positive UCP UCP call responses
             which were received from the SC termination point."
        ::= { scTerminationPointEntry 171 }

    scTerminationPointCntAoUcp01Nack OBJECT-TYPE
        SYNTAX  Counter
        ACCESS  read-only
        STATUS  mandatory
        DESCRIPTION
            "Counts the total number of negative UCP UCP call responses
             which were received from the SC termination point."
        ::= { scTerminationPointEntry 172 }

    scTerminationPointAoUcp01TimeSpent OBJECT-TYPE
        SYNTAX  HighResTime
        ACCESS  read-only
        STATUS  mandatory
        DESCRIPTION
            "Total time spent in processing UCP UCP call requests."
        ::= { scTerminationPointEntry 173 }

    scTerminationPointAoUcp01ShortestRespTime OBJECT-TYPE
        SYNTAX  HighResTime
        ACCESS  read-only
        STATUS  mandatory
        DESCRIPTION
            "Shortest response time for processing a UCP UCP call
             requests."
        ::= { scTerminationPointEntry 174 }

    scTerminationPointAoUcp01TimestampShortestResp OBJECT-TYPE
        SYNTAX  TimeStamp
        ACCESS  read-write
        STATUS  mandatory
        DESCRIPTION
            "Time stamp when shortest response time of a UCP UCP call
             request occurred. The shortest response time can be reset
             by setting shortest response time stamp to zero."
        ::= { scTerminationPointEntry 175 }

    scTerminationPointAoUcp01LongestRespTime OBJECT-TYPE
        SYNTAX  HighResTime
        ACCESS  read-only
        STATUS  mandatory
        DESCRIPTION
            "Longest response time for processing a UCP UCP call
             requests."
        ::= { scTerminationPointEntry 176 }

    scTerminationPointAoUcp01TimestampLongestResp OBJECT-TYPE
        SYNTAX  TimeStamp
        ACCESS  read-write
        STATUS  mandatory
        DESCRIPTION
            "Time stamp when longest response time of a UCP UCP call
             request occurred. The longest response time can be reset by
             setting longtest response time stamp to zero."
        ::= { scTerminationPointEntry 177 }

    scTerminationPointCntAoUcp30Request OBJECT-TYPE
        SYNTAX  Counter
        ACCESS  read-only
        STATUS  mandatory
        DESCRIPTION
            "Counts the total number of UCP submit message transfer which
             were sent to the SC Termination Point."
        ::= { scTerminationPointEntry 190 }

    scTerminationPointCntAoUcp30Ack OBJECT-TYPE
        SYNTAX  Counter
        ACCESS  read-only
        STATUS  mandatory
        DESCRIPTION
            "Counts the total number of positive UCP message transfer 
             responses which were received from the SC Termination Point."
        ::= { scTerminationPointEntry 191 }

    scTerminationPointCntAoUcp30Nack OBJECT-TYPE
        SYNTAX  Counter
        ACCESS  read-only
        STATUS  mandatory
        DESCRIPTION
            "Counts the total number of negative UCP message transfer 
             responses which were received from the SC Termination Point."
        ::= { scTerminationPointEntry 192 }

    scTerminationPointAoUcp30TimeSpent OBJECT-TYPE
        SYNTAX  HighResTime
        ACCESS  read-only
        STATUS  mandatory
        DESCRIPTION
            "Total time spent in processing UCP message transfer requests."
        ::= { scTerminationPointEntry 193 }

    scTerminationPointAoUcp30ShortestRespTime OBJECT-TYPE
        SYNTAX  HighResTime
        ACCESS  read-only
        STATUS  mandatory
        DESCRIPTION
            "Shortest response time for processing a UCP message transfer
             request."
        ::= { scTerminationPointEntry 194 }

    scTerminationPointAoUcp30TimestampShortestResp OBJECT-TYPE
        SYNTAX  TimeStamp
        ACCESS  read-write
        STATUS  mandatory
        DESCRIPTION
            "Timestamp when shortest response time of a UCP message transfer
             request occurred. The shortest response time can be reset
             by setting shortest response timestamp to zero."
        ::= { scTerminationPointEntry 195 }

    scTerminationPointAoUcp30LongestRespTime OBJECT-TYPE
        SYNTAX  HighResTime
        ACCESS  read-only
        STATUS  mandatory
        DESCRIPTION
            "Longest response time for processing a UCP message transfer
             request."
        ::= { scTerminationPointEntry 196 }

    scTerminationPointAoUcp30TimestampLongestResp OBJECT-TYPE
        SYNTAX  TimeStamp
        ACCESS  read-write
        STATUS  mandatory
        DESCRIPTION
            "Timestamp when longest response time of a UCP message transfer
             request occurred. The longest response time can be reset by
             setting longest response timestamp to zero."
        ::= { scTerminationPointEntry 197 }


    scTerminationPointCntAoUcp31Request OBJECT-TYPE
        SYNTAX  Counter
        ACCESS  read-only
        STATUS  mandatory
        DESCRIPTION
            "Counts the total number of UCP alert requests which were
             sent to the SC Termination Point."
        ::= { scTerminationPointEntry 200 }

    scTerminationPointCntAoUcp31Ack OBJECT-TYPE
        SYNTAX  Counter
        ACCESS  read-only
        STATUS  mandatory
        DESCRIPTION
            "Counts the total number of positive UCP alert responses
             which were received from the SC Termination Point."
        ::= { scTerminationPointEntry 201 }

    scTerminationPointCntAoUcp31Nack OBJECT-TYPE
        SYNTAX  Counter
        ACCESS  read-only
        STATUS  mandatory
        DESCRIPTION
            "Counts the total number of negative UCP alert responses
             which were received from the SC Termination Point."
        ::= { scTerminationPointEntry 202 }

    scTerminationPointAoUcp31TimeSpent OBJECT-TYPE
        SYNTAX  HighResTime
        ACCESS  read-only
        STATUS  mandatory
        DESCRIPTION
            "Total time spent in processing UCP alert requests."
        ::= { scTerminationPointEntry 203 }

    scTerminationPointAoUcp31ShortestRespTime OBJECT-TYPE
        SYNTAX  HighResTime
        ACCESS  read-only
        STATUS  mandatory
        DESCRIPTION
            "Shortest response time for processing a UCP alert
             request."
        ::= { scTerminationPointEntry 204 }

    scTerminationPointAoUcp31TimestampShortestResp OBJECT-TYPE
        SYNTAX  TimeStamp
        ACCESS  read-write
        STATUS  mandatory
        DESCRIPTION
            "Timestamp when shortest response time of a UCP alert
             request occurred. The shortest response time can be reset
             by setting shortest response timestamp to zero."
        ::= { scTerminationPointEntry 205 }

    scTerminationPointAoUcp31LongestRespTime OBJECT-TYPE
        SYNTAX  HighResTime
        ACCESS  read-only
        STATUS  mandatory
        DESCRIPTION
            "Longest response time for processing a UCP alert request."
        ::= { scTerminationPointEntry 206 }

    scTerminationPointAoUcp31TimestampLongestResp OBJECT-TYPE
        SYNTAX  TimeStamp
        ACCESS  read-write
        STATUS  mandatory
        DESCRIPTION
            "Timestamp when longest response time of a UCP alert
             request occurred. The longest response time can be reset by
             setting longest response timestamp to zero."
        ::= { scTerminationPointEntry 207 }

    scTerminationPointCntAoUcp51Request OBJECT-TYPE
        SYNTAX  Counter
        ACCESS  read-only
        STATUS  mandatory
        DESCRIPTION
            "Counts the total number of UCP submit sm requests which were
             sent to the SC Termination Point."
        ::= { scTerminationPointEntry 208 }

    scTerminationPointCntAoUcp51Ack OBJECT-TYPE
        SYNTAX  Counter
        ACCESS  read-only
        STATUS  mandatory
        DESCRIPTION
            "Counts the total number of positive UCP submit sm responses
             which were received from the SC Termination Point."
        ::= { scTerminationPointEntry 209 }

    scTerminationPointCntAoUcp51Nack OBJECT-TYPE
        SYNTAX  Counter
        ACCESS  read-only
        STATUS  mandatory
        DESCRIPTION
            "Counts the total number of negative UCP submit sm responses
             which were received from the SC Termination Point."
        ::= { scTerminationPointEntry 210 }

    scTerminationPointAoUcp51TimeSpent OBJECT-TYPE
        SYNTAX  HighResTime
        ACCESS  read-only
        STATUS  mandatory
        DESCRIPTION
            "Total time spent in processing UCP submit sm requests."
        ::= { scTerminationPointEntry 211 }

    scTerminationPointAoUcp51ShortestRespTime OBJECT-TYPE
        SYNTAX  HighResTime
        ACCESS  read-only
        STATUS  mandatory
        DESCRIPTION
            "Shortest response time for processing a UCP submit sm
             request."
        ::= { scTerminationPointEntry 212 }

    scTerminationPointAoUcp51TimestampShortestResp OBJECT-TYPE
        SYNTAX  TimeStamp
        ACCESS  read-write
        STATUS  mandatory
        DESCRIPTION
            "Timestamp when shortest response time of a UCP submit sm
             request occurred. The shortest response time can be reset
             by setting shortest response timestamp to zero."
        ::= { scTerminationPointEntry 213 }

    scTerminationPointAoUcp51LongestRespTime OBJECT-TYPE
        SYNTAX  HighResTime
        ACCESS  read-only
        STATUS  mandatory
        DESCRIPTION
            "Longest response time for processing a UCP submit sm
             request."
        ::= { scTerminationPointEntry 214 }

    scTerminationPointAoUcp51TimestampLongestResp OBJECT-TYPE
        SYNTAX  TimeStamp
        ACCESS  read-write
        STATUS  mandatory
        DESCRIPTION
            "Timestamp when longest response time of a UCP submit sm
             request occurred. The longest response time can be reset by
             setting longest response timestamp to zero."
        ::= { scTerminationPointEntry 215 }

    scTerminationPointCntAoUcp54Request OBJECT-TYPE
        SYNTAX  Counter
        ACCESS  read-only
        STATUS  mandatory
        DESCRIPTION
            "Counts the total number of UCP modify requests which were
             sent to the SC Termination Point."
        ::= { scTerminationPointEntry 216 }

    scTerminationPointCntAoUcp54Ack OBJECT-TYPE
        SYNTAX  Counter
        ACCESS  read-only
        STATUS  mandatory
        DESCRIPTION
            "Counts the total number of positive UCP modify responses
             which were received from the SC Termination Point."
        ::= { scTerminationPointEntry 217 }

    scTerminationPointCntAoUcp54Nack OBJECT-TYPE
        SYNTAX  Counter
        ACCESS  read-only
        STATUS  mandatory
        DESCRIPTION
            "Counts the total number of negative UCP modify responses
             which were received from the SC Termination Point."
        ::= { scTerminationPointEntry 218 }

    scTerminationPointAoUcp54TimeSpent OBJECT-TYPE
        SYNTAX  HighResTime
        ACCESS  read-only
        STATUS  mandatory
        DESCRIPTION
            "Total time spent in processing UCP modify requests."
        ::= { scTerminationPointEntry 219 }

    scTerminationPointAoUcp54ShortestRespTime OBJECT-TYPE
        SYNTAX  HighResTime
        ACCESS  read-only
        STATUS  mandatory
        DESCRIPTION
            "Shortest response time for processing a UCP modify
             request."
        ::= { scTerminationPointEntry 220 }

    scTerminationPointAoUcp54TimestampShortestResp OBJECT-TYPE
        SYNTAX  TimeStamp
        ACCESS  read-write
        STATUS  mandatory
        DESCRIPTION
            "Timestamp when shortest response time of a UCP modify
             request occurred. The shortest response time can be reset
             by setting shortest response timestamp to zero."
        ::= { scTerminationPointEntry 221 }

    scTerminationPointAoUcp54LongestRespTime OBJECT-TYPE
        SYNTAX  HighResTime
        ACCESS  read-only
        STATUS  mandatory
        DESCRIPTION
            "Longest response time for processing a UCP modify
             request."
        ::= { scTerminationPointEntry 222 }

    scTerminationPointAoUcp54TimestampLongestResp OBJECT-TYPE
        SYNTAX  TimeStamp
        ACCESS  read-write
        STATUS  mandatory
        DESCRIPTION
            "Timestamp when longest response time of a UCP modify
             request occurred. The longest response time can be reset by
             setting longest response timestamp to zero."
        ::= { scTerminationPointEntry 223 }

    scTerminationPointCntAoUcp60Request OBJECT-TYPE
        SYNTAX  Counter
        ACCESS  read-only
        STATUS  mandatory
        DESCRIPTION
            "Counts the total number of UCP session management requests
             which were sent to the SC Termination Point."
        ::= { scTerminationPointEntry 224 }

    scTerminationPointCntAoUcp60Ack OBJECT-TYPE
        SYNTAX  Counter
        ACCESS  read-only
        STATUS  mandatory
        DESCRIPTION
            "Counts the total number of positive UCP session management
             responses which were received from the SC Termination
             Point."
        ::= { scTerminationPointEntry 225 }

    scTerminationPointCntAoUcp60Nack OBJECT-TYPE
        SYNTAX  Counter
        ACCESS  read-only
        STATUS  mandatory
        DESCRIPTION
            "Counts the total number of negative UCP session management
             responses which were received from the SC Termination
             Point."
        ::= { scTerminationPointEntry 226 }

    scTerminationPointAoUcp60TimeSpent OBJECT-TYPE
        SYNTAX  HighResTime
        ACCESS  read-only
        STATUS  mandatory
        DESCRIPTION
            "Total time spent in processing UCP session management
             requests."
        ::= { scTerminationPointEntry 227 }

    scTerminationPointAoUcp60ShortestRespTime OBJECT-TYPE
        SYNTAX  HighResTime
        ACCESS  read-only
        STATUS  mandatory
        DESCRIPTION
            "Shortest response time for processing a UCP session
             management request."
        ::= { scTerminationPointEntry 228 }

    scTerminationPointAoUcp60TimestampShortestResp OBJECT-TYPE
        SYNTAX  TimeStamp
        ACCESS  read-write
        STATUS  mandatory
        DESCRIPTION
            "Timestamp when shortest response time of a UCP session
             management request occurred. The shortest response time can
             be reset by setting shortest response timestamp to zero."
        ::= { scTerminationPointEntry 229 }

    scTerminationPointAoUcp60LongestRespTime OBJECT-TYPE
        SYNTAX  HighResTime
        ACCESS  read-only
        STATUS  mandatory
        DESCRIPTION
            "Longest response time for processing a UCP session
             management request."
        ::= { scTerminationPointEntry 230 }

    scTerminationPointAoUcp60TimestampLongestResp OBJECT-TYPE
        SYNTAX  TimeStamp
        ACCESS  read-write
        STATUS  mandatory
        DESCRIPTION
            "Timestamp when longest response time of a UCP session
             management request occurred. The longest response time can
             be reset by setting longest response timestamp to zero."
        ::= { scTerminationPointEntry 231 }

    scTerminationPointCntAoUcpOtherRequest OBJECT-TYPE
        SYNTAX  Counter
        ACCESS  read-only
        STATUS  mandatory
        DESCRIPTION
            "Counts the total number of unknown UCP requests which were
             sent to the SC Termination Point."
        ::= { scTerminationPointEntry 232 }

    scTerminationPointCntAoUcpOtherAck OBJECT-TYPE
        SYNTAX  Counter
        ACCESS  read-only
        STATUS  mandatory
        DESCRIPTION
            "Counts the total number of positive unknown UCP responses
             which were received from the SC Termination Point."
        ::= { scTerminationPointEntry 233 }

    scTerminationPointCntAoUcpOtherNack OBJECT-TYPE
        SYNTAX  Counter
        ACCESS  read-only
        STATUS  mandatory
        DESCRIPTION
            "Counts the total number of negative unknown UCP responses
             which were received from the SC Termination Point."
        ::= { scTerminationPointEntry 234 }

    scTerminationPointAoUcpOtherTimeSpent OBJECT-TYPE
        SYNTAX  HighResTime
        ACCESS  read-only
        STATUS  mandatory
        DESCRIPTION
            "Total time spent in processing unknown UCP requests."
        ::= { scTerminationPointEntry 235 }

    scTerminationPointAoUcpOtherShortestRespTime OBJECT-TYPE
        SYNTAX  HighResTime
        ACCESS  read-only
        STATUS  mandatory
        DESCRIPTION
            "Shortest response time for processing an unknown UCP
             request."
        ::= { scTerminationPointEntry 236 }

    scTerminationPointAoUcpOtherTimestampShortestResp OBJECT-TYPE
        SYNTAX  TimeStamp
        ACCESS  read-write
        STATUS  mandatory
        DESCRIPTION
            "Timestamp when shortest response time of an unknown UCP
             request occurred. The shortest response time can be reset
             by setting shortest response timestamp to zero."
        ::= { scTerminationPointEntry 237 }

    scTerminationPointAoUcpOtherLongestRespTime OBJECT-TYPE
        SYNTAX  HighResTime
        ACCESS  read-only
        STATUS  mandatory
        DESCRIPTION
            "Longest response time for processing an unknown UCP
             request."
        ::= { scTerminationPointEntry 238 }

    scTerminationPointAoUcpOtherTimestampLongestResp OBJECT-TYPE
        SYNTAX  TimeStamp
        ACCESS  read-write
        STATUS  mandatory
        DESCRIPTION
            "Timestamp when longest response time of an unknown UCP
             request occurred. The longest response time can be reset by
             setting longest response timestamp to zero."
        ::= { scTerminationPointEntry 239 }

    scTerminationPointCntAoUcp55Request OBJECT-TYPE
        SYNTAX  Counter
        ACCESS  read-only
        STATUS  mandatory
        DESCRIPTION
            "Counts the total number of UCP inquiry message requests
             which were sent to the SC termination point."
        ::= { scTerminationPointEntry 240 }

    scTerminationPointCntAoUcp55Ack OBJECT-TYPE
        SYNTAX  Counter
        ACCESS  read-only
        STATUS  mandatory
        DESCRIPTION
            "Counts the total number of positive UCP inquiry message
             responses which were received from the SC termination
             point."
        ::= { scTerminationPointEntry 241 }

    scTerminationPointCntAoUcp55Nack OBJECT-TYPE
        SYNTAX  Counter
        ACCESS  read-only
        STATUS  mandatory
        DESCRIPTION
            "Counts the total number of negative UCP inquiry message
             responses which were received from the SC termination
             point."
        ::= { scTerminationPointEntry 242 }

    scTerminationPointAoUcp55TimeSpent OBJECT-TYPE
        SYNTAX  HighResTime
        ACCESS  read-only
        STATUS  mandatory
        DESCRIPTION
            "Total time spent in processing UCP inquiry message
             requests."
        ::= { scTerminationPointEntry 243 }

    scTerminationPointAoUcp55ShortestRespTime OBJECT-TYPE
        SYNTAX  HighResTime
        ACCESS  read-only
        STATUS  mandatory
        DESCRIPTION
            "Shortest response time for processing a UCP inquiry message
             request."
        ::= { scTerminationPointEntry 244 }

    scTerminationPointAoUcp55TimestampShortestResp OBJECT-TYPE
        SYNTAX  TimeStamp
        ACCESS  read-write
        STATUS  mandatory
        DESCRIPTION
            "Timestamp when shortest response time of a UCP inquiry
             message request occurred. The shortest response time can be
             reset by setting shortest response timestamp to zero."
        ::= { scTerminationPointEntry 245 }

    scTerminationPointAoUcp55LongestRespTime OBJECT-TYPE
        SYNTAX  HighResTime
        ACCESS  read-only
        STATUS  mandatory
        DESCRIPTION
            "Longest response time for processing a UCP inquiry message
             request."
        ::= { scTerminationPointEntry 246 }

    scTerminationPointAoUcp55TimestampLongestResp OBJECT-TYPE
        SYNTAX  TimeStamp
        ACCESS  read-write
        STATUS  mandatory
        DESCRIPTION
            "Timestamp when longest response time of a UCP inquiry
             message request occurred. The longest response time can be
             reset by setting longest response timestamp to zero."
        ::= { scTerminationPointEntry 247 }

    scTerminationPointCntAoUcp56Request OBJECT-TYPE
        SYNTAX  Counter
        ACCESS  read-only
        STATUS  mandatory
        DESCRIPTION
            "Counts the total number of UCP delete message requests
             which were sent to the SC termination point."
        ::= { scTerminationPointEntry 248 }

    scTerminationPointCntAoUcp56Ack OBJECT-TYPE
        SYNTAX  Counter
        ACCESS  read-only
        STATUS  mandatory
        DESCRIPTION
            "Counts the total number of positive UCP delete message
             responses which were received from the SC termination
             point."
        ::= { scTerminationPointEntry 249 }

    scTerminationPointCntAoUcp56Nack OBJECT-TYPE
        SYNTAX  Counter
        ACCESS  read-only
        STATUS  mandatory
        DESCRIPTION
            "Counts the total number of negative UCP delete message
             responses which were received from the SC termination
             point."
        ::= { scTerminationPointEntry 250 }

    scTerminationPointAoUcp56TimeSpent OBJECT-TYPE
        SYNTAX  HighResTime
        ACCESS  read-only
        STATUS  mandatory
        DESCRIPTION
            "Total time spent in processing UCP delete message
             requests."
        ::= { scTerminationPointEntry 251 }

    scTerminationPointAoUcp56ShortestRespTime OBJECT-TYPE
        SYNTAX  HighResTime
        ACCESS  read-only
        STATUS  mandatory
        DESCRIPTION
            "Shortest response time for processing a UCP delete message
             request."
        ::= { scTerminationPointEntry 252 }

    scTerminationPointAoUcp56TimestampShortestResp OBJECT-TYPE
        SYNTAX  TimeStamp
        ACCESS  read-write
        STATUS  mandatory
        DESCRIPTION
            "Timestamp when shortest response time of a UCP delete
             message request occurred. The shortest response time can be
             reset by setting shortest response timestamp to zero."
        ::= { scTerminationPointEntry 253 }

    scTerminationPointAoUcp56LongestRespTime OBJECT-TYPE
        SYNTAX  HighResTime
        ACCESS  read-only
        STATUS  mandatory
        DESCRIPTION
            "Longest response time for processing a UCP delete message
             request."
        ::= { scTerminationPointEntry 254 }

    scTerminationPointAoUcp56TimestampLongestResp OBJECT-TYPE
        SYNTAX  TimeStamp
        ACCESS  read-write
        STATUS  mandatory
        DESCRIPTION
            "Timestamp when longest response time of a UCP delete
             message request occurred. The longest response time can be
             reset by setting longest response timestamp to zero."
        ::= { scTerminationPointEntry 255 }

    scTerminationPointCntAoSmppSubmitSmRequest OBJECT-TYPE
        SYNTAX  Counter
        ACCESS  read-only
        STATUS  mandatory
        DESCRIPTION
            "Counts the total number of SMPP submit sm requests which
             were sent to the SC Termination Point."
        ::= { scTerminationPointEntry 300 }

    scTerminationPointCntAoSmppSubmitSmAck OBJECT-TYPE
        SYNTAX  Counter
        ACCESS  read-only
        STATUS  mandatory
        DESCRIPTION
            "Counts the total number of positive SMPP submit sm
             responses which were received from the SC Termination
             Point."
        ::= { scTerminationPointEntry 301 }

    scTerminationPointCntAoSmppSubmitSmNack OBJECT-TYPE
        SYNTAX  Counter
        ACCESS  read-only
        STATUS  mandatory
        DESCRIPTION
            "Counts the total number of negative SMPP submit sm
             responses which were received from the SC Termination
             Point."
        ::= { scTerminationPointEntry 302 }

    scTerminationPointAoSmppSubmitSmTimeSpent OBJECT-TYPE
        SYNTAX  HighResTime
        ACCESS  read-only
        STATUS  mandatory
        DESCRIPTION
            "Total time spent in processing SMPP submit sm requests."
        ::= { scTerminationPointEntry 303 }

    scTerminationPointAoSmppSubmitSmShortestRespTime OBJECT-TYPE
        SYNTAX  HighResTime
        ACCESS  read-only
        STATUS  mandatory
        DESCRIPTION
            "Shortest response time for processing an SMPP submit sm
             request."
        ::= { scTerminationPointEntry 304 }

    scTerminationPointAoSmppSubmitSmTimestampShortestResp OBJECT-TYPE
        SYNTAX  TimeStamp
        ACCESS  read-write
        STATUS  mandatory
        DESCRIPTION
            "Timestamp when shortest response time of an SMPP submit sm
             request occurred. The shortest response time can be reset
             by setting shortest response timestamp to zero."
        ::= { scTerminationPointEntry 305 }

    scTerminationPointAoSmppSubmitSmLongestRespTime OBJECT-TYPE
        SYNTAX  HighResTime
        ACCESS  read-only
        STATUS  mandatory
        DESCRIPTION
            "Longest response time for processing an SMPP submit sm
             request."
        ::= { scTerminationPointEntry 306 }

    scTerminationPointAoSmppSubmitSmTimestampLongestResp OBJECT-TYPE
        SYNTAX  TimeStamp
        ACCESS  read-write
        STATUS  mandatory
        DESCRIPTION
            "Timestamp when longest response time of an SMPP submit sm
             request occurred. The longest response time can be reset by
             setting the related  timestamp to zero."
        ::= { scTerminationPointEntry 307 }

    scTerminationPointCntAoSmppDataSmRequest OBJECT-TYPE
        SYNTAX  Counter
        ACCESS  read-only
        STATUS  mandatory
        DESCRIPTION
            "Counts the total number of SMPP data sm requests which were
             sent to the SC Termination Point."
        ::= { scTerminationPointEntry 308 }

    scTerminationPointCntAoSmppDataSmAck OBJECT-TYPE
        SYNTAX  Counter
        ACCESS  read-only
        STATUS  mandatory
        DESCRIPTION
            "Counts the total number of positive SMPP data sm responses
             which were received from the SC Termination Point."
        ::= { scTerminationPointEntry 309 }

    scTerminationPointCntAoSmppDataSmNack OBJECT-TYPE
        SYNTAX  Counter
        ACCESS  read-only
        STATUS  mandatory
        DESCRIPTION
            "Counts the total number of negative SMPP data sm responses
             which were received from the SC Termination Point."
        ::= { scTerminationPointEntry 310 }

    scTerminationPointAoSmppDataSmTimeSpent OBJECT-TYPE
        SYNTAX  HighResTime
        ACCESS  read-only
        STATUS  mandatory
        DESCRIPTION
            "Total time spent in processing SMPP data sm requests."
        ::= { scTerminationPointEntry 311 }

    scTerminationPointAoSmppDataSmShortestRespTime OBJECT-TYPE
        SYNTAX  HighResTime
        ACCESS  read-only
        STATUS  mandatory
        DESCRIPTION
            "Shortest response time for processing an SMPP data sm
             request."
        ::= { scTerminationPointEntry 312 }

    scTerminationPointAoSmppDataSmTimestampShortestResp OBJECT-TYPE
        SYNTAX  TimeStamp
        ACCESS  read-write
        STATUS  mandatory
        DESCRIPTION
            "Timestamp when shortest response time of an SMPP data sm
             request occurred. The shortest response time can be reset
             by setting shortest response timestamp to zero."
        ::= { scTerminationPointEntry 313 }

    scTerminationPointAoSmppDataSmLongestRespTime OBJECT-TYPE
        SYNTAX  HighResTime
        ACCESS  read-only
        STATUS  mandatory
        DESCRIPTION
            "Longest response time for processing an SMPP data sm
             request."
        ::= { scTerminationPointEntry 314 }

    scTerminationPointAoSmppDataSmTimestampLongestResp OBJECT-TYPE
        SYNTAX  TimeStamp
        ACCESS  read-write
        STATUS  mandatory
        DESCRIPTION
            "Timestamp when longest response time of an SMPP data sm
             request occurred. The longest response time can be reset by
             setting longest response timestamp to zero."
        ::= { scTerminationPointEntry 315 }

    scTerminationPointCntAoSmppBindRxRequest OBJECT-TYPE
        SYNTAX  Counter
        ACCESS  read-only
        STATUS  mandatory
        DESCRIPTION
            "Counts the total number of SMPP bind receiver requests
             which were sent to the SC Termination Point."
        ::= { scTerminationPointEntry 316 }

    scTerminationPointCntAoSmppBindRxAck OBJECT-TYPE
        SYNTAX  Counter
        ACCESS  read-only
        STATUS  mandatory
        DESCRIPTION
            "Counts the total number of positive SMPP bind receiver
             responses which were received from the SC Termination
             Point."
        ::= { scTerminationPointEntry 317 }

    scTerminationPointCntAoSmppBindRxNack OBJECT-TYPE
        SYNTAX  Counter
        ACCESS  read-only
        STATUS  mandatory
        DESCRIPTION
            "Counts the total number of negative SMPP bind receiver
             responses which were received from the SC Termination
             Point."
        ::= { scTerminationPointEntry 318 }

    scTerminationPointAoSmppBindRxTimeSpent OBJECT-TYPE
        SYNTAX  HighResTime
        ACCESS  read-only
        STATUS  mandatory
        DESCRIPTION
            "Total time spent in processing SMPP bind receiver
             requests."
        ::= { scTerminationPointEntry 319 }

    scTerminationPointAoSmppBindRxShortestRespTime OBJECT-TYPE
        SYNTAX  HighResTime
        ACCESS  read-only
        STATUS  mandatory
        DESCRIPTION
            "Shortest response time for processing an SMPP bind receiver
             request."
        ::= { scTerminationPointEntry 320 }

    scTerminationPointAoSmppBindRxTimestampShortestResp OBJECT-TYPE
        SYNTAX  TimeStamp
        ACCESS  read-write
        STATUS  mandatory
        DESCRIPTION
            "Timestamp when shortest response time of an SMPP bind
             receiver request occurred. The shortest response time can
             be reset by setting shortest response timestamp to zero."
        ::= { scTerminationPointEntry 321 }

    scTerminationPointAoSmppBindRxLongestRespTime OBJECT-TYPE
        SYNTAX  HighResTime
        ACCESS  read-only
        STATUS  mandatory
        DESCRIPTION
            "Longest response time for processing an SMPP bind receiver
             request."
        ::= { scTerminationPointEntry 322 }

    scTerminationPointAoSmppBindRxTimestampLongestResp OBJECT-TYPE
        SYNTAX  TimeStamp
        ACCESS  read-write
        STATUS  mandatory
        DESCRIPTION
            "Timestamp when longest response time of an SMPP bind
             receiver request occurred. The longest response time can be
             reset by setting the related  timestamp to zero."
        ::= { scTerminationPointEntry 323 }

    scTerminationPointCntAoSmppBindTxRequest OBJECT-TYPE
        SYNTAX  Counter
        ACCESS  read-only
        STATUS  mandatory
        DESCRIPTION
            "Counts the total number of SMPP bind transmitter requests
             which were sent to the SC Termination Point."
        ::= { scTerminationPointEntry 324 }

    scTerminationPointCntAoSmppBindTxAck OBJECT-TYPE
        SYNTAX  Counter
        ACCESS  read-only
        STATUS  mandatory
        DESCRIPTION
            "Counts the total number of positive SMPP bind transmitter
             responses which were received from the SC Termination
             Point."
        ::= { scTerminationPointEntry 325 }

    scTerminationPointCntAoSmppBindTxNack OBJECT-TYPE
        SYNTAX  Counter
        ACCESS  read-only
        STATUS  mandatory
        DESCRIPTION
            "Counts the total number of negative SMPP bind transmitter
             responses which were received from the SC Termination
             Point."
        ::= { scTerminationPointEntry 326 }

    scTerminationPointAoSmppBindTxTimeSpent OBJECT-TYPE
        SYNTAX  HighResTime
        ACCESS  read-only
        STATUS  mandatory
        DESCRIPTION
            "Total time spent in processing SMPP bind transmitter
             requests."
        ::= { scTerminationPointEntry 327 }

    scTerminationPointAoSmppBindTxShortestRespTime OBJECT-TYPE
        SYNTAX  HighResTime
        ACCESS  read-only
        STATUS  mandatory
        DESCRIPTION
            "Shortest response time for processing an SMPP bind
             transmitter request."
        ::= { scTerminationPointEntry 328 }

    scTerminationPointAoSmppBindTxTimestampShortestResp OBJECT-TYPE
        SYNTAX  TimeStamp
        ACCESS  read-write
        STATUS  mandatory
        DESCRIPTION
            "Timestamp when shortest response time of an SMPP bind
             transmitter request occurred. The shortest response time
             can be reset by setting shortest response timestamp to
             zero."
        ::= { scTerminationPointEntry 329 }

    scTerminationPointAoSmppBindTxLongestRespTime OBJECT-TYPE
        SYNTAX  HighResTime
        ACCESS  read-only
        STATUS  mandatory
        DESCRIPTION
            "Longest response time for processing an SMPP bind
             transmitter request."
        ::= { scTerminationPointEntry 330 }

    scTerminationPointAoSmppBindTxTimestampLongestResp OBJECT-TYPE
        SYNTAX  TimeStamp
        ACCESS  read-write
        STATUS  mandatory
        DESCRIPTION
            "Timestamp when longest response time of an SMPP bind
             transmitter request occurred. The longest response time can
             be reset by setting longest response timestamp to zero."
        ::= { scTerminationPointEntry 331 }

    scTerminationPointCntAoSmppBindTrxRequest OBJECT-TYPE
        SYNTAX  Counter
        ACCESS  read-only
        STATUS  mandatory
        DESCRIPTION
            "Counts the total number of SMPP bind transceiver requests
             which were sent to the SC Termination Point."
        ::= { scTerminationPointEntry 332 }

    scTerminationPointCntAoSmppBindTrxAck OBJECT-TYPE
        SYNTAX  Counter
        ACCESS  read-only
        STATUS  mandatory
        DESCRIPTION
            "Counts the total number of positive SMPP bind transceiver 
             responses which were received from the SC Termination
             Point."
        ::= { scTerminationPointEntry 333 }

    scTerminationPointCntAoSmppBindTrxNack OBJECT-TYPE
        SYNTAX  Counter
        ACCESS  read-only
        STATUS  mandatory
        DESCRIPTION
            "Counts the total number of negative SMPP bind transceiver 
             responses which were received from the SC Termination
             Point."
        ::= { scTerminationPointEntry 334 }

    scTerminationPointAoSmppBindTrxTimeSpent OBJECT-TYPE
        SYNTAX  HighResTime
        ACCESS  read-only
        STATUS  mandatory
        DESCRIPTION
            "Total time spent in processing SMPP bind transceiver 
             requests."
        ::= { scTerminationPointEntry 335 }

    scTerminationPointAoSmppBindTrxShortestRespTime OBJECT-TYPE
        SYNTAX  HighResTime
        ACCESS  read-only
        STATUS  mandatory
        DESCRIPTION
            "Shortest response time for processing an SMPP bind
             transceiver request."
        ::= { scTerminationPointEntry 336 }

    scTerminationPointAoSmppBindTrxTimestampShortestResp OBJECT-TYPE
        SYNTAX  TimeStamp
        ACCESS  read-write
        STATUS  mandatory
        DESCRIPTION
            "Timestamp when shortest response time of an SMPP bind
             transceiver request occurred. The shortest response time
             can be reset by setting shortest response timestamp to
             zero."
        ::= { scTerminationPointEntry 337 }

    scTerminationPointAoSmppBindTrxLongestRespTime OBJECT-TYPE
        SYNTAX  HighResTime
        ACCESS  read-only
        STATUS  mandatory
        DESCRIPTION
            "Longest response time for processing an SMPP bind
             transceiver request."
        ::= { scTerminationPointEntry 338 }

    scTerminationPointAoSmppBindTrxTimestampLongestResp OBJECT-TYPE
        SYNTAX  TimeStamp
        ACCESS  read-write
        STATUS  mandatory
        DESCRIPTION
            "Timestamp when longest response time of an SMPP bind
             transceiver request occurred. The longest response time can
             be reset by setting the related  timestamp to zero."
        ::= { scTerminationPointEntry 339 }

    scTerminationPointCntAoSmppUnbindRequest OBJECT-TYPE
        SYNTAX  Counter
        ACCESS  read-only
        STATUS  mandatory
        DESCRIPTION
            "Counts the total number of SMPP unbind requests which were
             sent to the SC Termination Point."
        ::= { scTerminationPointEntry 340 }

    scTerminationPointCntAoSmppUnbindAck OBJECT-TYPE
        SYNTAX  Counter
        ACCESS  read-only
        STATUS  mandatory
        DESCRIPTION
            "Counts the total number of positive SMPP unbind responses
             which were received from the SC Termination Point."
        ::= { scTerminationPointEntry 341 }

    scTerminationPointCntAoSmppUnbindNack OBJECT-TYPE
        SYNTAX  Counter
        ACCESS  read-only
        STATUS  mandatory
        DESCRIPTION
            "Counts the total number of negative SMPP unbind responses
             which were received from the SC Termination Point."
        ::= { scTerminationPointEntry 342 }

    scTerminationPointAoSmppUnbindTimeSpent OBJECT-TYPE
        SYNTAX  HighResTime
        ACCESS  read-only
        STATUS  mandatory
        DESCRIPTION
            "Total time spent in processing SMPP unbind requests."
        ::= { scTerminationPointEntry 343 }

    scTerminationPointAoSmppUnbindShortestRespTime OBJECT-TYPE
        SYNTAX  HighResTime
        ACCESS  read-only
        STATUS  mandatory
        DESCRIPTION
            "Shortest response time for processing an SMPP unbind
             request."
        ::= { scTerminationPointEntry 344 }

    scTerminationPointAoSmppUnbindTimestampShortestResp OBJECT-TYPE
        SYNTAX  TimeStamp
        ACCESS  read-write
        STATUS  mandatory
        DESCRIPTION
            "Timestamp when shortest response time of an SMPP unbind
             request occurred. The shortest response time can be reset
             by setting shortest response timestamp to zero."
        ::= { scTerminationPointEntry 345 }

    scTerminationPointAoSmppUnbindLongestRespTime OBJECT-TYPE
        SYNTAX  HighResTime
        ACCESS  read-only
        STATUS  mandatory
        DESCRIPTION
            "Longest response time for processing an SMPP unbind
             request."
        ::= { scTerminationPointEntry 346 }

    scTerminationPointAoSmppUnbindTimestampLongestResp OBJECT-TYPE
        SYNTAX  TimeStamp
        ACCESS  read-write
        STATUS  mandatory
        DESCRIPTION
            "Timestamp when longest response time of an SMPP unbind
             request occurred. The longest response time can be reset by
             setting longest response timestamp to zero."
        ::= { scTerminationPointEntry 347 }

    scTerminationPointCntAoSmppQuerySmRequest OBJECT-TYPE
        SYNTAX  Counter
        ACCESS  read-only
        STATUS  mandatory
        DESCRIPTION
            "Counts the total number of SMPP query sm requests which were
             sent to the SC Termination Point."
        ::= { scTerminationPointEntry 348 }

    scTerminationPointCntAoSmppQuerySmAck OBJECT-TYPE
        SYNTAX  Counter
        ACCESS  read-only
        STATUS  mandatory
        DESCRIPTION
            "Counts the total number of positive SMPP query sm responses
             which were received from the SC Termination Point."
        ::= { scTerminationPointEntry 349 }

    scTerminationPointCntAoSmppQuerySmNack OBJECT-TYPE
        SYNTAX  Counter
        ACCESS  read-only
        STATUS  mandatory
        DESCRIPTION
            "Counts the total number of negative SMPP query sm responses
             which were received from the SC Termination Point."
        ::= { scTerminationPointEntry 350 }

    scTerminationPointAoSmppQuerySmTimeSpent OBJECT-TYPE
        SYNTAX  HighResTime
        ACCESS  read-only
        STATUS  mandatory
        DESCRIPTION
            "Total time spent in processing SMPP query sm requests."
        ::= { scTerminationPointEntry 351 }

    scTerminationPointAoSmppQuerySmShortestRespTime OBJECT-TYPE
        SYNTAX  HighResTime
        ACCESS  read-only
        STATUS  mandatory
        DESCRIPTION
            "Shortest response time for processing an SMPP query sm
             request."
        ::= { scTerminationPointEntry 352 }

    scTerminationPointAoSmppQuerySmTimestampShortestResp OBJECT-TYPE
        SYNTAX  TimeStamp
        ACCESS  read-write
        STATUS  mandatory
        DESCRIPTION
            "Timestamp when shortest response time of an SMPP query sm
             request occurred. The shortest response time can be reset
             by setting shortest response timestamp to zero."
        ::= { scTerminationPointEntry 353 }

    scTerminationPointAoSmppQuerySmLongestRespTime OBJECT-TYPE
        SYNTAX  HighResTime
        ACCESS  read-only
        STATUS  mandatory
        DESCRIPTION
            "Longest response time for processing an SMPP query sm
             request."
        ::= { scTerminationPointEntry 354 }

    scTerminationPointAoSmppQuerySmTimestampLongestResp OBJECT-TYPE
        SYNTAX  TimeStamp
        ACCESS  read-write
        STATUS  mandatory
        DESCRIPTION
            "Timestamp when longest response time of an SMPP query sm
             request occurred. The longest response time can be reset by
             setting the related  timestamp to zero."
        ::= { scTerminationPointEntry 355 }

    scTerminationPointCntAoSmppReplaceSmRequest OBJECT-TYPE
        SYNTAX  Counter
        ACCESS  read-only
        STATUS  mandatory
        DESCRIPTION
            "Counts the total number of SMPP replace sm requests which
             were sent to the SC Termination Point."
        ::= { scTerminationPointEntry 356 }

    scTerminationPointCntAoSmppReplaceSmAck OBJECT-TYPE
        SYNTAX  Counter
        ACCESS  read-only
        STATUS  mandatory
        DESCRIPTION
            "Counts the total number of positive SMPP replace sm
             responses which were received from the SC Termination
             Point."
        ::= { scTerminationPointEntry 357 }

    scTerminationPointCntAoSmppReplaceSmNack OBJECT-TYPE
        SYNTAX  Counter
        ACCESS  read-only
        STATUS  mandatory
        DESCRIPTION
            "Counts the total number of negative SMPP replace sm
             responses which were received from the SC Termination
             Point."
        ::= { scTerminationPointEntry 358 }

    scTerminationPointAoSmppReplaceSmTimeSpent OBJECT-TYPE
        SYNTAX  HighResTime
        ACCESS  read-only
        STATUS  mandatory
        DESCRIPTION
            "Total time spent in processing SMPP replace sm requests."
        ::= { scTerminationPointEntry 359 }

    scTerminationPointAoSmppReplaceSmShortestRespTime OBJECT-TYPE
        SYNTAX  HighResTime
        ACCESS  read-only
        STATUS  mandatory
        DESCRIPTION
            "Shortest response time for processing an SMPP replace sm
             request."
        ::= { scTerminationPointEntry 360 }

    scTerminationPointAoSmppReplaceSmTimestampShortestResp OBJECT-TYPE
        SYNTAX  TimeStamp
        ACCESS  read-write
        STATUS  mandatory
        DESCRIPTION
            "Timestamp when shortest response time of an SMPP replace sm
             request occurred. The shortest response time can be reset
             by setting shortest response timestamp to zero."
        ::= { scTerminationPointEntry 361 }

    scTerminationPointAoSmppReplaceSmLongestRespTime OBJECT-TYPE
        SYNTAX  HighResTime
        ACCESS  read-only
        STATUS  mandatory
        DESCRIPTION
            "Longest response time for processing an SMPP replace sm
             request."
        ::= { scTerminationPointEntry 362 }

    scTerminationPointAoSmppReplaceSmTimestampLongestResp OBJECT-TYPE
        SYNTAX  TimeStamp
        ACCESS  read-write
        STATUS  mandatory
        DESCRIPTION
            "Timestamp when longest response time of an SMPP replace sm
             request occurred. The longest response time can be reset by
             setting longest response timestamp to zero."
        ::= { scTerminationPointEntry 363 }

    scTerminationPointCntAoSmppCancelSmRequest OBJECT-TYPE
        SYNTAX  Counter
        ACCESS  read-only
        STATUS  mandatory
        DESCRIPTION
            "Counts the total number of SMPP cancel sm requests which
             were sent to the SC Termination Point."
        ::= { scTerminationPointEntry 364 }

    scTerminationPointCntAoSmppCancelSmAck OBJECT-TYPE
        SYNTAX  Counter
        ACCESS  read-only
        STATUS  mandatory
        DESCRIPTION
            "Counts the total number of positive SMPP cancel sm
             responses which were received from the SC Termination
             Point."
        ::= { scTerminationPointEntry 365 }

    scTerminationPointCntAoSmppCancelSmNack OBJECT-TYPE
        SYNTAX  Counter
        ACCESS  read-only
        STATUS  mandatory
        DESCRIPTION
            "Counts the total number of negative SMPP cancel sm
             responses which were received from the SC Termination
             Point."
        ::= { scTerminationPointEntry 366 }

    scTerminationPointAoSmppCancelSmTimeSpent OBJECT-TYPE
        SYNTAX  HighResTime
        ACCESS  read-only
        STATUS  mandatory
        DESCRIPTION
            "Total time spent in processing SMPP cancel sm requests."
        ::= { scTerminationPointEntry 367 }

    scTerminationPointAoSmppCancelSmShortestRespTime OBJECT-TYPE
        SYNTAX  HighResTime
        ACCESS  read-only
        STATUS  mandatory
        DESCRIPTION
            "Shortest response time for processing an SMPP cancel sm
             requests."
        ::= { scTerminationPointEntry 368 }

    scTerminationPointAoSmppCancelSmTimestampShortestResp OBJECT-TYPE
        SYNTAX  TimeStamp
        ACCESS  read-write
        STATUS  mandatory
        DESCRIPTION
            "Timestamp when longest response time of an SMPP cancel sm
             request occurred. The shortest response time can be reset
             by setting shortest response timestamp to zero."
        ::= { scTerminationPointEntry 369 }

    scTerminationPointAoSmppCancelSmLongestRespTime OBJECT-TYPE
        SYNTAX  HighResTime
        ACCESS  read-only
        STATUS  mandatory
        DESCRIPTION
            "Longest response time for processing an SMPP cancel sm
             request."
        ::= { scTerminationPointEntry 370 }

    scTerminationPointAoSmppCancelSmTimestampLongestResp OBJECT-TYPE
        SYNTAX  TimeStamp
        ACCESS  read-write
        STATUS  mandatory
        DESCRIPTION
            "Timestamp when longest response time of an SMPP cancel sm
             request occurred. The longest response time can be reset by
             setting the related  timestamp to zero."
        ::= { scTerminationPointEntry 371 }

    scTerminationPointCntAoSmppEnquireLinkRequest OBJECT-TYPE
        SYNTAX  Counter
        ACCESS  read-only
        STATUS  mandatory
        DESCRIPTION
            "Counts the total number of SMPP enquire link requests which
             were sent to the SC Termination Point."
        ::= { scTerminationPointEntry 372 }

    scTerminationPointCntAoSmppEnquireLinkAck OBJECT-TYPE
        SYNTAX  Counter
        ACCESS  read-only
        STATUS  mandatory
        DESCRIPTION
            "Counts the total number of positive SMPP enquire link
             responses which were received from the SC Termination
             Point."
        ::= { scTerminationPointEntry 373 }

    scTerminationPointCntAoSmppEnquireLinkNack OBJECT-TYPE
        SYNTAX  Counter
        ACCESS  read-only
        STATUS  mandatory
        DESCRIPTION
            "Counts the total number of negative SMPP enquire link
             responses which were received from the SC Termination
             Point."
        ::= { scTerminationPointEntry 374 }

    scTerminationPointAoSmppEnquireLinkTimeSpent OBJECT-TYPE
        SYNTAX  HighResTime
        ACCESS  read-only
        STATUS  mandatory
        DESCRIPTION
            "Total time spent in processing SMPP enquire link requests."
        ::= { scTerminationPointEntry 375 }

    scTerminationPointAoSmppEnquireLinkShortestRespTime OBJECT-TYPE
        SYNTAX  HighResTime
        ACCESS  read-only
        STATUS  mandatory
        DESCRIPTION
            "Shortest response time for processing an SMPP enquire link
             requests."
        ::= { scTerminationPointEntry 376 }

    scTerminationPointAoSmppEnquireLinkTimestampShortestResp OBJECT-TYPE
        SYNTAX  TimeStamp
        ACCESS  read-write
        STATUS  mandatory
        DESCRIPTION
            "Timestamp when longest response time of an SMPP enquire
             link request occurred. The shortest response time can be
             reset by setting shortest response timestamp to zero."
        ::= { scTerminationPointEntry 377 }

    scTerminationPointAoSmppEnquireLinkLongestRespTime OBJECT-TYPE
        SYNTAX  HighResTime
        ACCESS  read-only
        STATUS  mandatory
        DESCRIPTION
            "Longest response time for processing an SMPP enquire link
             request."
        ::= { scTerminationPointEntry 378 }

    scTerminationPointAoSmppEnquireLinkTimestampLongestResp OBJECT-TYPE
        SYNTAX  TimeStamp
        ACCESS  read-write
        STATUS  mandatory
        DESCRIPTION
            "Timestamp when longest response time of an SMPP enquire
             link request occurred. The longest response time can be
             reset by setting the related  timestamp to zero."
        ::= { scTerminationPointEntry 379 }

    scTerminationPointCntAoSmppOtherRequest OBJECT-TYPE
        SYNTAX  Counter
        ACCESS  read-only
        STATUS  mandatory
        DESCRIPTION
            "Counts the total number of SMPP unknown requests which were
             sent to the SC Termination Point."
        ::= { scTerminationPointEntry 380 }

    scTerminationPointCntAoSmppOtherAck OBJECT-TYPE
        SYNTAX  Counter
        ACCESS  read-only
        STATUS  mandatory
        DESCRIPTION
            "Counts the total number of positive SMPP unknown responses
             which were received from the SC Termination Point."
        ::= { scTerminationPointEntry 381 }

    scTerminationPointCntAoSmppOtherNack OBJECT-TYPE
        SYNTAX  Counter
        ACCESS  read-only
        STATUS  mandatory
        DESCRIPTION
            "Counts the total number of negative SMPP unknown responses
             which were received from the SC Termination Point."
        ::= { scTerminationPointEntry 382 }

    scTerminationPointAoSmppOtherTimeSpent OBJECT-TYPE
        SYNTAX  HighResTime
        ACCESS  read-only
        STATUS  mandatory
        DESCRIPTION
            "Total time spent in processing SMPP unknown requests."
        ::= { scTerminationPointEntry 383 }

    scTerminationPointAoSmppOtherShortestRespTime OBJECT-TYPE
        SYNTAX  HighResTime
        ACCESS  read-only
        STATUS  mandatory
        DESCRIPTION
            "Shortest response time for processing an SMPP unknown
             request."
        ::= { scTerminationPointEntry 384 }

    scTerminationPointAoSmppOtherTimestampShortestResp OBJECT-TYPE
        SYNTAX  TimeStamp
        ACCESS  read-write
        STATUS  mandatory
        DESCRIPTION
            "Timestamp when shortest response time of an SMPP unknown
             request occurred. The shortest response time can be reset
             by setting shortest response timestamp to zero."
        ::= { scTerminationPointEntry 385 }

    scTerminationPointAoSmppOtherLongestRespTime OBJECT-TYPE
        SYNTAX  HighResTime
        ACCESS  read-only
        STATUS  mandatory
        DESCRIPTION
            "Longest response time for processing an SMPP unknown
             requests."
        ::= { scTerminationPointEntry 386 }

    scTerminationPointAoSmppOtherTimestampLongestResp OBJECT-TYPE
        SYNTAX  TimeStamp
        ACCESS  read-write
        STATUS  mandatory
        DESCRIPTION
            "Timestamp when longest response time of an SMPP unknown
             request occurred. The longest response time can be reset by
             setting longest response timestamp to zero."
        ::= { scTerminationPointEntry 387 }

    scTerminationPointAoSmppGenericNack OBJECT-TYPE
        SYNTAX  Counter
        ACCESS  read-only
        STATUS  mandatory
        DESCRIPTION
            "Counts the total number of SMPP generic nacks which were
             received from the SC Termination Point."
        ::= { scTerminationPointEntry 388 }

    scTerminationPointCntAoCimdLoginRequest OBJECT-TYPE
        SYNTAX  Counter
        ACCESS  read-only
        STATUS  mandatory
        DESCRIPTION
            "Counts the total number of CIMD login requests which were
             sent to the SC Termination Point."
        ::= { scTerminationPointEntry 400 }

    scTerminationPointCntAoCimdLoginAck OBJECT-TYPE
        SYNTAX  Counter
        ACCESS  read-only
        STATUS  mandatory
        DESCRIPTION
            "Counts the total number of positive CIMD login responses
             which were received from the SC Termination Point."
        ::= { scTerminationPointEntry 401 }

    scTerminationPointCntAoCimdLoginNack OBJECT-TYPE
        SYNTAX  Counter
        ACCESS  read-only
        STATUS  mandatory
        DESCRIPTION
            "Counts the total number of negative CIMD login responses
             which were received from the SC Termination Point."
        ::= { scTerminationPointEntry 402 }

    scTerminationPointAoCimdLoginTimeSpent OBJECT-TYPE
        SYNTAX  HighResTime
        ACCESS  read-only
        STATUS  mandatory
        DESCRIPTION
            "Total time spent in processing CIMD login requests."
        ::= { scTerminationPointEntry 403 }

    scTerminationPointAoCimdLoginShortestRespTime OBJECT-TYPE
        SYNTAX  HighResTime
        ACCESS  read-only
        STATUS  mandatory
        DESCRIPTION
            "Shortest response time for processing a CIMD login
             request."
        ::= { scTerminationPointEntry 404 }

    scTerminationPointAoCimdLoginTimestampShortestResp OBJECT-TYPE
        SYNTAX  TimeStamp
        ACCESS  read-write
        STATUS  mandatory
        DESCRIPTION
            "Timestamp when shortest response time of a CIMD login
             request occurred. The shortest response time can be reset
             by setting shortest response timestamp to zero."
        ::= { scTerminationPointEntry 405 }

    scTerminationPointAoCimdLoginLongestRespTime OBJECT-TYPE
        SYNTAX  HighResTime
        ACCESS  read-only
        STATUS  mandatory
        DESCRIPTION
            "Longest response time for processing a CIMD login
             request."
        ::= { scTerminationPointEntry 406 }

    scTerminationPointAoCimdLoginTimestampLongestResp OBJECT-TYPE
        SYNTAX  TimeStamp
        ACCESS  read-write
        STATUS  mandatory
        DESCRIPTION
            "Timestamp when longest response time of a CIMD login
             request occurred. The longest response time can be reset by
             setting the related  timestamp to zero."
        ::= { scTerminationPointEntry 407 }

    scTerminationPointCntAoCimdLogoutRequest OBJECT-TYPE
        SYNTAX  Counter
        ACCESS  read-only
        STATUS  mandatory
        DESCRIPTION
            "Counts the total number of CIMD logout requests which were
             sent to the SC Termination Point."
        ::= { scTerminationPointEntry 408 }

    scTerminationPointCntAoCimdLogoutAck OBJECT-TYPE
        SYNTAX  Counter
        ACCESS  read-only
        STATUS  mandatory
        DESCRIPTION
            "Counts the total number of positive CIMD logout responses
             which were received from the SC Termination Point."
        ::= { scTerminationPointEntry 409 }

    scTerminationPointCntAoCimdLogoutNack OBJECT-TYPE
        SYNTAX  Counter
        ACCESS  read-only
        STATUS  mandatory
        DESCRIPTION
            "Counts the total number of negative CIMD logout responses
             which were received from the SC Termination Point."
        ::= { scTerminationPointEntry 410 }

    scTerminationPointAoCimdLogoutTimeSpent OBJECT-TYPE
        SYNTAX  HighResTime
        ACCESS  read-only
        STATUS  mandatory
        DESCRIPTION
            "Total time spent in processing CIMD logout requests."
        ::= { scTerminationPointEntry 411 }

    scTerminationPointAoCimdLogoutShortestRespTime OBJECT-TYPE
        SYNTAX  HighResTime
        ACCESS  read-only
        STATUS  mandatory
        DESCRIPTION
            "Shortest response time for processing a CIMD logout
             request."
        ::= { scTerminationPointEntry 412 }

    scTerminationPointAoCimdLogoutTimestampShortestResp OBJECT-TYPE
        SYNTAX  TimeStamp
        ACCESS  read-write
        STATUS  mandatory
        DESCRIPTION
            "Timestamp when shortest response time of a CIMD logout
             request occurred. The shortest response time can be reset
             by setting shortest response timestamp to zero."
        ::= { scTerminationPointEntry 413 }

    scTerminationPointAoCimdLogoutLongestRespTime OBJECT-TYPE
        SYNTAX  HighResTime
        ACCESS  read-only
        STATUS  mandatory
        DESCRIPTION
            "Longest response time for processing a CIMD logout
             request."
        ::= { scTerminationPointEntry 414 }

    scTerminationPointAoCimdLogoutTimestampLongestResp OBJECT-TYPE
        SYNTAX  TimeStamp
        ACCESS  read-write
        STATUS  mandatory
        DESCRIPTION
            "Timestamp when longest response time of a CIMD logout
             request occurred. The longest response time can be reset by
             setting the related  timestamp to zero."
        ::= { scTerminationPointEntry 415 }

    scTerminationPointCntAoCimdSubmitRequest OBJECT-TYPE
        SYNTAX  Counter
        ACCESS  read-only
        STATUS  mandatory
        DESCRIPTION
            "Counts the total number of CIMD submit sm request which
             were sent to the SC Termination Point."
        ::= { scTerminationPointEntry 416 }

    scTerminationPointCntAoCimdSubmitAck OBJECT-TYPE
        SYNTAX  Counter
        ACCESS  read-only
        STATUS  mandatory
        DESCRIPTION
            "Counts the total number of positive CIMD submit sm
             responses which were received from the SC Termination
             Point."
        ::= { scTerminationPointEntry 417 }

    scTerminationPointCntAoCimdSubmitNack OBJECT-TYPE
        SYNTAX  Counter
        ACCESS  read-only
        STATUS  mandatory
        DESCRIPTION
            "Counts the total number of negative CIMD submit sm
             responses which were received from the SC Termination
             Point."
        ::= { scTerminationPointEntry 418 }

    scTerminationPointAoCimdSubmitTimeSpent OBJECT-TYPE
        SYNTAX  HighResTime
        ACCESS  read-only
        STATUS  mandatory
        DESCRIPTION
            "Total time spent in processing CIMD submit sm requests."
        ::= { scTerminationPointEntry 419 }

    scTerminationPointAoCimdSubmitShortestRespTime OBJECT-TYPE
        SYNTAX  HighResTime
        ACCESS  read-only
        STATUS  mandatory
        DESCRIPTION
            "Shortest response time for processing a CIMD submit sm
             request."
        ::= { scTerminationPointEntry 420 }

    scTerminationPointAoCimdSubmitTimestampShortestResp OBJECT-TYPE
        SYNTAX  TimeStamp
        ACCESS  read-write
        STATUS  mandatory
        DESCRIPTION
            "Timestamp when shortest response time of a CIMD submit sm
             request occurred. The shortest response time can be reset
             by setting shortest response timestamp to zero."
        ::= { scTerminationPointEntry 421 }

    scTerminationPointAoCimdSubmitLongestRespTime OBJECT-TYPE
        SYNTAX  HighResTime
        ACCESS  read-only
        STATUS  mandatory
        DESCRIPTION
            "Longest response time for processing a CIMD submit sm
             request."
        ::= { scTerminationPointEntry 422 }

    scTerminationPointAoCimdSubmitTimestampLongestResp OBJECT-TYPE
        SYNTAX  TimeStamp
        ACCESS  read-write
        STATUS  mandatory
        DESCRIPTION
            "Timestamp when longest response time of a CIMD submit sm
             request occurred. The longest response time can be reset by
             setting the related  timestamp to zero."
        ::= { scTerminationPointEntry 423 }

    scTerminationPointCntAoCimdEnquireRequest OBJECT-TYPE
        SYNTAX  Counter
        ACCESS  read-only
        STATUS  mandatory
        DESCRIPTION
            "Counts the total number of CIMD enquire message status
             requests which were sent to the SC Termination Point."
        ::= { scTerminationPointEntry 424 }

    scTerminationPointCntAoCimdEnquireAck OBJECT-TYPE
        SYNTAX  Counter
        ACCESS  read-only
        STATUS  mandatory
        DESCRIPTION
            "Counts the total number of positive CIMD enquire message
             status responses which were received from the SC
             Termination Point."
        ::= { scTerminationPointEntry 425 }

    scTerminationPointCntAoCimdEnquireNack OBJECT-TYPE
        SYNTAX  Counter
        ACCESS  read-only
        STATUS  mandatory
        DESCRIPTION
            "Counts the total number of negative CIMD enquire message
             status responses which were received from the SC
             Termination Point."
        ::= { scTerminationPointEntry 426 }

    scTerminationPointAoCimdEnquireTimeSpent OBJECT-TYPE
        SYNTAX  HighResTime
        ACCESS  read-only
        STATUS  mandatory
        DESCRIPTION
            "Total time spent in processing CIMD enquire message status
             requests."
        ::= { scTerminationPointEntry 427 }

    scTerminationPointAoCimdEnquireShortestRespTime OBJECT-TYPE
        SYNTAX  HighResTime
        ACCESS  read-only
        STATUS  mandatory
        DESCRIPTION
            "Shortest response time for processing a CIMD enquire
             message status request."
        ::= { scTerminationPointEntry 428 }

    scTerminationPointAoCimdEnquireTimestampShortestResp OBJECT-TYPE
        SYNTAX  TimeStamp
        ACCESS  read-write
        STATUS  mandatory
        DESCRIPTION
            "Timestamp when shortest response time of a CIMD enquire
             message status request occurred. The shortest response time
             can be reset by setting shortest response timestamp to
             zero."
        ::= { scTerminationPointEntry 429 }

    scTerminationPointAoCimdEnquireLongestRespTime OBJECT-TYPE
        SYNTAX  HighResTime
        ACCESS  read-only
        STATUS  mandatory
        DESCRIPTION
            "Longest response time for processing a CIMD enquire message
             status request."
        ::= { scTerminationPointEntry 430 }

    scTerminationPointAoCimdEnquireTimestampLongestResp OBJECT-TYPE
        SYNTAX  TimeStamp
        ACCESS  read-write
        STATUS  mandatory
        DESCRIPTION
            "Timestamp when longest response time of a CIMD enquire
             message status request occurred. The longest response time
             can be reset by setting the related  timestamp to zero."
        ::= { scTerminationPointEntry 431 }

    scTerminationPointCntAoCimdOtherRequest OBJECT-TYPE
        SYNTAX  Counter
        ACCESS  read-only
        STATUS  mandatory
        DESCRIPTION
            "Counts the total number of unknown CIMD requests which were
             sent to the SC Termination Point."
        ::= { scTerminationPointEntry 432 }

    scTerminationPointCntAoCimdOtherAck OBJECT-TYPE
        SYNTAX  Counter
        ACCESS  read-only
        STATUS  mandatory
        DESCRIPTION
            "Counts the total number of positive unknown CIMD responses
             which were received from the SC Termination Point."
        ::= { scTerminationPointEntry 433 }

    scTerminationPointCntAoCimdOtherNack OBJECT-TYPE
        SYNTAX  Counter
        ACCESS  read-only
        STATUS  mandatory
        DESCRIPTION
            "Counts the total number of negative unknown CIMD responses
             which were received from the SC Termination Point."
        ::= { scTerminationPointEntry 434 }

    scTerminationPointAoCimdOtherTimeSpent OBJECT-TYPE
        SYNTAX  HighResTime
        ACCESS  read-only
        STATUS  mandatory
        DESCRIPTION
            "Total time spent in processing unknown CIMD requests."
        ::= { scTerminationPointEntry 435 }

    scTerminationPointAoCimdOtherShortestRespTime OBJECT-TYPE
        SYNTAX  HighResTime
        ACCESS  read-only
        STATUS  mandatory
        DESCRIPTION
            "Shortest response time for processing an unknown CIMD
             request."
        ::= { scTerminationPointEntry 436 }

    scTerminationPointAoCimdOtherTimestampShortestResp OBJECT-TYPE
        SYNTAX  TimeStamp
        ACCESS  read-write
        STATUS  mandatory
        DESCRIPTION
            "Timestamp when shortest response time of an unknown CIMD
             request occurred. The shortest response time can be reset
             by setting shortest response timestamp to zero."
        ::= { scTerminationPointEntry 437 }

    scTerminationPointAoCimdOtherLongestRespTime OBJECT-TYPE
        SYNTAX  HighResTime
        ACCESS  read-only
        STATUS  mandatory
        DESCRIPTION
            "Longest response time for processing an unknown CIMD
             request."
        ::= { scTerminationPointEntry 438 }

    scTerminationPointAoCimdOtherTimestampLongestResp OBJECT-TYPE
        SYNTAX  TimeStamp
        ACCESS  read-write
        STATUS  mandatory
        DESCRIPTION
            "Timestamp when longest response time of an unknown CIMD
             request occurred. The longest response time can be reset by
             setting the related  timestamp to zero."
        ::= { scTerminationPointEntry 439 }

    scTerminationPointCntAtUcp52Request OBJECT-TYPE
        SYNTAX  Counter
        ACCESS  read-only
        STATUS  mandatory
        DESCRIPTION
            "Counts the total number of UCP deliver sm request which
             were received from the SC Termination Point."
        ::= { scTerminationPointEntry 500 }

    scTerminationPointCntAtUcp52Ack OBJECT-TYPE
        SYNTAX  Counter
        ACCESS  read-only
        STATUS  mandatory
        DESCRIPTION
            "Counts the total number of positive UCP deliver sm
             responses which were sent to the SC Termination Point."
        ::= { scTerminationPointEntry 501 }

    scTerminationPointCntAtUcp52Nack OBJECT-TYPE
        SYNTAX  Counter
        ACCESS  read-only
        STATUS  mandatory
        DESCRIPTION
            "Counts the total number of negative UCP deliver sm
             responses which were sent to the SC Termination Point."
        ::= { scTerminationPointEntry 502 }

    scTerminationPointCntAtUcp53Request OBJECT-TYPE
        SYNTAX  Counter
        ACCESS  read-only
        STATUS  mandatory
        DESCRIPTION
            "Counts the total number of UCP deliver notify requests which
             were received from the SC Termination Point."
        ::= { scTerminationPointEntry 503 }

    scTerminationPointCntAtUcp53Ack OBJECT-TYPE
        SYNTAX  Counter
        ACCESS  read-only
        STATUS  mandatory
        DESCRIPTION
            "Counts the total number of positive UCP deliver notify
             responses which were sent to the SC Termination Point."
        ::= { scTerminationPointEntry 504 }

    scTerminationPointCntAtUcp53Nack OBJECT-TYPE
        SYNTAX  Counter
        ACCESS  read-only
        STATUS  mandatory
        DESCRIPTION
            "Counts the total number of negative UCP deliver notify
             responses which were sent to the SC Termination Point."
        ::= { scTerminationPointEntry 505 }

    scTerminationPointCntAtUcpOtherRequest OBJECT-TYPE
        SYNTAX  Counter
        ACCESS  read-only
        STATUS  mandatory
        DESCRIPTION
            "Counts the total number of unknown UCP requests which were
             received from the SC Termination Point."
        ::= { scTerminationPointEntry 506 }

    scTerminationPointCntAtUcpOtherAck OBJECT-TYPE
        SYNTAX  Counter
        ACCESS  read-only
        STATUS  mandatory
        DESCRIPTION
            "Counts the total number of positive unknown UCP responses
             which were sent to the SC Termination Point."
        ::= { scTerminationPointEntry 507 }

    scTerminationPointCntAtUcpOtherNack OBJECT-TYPE
        SYNTAX  Counter
        ACCESS  read-only
        STATUS  mandatory
        DESCRIPTION
            "Counts the total number of negative unknown UCP responses
             which were sent to the SC Termination Point."
        ::= { scTerminationPointEntry 508 }

    scTerminationPointCntAtUcp57Request OBJECT-TYPE
        SYNTAX  Counter
        ACCESS  read-only
        STATUS  mandatory
        DESCRIPTION
            "Counts the total number of UCP response inquiry message
             requests which were received from the SC termination
             point."
        ::= { scTerminationPointEntry 509 }

    scTerminationPointCntAtUcp57Ack OBJECT-TYPE
        SYNTAX  Counter
        ACCESS  read-only
        STATUS  mandatory
        DESCRIPTION
            "Counts the total number of positive UCP response inquiry
             message responses which were sent to the SC termination
             point."
        ::= { scTerminationPointEntry 510 }

    scTerminationPointCntAtUcp57Nack OBJECT-TYPE
        SYNTAX  Counter
        ACCESS  read-only
        STATUS  mandatory
        DESCRIPTION
            "Counts the total number of negative UCP response inquiry
             message responses which were sent to the SC termination
             point."
        ::= { scTerminationPointEntry 511 }

    scTerminationPointCntAtUcp58Request OBJECT-TYPE
        SYNTAX  Counter
        ACCESS  read-only
        STATUS  mandatory
        DESCRIPTION
            "Counts the total number of UCP response delete message
             requests which were received from the SC termination
             point."
        ::= { scTerminationPointEntry 512 }

    scTerminationPointCntAtUcp58Ack OBJECT-TYPE
        SYNTAX  Counter
        ACCESS  read-only
        STATUS  mandatory
        DESCRIPTION
            "Counts the total number of positive UCP response delete
             message responses which were sent to the SC termination
             point."
        ::= { scTerminationPointEntry 513 }

    scTerminationPointCntAtUcp58Nack OBJECT-TYPE
        SYNTAX  Counter
        ACCESS  read-only
        STATUS  mandatory
        DESCRIPTION
            "Counts the total number of negative UCP response delete
             message responses which were sent to the SC termination
             point."
        ::= { scTerminationPointEntry 514 }

    scTerminationPointCntAtSmppDeliverSmRequest OBJECT-TYPE
        SYNTAX  Counter
        ACCESS  read-only
        STATUS  mandatory
        DESCRIPTION
            "Counts the total number of SMPP deliver sm requests which
             were received from the SC Termination Point."
        ::= { scTerminationPointEntry 520 }

    scTerminationPointCntAtSmppDeliverSmAck OBJECT-TYPE
        SYNTAX  Counter
        ACCESS  read-only
        STATUS  mandatory
        DESCRIPTION
            "Counts the total number of positive SMPP deliver sm
             responses which were sent to the SC Termination Point."
        ::= { scTerminationPointEntry 521 }

    scTerminationPointCntAtSmppDeliverSmNack OBJECT-TYPE
        SYNTAX  Counter
        ACCESS  read-only
        STATUS  mandatory
        DESCRIPTION
            "Counts the total number of negative SMPP deliver sm
             responses which were sent to the SC Termination Point."
        ::= { scTerminationPointEntry 522 }

    scTerminationPointCntAtSmppDataSmRequest OBJECT-TYPE
        SYNTAX  Counter
        ACCESS  read-only
        STATUS  mandatory
        DESCRIPTION
            "Counts the total number of SMPP data sm requests which were
             received from the SC Termination Point."
        ::= { scTerminationPointEntry 523 }

    scTerminationPointCntAtSmppDataSmAck OBJECT-TYPE
        SYNTAX  Counter
        ACCESS  read-only
        STATUS  mandatory
        DESCRIPTION
            "Counts the total number of positive SMPP data sm responses
             which were sent to the SC Termination Point."
        ::= { scTerminationPointEntry 524 }

    scTerminationPointCntAtSmppDataSmNack OBJECT-TYPE
        SYNTAX  Counter
        ACCESS  read-only
        STATUS  mandatory
        DESCRIPTION
            "Counts the total number of negative SMPP data sm responses
             which were sent to the SC Termination Point."
        ::= { scTerminationPointEntry 525 }

    scTerminationPointCntAtSmppOtherRequest OBJECT-TYPE
        SYNTAX  Counter
        ACCESS  read-only
        STATUS  mandatory
        DESCRIPTION
            "Counts the total number of unknown SMPP requests which were
             received from the SC Termination Point."
        ::= { scTerminationPointEntry 526 }

    scTerminationPointCntAtSmppOtherAck OBJECT-TYPE
        SYNTAX  Counter
        ACCESS  read-only
        STATUS  mandatory
        DESCRIPTION
            "Counts the total number of positive unknown SMPP responses
             which were sent to the SC Termination Point."
        ::= { scTerminationPointEntry 527 }

    scTerminationPointCntAtSmppOtherNack OBJECT-TYPE
        SYNTAX  Counter
        ACCESS  read-only
        STATUS  mandatory
        DESCRIPTION
            "Counts the total number of negative unknown SMPP responses
             which were sent to the SC Termination Point."
        ::= { scTerminationPointEntry 528 }

    scTerminationPointCntAtCimdDeliverRequest OBJECT-TYPE
        SYNTAX  Counter
        ACCESS  read-only
        STATUS  mandatory
        DESCRIPTION
            "Counts the total number of CIMD deliver sm requests which
             were received from the SC Termination Point."
        ::= { scTerminationPointEntry 540 }

    scTerminationPointCntAtCimdDeliverAck OBJECT-TYPE
        SYNTAX  Counter
        ACCESS  read-only
        STATUS  mandatory
        DESCRIPTION
            "Counts the total number of positive CIMD deliver sm
             responses which were sent to the SC Termination Point."
        ::= { scTerminationPointEntry 541 }

    scTerminationPointCntAtCimdDeliverNack OBJECT-TYPE
        SYNTAX  Counter
        ACCESS  read-only
        STATUS  mandatory
        DESCRIPTION
            "Counts the total number of negative CIMD deliver sm
             responses which were sent to the SC Termination Point."
        ::= { scTerminationPointEntry 542 }

    scTerminationPointCntAtCimdDeliverStatusRequest OBJECT-TYPE
        SYNTAX  Counter
        ACCESS  read-only
        STATUS  mandatory
        DESCRIPTION
            "Counts the total number of CIMD deliver status requests
             which were received from the SC Termination Point."
        ::= { scTerminationPointEntry 543 }

    scTerminationPointCntAtCimdDeliverStatusAck OBJECT-TYPE
        SYNTAX  Counter
        ACCESS  read-only
        STATUS  mandatory
        DESCRIPTION
            "Counts the total number of positive CIMD deliver status
             responses which were sent to the SC Termination Point."
        ::= { scTerminationPointEntry 544 }

    scTerminationPointCntAtCimdDeliverStatusNack OBJECT-TYPE
        SYNTAX  Counter
        ACCESS  read-only
        STATUS  mandatory
        DESCRIPTION
            "Counts the total number of negative CIMD deliver status
             responses which were sent to the SC Termination Point."
        ::= { scTerminationPointEntry 545 }

    scTerminationPointCntAtCimdAliveRequest OBJECT-TYPE
        SYNTAX  Counter
        ACCESS  read-only
        STATUS  mandatory
        DESCRIPTION
            "Counts the total number of CIMD alive message requests which
             were received from the SC Termination Point."
        ::= { scTerminationPointEntry 546 }

    scTerminationPointCntAtCimdAliveAck OBJECT-TYPE
        SYNTAX  Counter
        ACCESS  read-only
        STATUS  mandatory
        DESCRIPTION
            "Counts the total number of positive CIMD alive message
             responses which were sent to the SC Termination Point."
        ::= { scTerminationPointEntry 547 }

    scTerminationPointCntAtCimdAliveNack OBJECT-TYPE
        SYNTAX  Counter
        ACCESS  read-only
        STATUS  mandatory
        DESCRIPTION
            "Counts the total number of negative CIMD alive message
             responses which were sent to the SC Termination Point."
        ::= { scTerminationPointEntry 548 }

    scTerminationPointCntAtCimdOtherRequest OBJECT-TYPE
        SYNTAX  Counter
        ACCESS  read-only
        STATUS  mandatory
        DESCRIPTION
            "Counts the total number of unknown CIMD requests which were
             received from the SC Termination Point."
        ::= { scTerminationPointEntry 549 }

    scTerminationPointCntAtCimdOtherAck OBJECT-TYPE
        SYNTAX  Counter
        ACCESS  read-only
        STATUS  mandatory
        DESCRIPTION
            "Counts the total number of positive unknown CIMD responses
             which were sent to the SC Termination Point."
        ::= { scTerminationPointEntry 550 }

    scTerminationPointCntAtCimdOtherNack OBJECT-TYPE
        SYNTAX  Counter
        ACCESS  read-only
        STATUS  mandatory
        DESCRIPTION
            "Counts the total number of negative unknown CIMD responses
             which were sent to the SC Termination Point."
        ::= { scTerminationPointEntry 551 }


    -- the ApplicationServiceCentre Entity

    applicationServiceCentreTable OBJECT-TYPE
        SYNTAX  SEQUENCE OF ApplicationServiceCentreEntry
        ACCESS  not-accessible
        STATUS  mandatory
        DESCRIPTION
            "A table containing properties for each association between an
            Application and a ServiceCentre.
            Only applicable for applications with SessionModel:
            InsideOnlyScList, PermDialoutScList, DistributeScList or
            ReplicateScList.
            Entries can only be added in case the Application is inactive or
            in case the Application is active and the Session model is one of
            the above."
        ::= { apc 24 }

    applicationServiceCentreEntry OBJECT-TYPE
        SYNTAX  ApplicationServiceCentreEntry
        ACCESS  not-accessible
        STATUS  mandatory
        DESCRIPTION
            "Table entry defining a single ApplicationServiceCentre."
        INDEX   { applicationServiceCentreApplicationIndex,
                  applicationServiceCentreServiceCentreIndex }
        ::= { applicationServiceCentreTable 1 }

    ApplicationServiceCentreEntry ::=
        SEQUENCE {
            applicationServiceCentreApplicationIndex        ApplicationTableIndex,
            applicationServiceCentreServiceCentreIndex      ServiceCentreTableIndex,
            applicationServiceCentreAdminState              AdminState,
            applicationServiceCentrePriority                Priority,
            applicationServiceCentreWeight                  Weight
        }

    applicationServiceCentreApplicationIndex OBJECT-TYPE
        SYNTAX  ApplicationTableIndex
        ACCESS  read-write
        STATUS  mandatory
        DESCRIPTION
            "Index referring to an entry in the Application table."
        ::= { applicationServiceCentreEntry 1 }

    applicationServiceCentreServiceCentreIndex OBJECT-TYPE
        SYNTAX  ServiceCentreTableIndex
        ACCESS  read-write
        STATUS  mandatory
        DESCRIPTION
            "Index referring to an entry in the Service Centre table."
        ::= { applicationServiceCentreEntry 2 }

    applicationServiceCentreAdminState OBJECT-TYPE
        SYNTAX  AdminState
        ACCESS  read-write
        STATUS  mandatory
        DESCRIPTION
            "Administrative state of the ApplicationServiceCentre.

            Transition from 'inactive' to 'active' is only possible when:
            1) Application and ServiceCentre exist.

            Transition from 'active' to 'inactive' is always possible but will
            result in a graceful shutdown of pending inside sessions towards
            this Service Centre.

            Transition to 'destroy' is always possible.

            For details, refer to the comment on the AdminState type."
        ::= { applicationServiceCentreEntry 3 }

    applicationServiceCentrePriority OBJECT-TYPE
        SYNTAX  Priority
        ACCESS  read-write
        STATUS  mandatory
        DESCRIPTION
            "Priority of a Service Centre when routing AO messages to a set of
            Service Centres.

            For details, refer to the comment on the Priority type."
        ::= { applicationServiceCentreEntry 11 }

    applicationServiceCentreWeight OBJECT-TYPE
        SYNTAX  Weight
        ACCESS  read-write
        STATUS  mandatory
        DESCRIPTION
            "Weight in load-balancing scheme for a Service Centre when routing
            AO messages to a set of Service Centres."
        ::= { applicationServiceCentreEntry 12 }

    ----------------------------------------------------------------------------
    --                                T R A P S                               --
    ----------------------------------------------------------------------------

    applicationOutsideSmppReceiverStarted TRAP-TYPE
        ENTERPRISE apc
        VARIABLES { applicationOutsideSmppReceiversCounter, applicationName, deviceType }
        DESCRIPTION
            "Application established a new SMPP receiver with TextPass"
        ::= 1

    applicationOutsideSmppReceiverStopped TRAP-TYPE
        ENTERPRISE apc
        VARIABLES { applicationOutsideSmppReceiversCounter, applicationName, deviceType }
        DESCRIPTION
            "An SMPP receiver between Application and TextPass has been
            released"
        ::= 2

    applicationOutsideSmppTransmitterStarted TRAP-TYPE
        ENTERPRISE apc
        VARIABLES { applicationOutsideSmppTransmittersCounter, applicationName, deviceType }
        DESCRIPTION
            "Application established a new SMPP transmitter with TextPass"
        ::= 3

    applicationOutsideSmppTransmitterStopped TRAP-TYPE
        ENTERPRISE apc
        VARIABLES { applicationOutsideSmppTransmittersCounter, applicationName, deviceType }
        DESCRIPTION
            "An SMPP transmitter between Application and TextPass has been
            released"
        ::= 4

    applicationOutsideSmppTransceiverStarted TRAP-TYPE
        ENTERPRISE apc
        VARIABLES { applicationOutsideSmppTransceiversCounter, applicationName, deviceType }
        DESCRIPTION
            "Application established a new SMPP transceiver with TextPass"
        ::= 5

    applicationOutsideSmppTransceiverStopped TRAP-TYPE
        ENTERPRISE apc
        VARIABLES { applicationOutsideSmppTransceiversCounter, applicationName, deviceType }
        DESCRIPTION
            "An SMPP transceiver between Application and TextPass has been
            released"
        ::= 6

    applicationOutsideUcpSessionStarted TRAP-TYPE
        ENTERPRISE apc
        VARIABLES { applicationOutsideUcpSessionsCounter, applicationName, deviceType }
        DESCRIPTION
            "Application established a new UCP session with TextPass"
        ::= 7

    applicationOutsideUcpSessionStopped TRAP-TYPE
        ENTERPRISE apc
        VARIABLES { applicationOutsideUcpSessionsCounter, applicationName, deviceType }
        DESCRIPTION
            "A UCP session between Application and TextPass has been released"
        ::= 8

    applicationOutsideCimdSessionStarted TRAP-TYPE
        ENTERPRISE apc
        VARIABLES { applicationOutsideCimdSessionsCounter, applicationName, deviceType }
        DESCRIPTION
            "Application established a new CIMD session with TextPass"
        ::= 9

    applicationOutsideCimdSessionStopped TRAP-TYPE
        ENTERPRISE apc
        VARIABLES { applicationOutsideCimdSessionsCounter, applicationName, deviceType }
        DESCRIPTION
            "A CIMD session between Application and TextPass has been
            released"
        ::= 10

    applicationInsideSmppReceiverStarted TRAP-TYPE
        ENTERPRISE apc
        VARIABLES { applicationInsideSmppReceiversCounter, applicationName, deviceType }
        DESCRIPTION
            "TextPass established a new SMPP receiver with ScTerminationPoint"
        ::= 11

    applicationInsideSmppReceiverStopped TRAP-TYPE
        ENTERPRISE apc
        VARIABLES { applicationInsideSmppReceiversCounter, applicationName, deviceType }
        DESCRIPTION
            "An SMPP receiver between TextPass and ScTerminationPoint has
            been released"
        ::= 12

    applicationInsideSmppTransmitterStarted TRAP-TYPE
        ENTERPRISE apc
        VARIABLES { applicationInsideSmppTransmittersCounter, applicationName, deviceType }
        DESCRIPTION
            "TextPass established a new SMPP transmitter with
            ScTerminationPoint"
        ::= 13

    applicationInsideSmppTransmitterStopped TRAP-TYPE
        ENTERPRISE apc
        VARIABLES { applicationInsideSmppTransmittersCounter, applicationName, deviceType }
        DESCRIPTION
            "An SMPP transmitter between TextPass and ScTerminationPoint has
            been released"
        ::= 14

    applicationInsideSmppTransceiverStarted TRAP-TYPE
        ENTERPRISE apc
        VARIABLES { applicationInsideSmppTransceiversCounter, applicationName, deviceType }
        DESCRIPTION
            "TextPass established a new SMPP transceiver with
            ScTerminationPoint"
        ::= 15

    applicationInsideSmppTransceiverStopped TRAP-TYPE
        ENTERPRISE apc
        VARIABLES { applicationInsideSmppTransceiversCounter, applicationName, deviceType }
        DESCRIPTION
            "An SMPP transceiver between TextPass and ScTerminationPoint has
            been released"
        ::= 16

    applicationInsideUcpSessionStarted TRAP-TYPE
        ENTERPRISE apc
        VARIABLES { applicationInsideUcpSessionsCounter, applicationName, deviceType }
        DESCRIPTION
            "TextPass established a new UCP session with ScTerminationPoint"
        ::= 17

    applicationInsideUcpSessionStopped TRAP-TYPE
        ENTERPRISE apc
        VARIABLES { applicationInsideUcpSessionsCounter, applicationName, deviceType }
        DESCRIPTION
            "A UCP session between TextPass and ScTerminationPoint has been
            released"
        ::= 18

    applicationInsideCimdSessionStarted TRAP-TYPE
        ENTERPRISE apc
        VARIABLES { applicationInsideCimdSessionsCounter, applicationName, deviceType }
        DESCRIPTION
            "TextPass established a new CIMD session with ScTerminationPoint"
        ::= 19

    applicationInsideCimdSessionStopped TRAP-TYPE
        ENTERPRISE apc
        VARIABLES { applicationOutsideCimdSessionsCounter, applicationName, deviceType }
        DESCRIPTION
            "A CIMD session between TextPass and ScTerminationPoint has been
            released"
        ::= 20

    scTerminationPointSessionStarted TRAP-TYPE
        ENTERPRISE apc
        VARIABLES { scTerminationPointSessionsCounter, scTerminationPointName, scTerminationPointProtocol, deviceType }
        DESCRIPTION
            "TextPass established a new session with ScTerminationPoint"
        ::= 21

    scTerminationPointSessionStopped TRAP-TYPE
        ENTERPRISE apc
        VARIABLES { scTerminationPointSessionsCounter, scTerminationPointName, scTerminationPointProtocol, deviceType}
        DESCRIPTION
            "A session between TextPass and ScTerminationPoint has been
            released"
        ::= 22

    scNodeSessionStarted TRAP-TYPE
        ENTERPRISE apc
        VARIABLES { scNodeSessionsCounter, scNodeName, deviceType}
        DESCRIPTION
            "TextPass established a new session with ScNode"
        ::= 23

    scNodeSessionStopped TRAP-TYPE
        ENTERPRISE apc
        VARIABLES { scNodeSessionsCounter, scNodeName, deviceType}
        DESCRIPTION
            "A session between TextPass and ScNode has been released"
        ::= 24

    serviceCentreSessionStarted TRAP-TYPE
        ENTERPRISE apc
        VARIABLES { serviceCentreSessionsCounter, serviceCentreName, deviceType}
        DESCRIPTION
            "TextPass established a new session with ServiceCentre"
        ::= 25

    serviceCentreSessionStopped TRAP-TYPE
        ENTERPRISE apc
        VARIABLES { serviceCentreSessionsCounter, serviceCentreName, deviceType}
        DESCRIPTION
            "A session between TextPass and ServiceCentre has been released"
        ::= 26

    scTerminationPointOperationalStateChanged TRAP-TYPE
        ENTERPRISE apc
        VARIABLES { scTerminationPointOperationalState, scTerminationPointName, deviceType }
        DESCRIPTION
            "Operational state of a ScTerminationPoint has changed"
        ::= 31

    scNodeOperationalStateChanged TRAP-TYPE
        ENTERPRISE apc
        VARIABLES { scNodeOperationalState, scNodeName, deviceType }
        DESCRIPTION
            "Operational state of a ScNode has changed"
        ::= 32

    serviceCentreOperationalStateChanged TRAP-TYPE
        ENTERPRISE apc
        VARIABLES { serviceCentreOperationalState, serviceCentreName, deviceType }
        DESCRIPTION
            "Operational state of a ServiceCentre has changed"
        ::= 33

    applicationOperationalStateChanged TRAP-TYPE
        ENTERPRISE apc
        VARIABLES { applicationOperationalState, applicationName, deviceType }
        DESCRIPTION
            "Operational state of an Application has changed"
        ::= 34

    applicationOutsideCapacityUsageAoGrowing TRAP-TYPE
        ENTERPRISE apc
        VARIABLES { applicationOutsideCapacityUsageAo, applicationName, deviceType }
        DESCRIPTION
            "Rate between actual number of pending submit transactions from
            the Application and the maximum is growing and just hit a
            threshold."
        ::= 41

    applicationOutsideCapacityUsageAoShrinking TRAP-TYPE
        ENTERPRISE apc
        VARIABLES { applicationOutsideCapacityUsageAo, applicationName, deviceType }
        DESCRIPTION
            "Rate between actual number of pending submit transactions from
            the Application and the maximum is shrinking and just hit a
            threshold."
        ::= 42

    applicationOutsideCapacityUsageAtGrowing TRAP-TYPE
        ENTERPRISE apc
        VARIABLES { applicationOutsideCapacityUsageAt, applicationName, deviceType }
        DESCRIPTION
            "Rate between actual number of pending delivery transactions
            towards the Application and the maximum is growing and just hit a
            threshold."
        ::= 43

    applicationOutsideCapacityUsageAtShrinking TRAP-TYPE
        ENTERPRISE apc
        VARIABLES { applicationOutsideCapacityUsageAt, applicationName, deviceType }
        DESCRIPTION
            "Rate between actual number of pending delivery transactions
            towards the Application and the maximum is shrinking and just hit
            a threshold."
        ::= 44

    applicationInsideCapacityUsageAoGrowing TRAP-TYPE
        ENTERPRISE apc
        VARIABLES { applicationInsideCapacityUsageAo, applicationName, deviceType }
        DESCRIPTION
            "Rate between actual number of pending submit transactions
            towards the ScTerminationPoint and the maximum is growing and
            just hit a threshold."
        ::= 45

    applicationInsideCapacityUsageAoShrinking TRAP-TYPE
        ENTERPRISE apc
        VARIABLES { applicationInsideCapacityUsageAo, applicationName, deviceType }
        DESCRIPTION
            "Rate between actual number of pending submit transactions
            towards the ScTerminationPoint and the maximum is shrinking and
            just hit a threshold."
        ::= 46

    applicationInsideCapacityUsageAtGrowing TRAP-TYPE
        ENTERPRISE apc
        VARIABLES { applicationInsideCapacityUsageAt, applicationName, deviceType }
        DESCRIPTION
            "Rate between actual number of pending delivery transactions from
            the ScTerminationPoint and the maximum is growing and just hit a
            threshold."
        ::= 47

    applicationInsideCapacityUsageAtShrinking TRAP-TYPE
        ENTERPRISE apc
        VARIABLES { applicationInsideCapacityUsageAt, applicationName, deviceType }
        DESCRIPTION
            "Rate between actual number of pending delivery transactions from
            the ScTerminationPoint and the maximum is shrinking and just hit
            a threshold."
        ::= 48

    applicationIncorrectOutsideSmppPassword TRAP-TYPE
        ENTERPRISE apc
        VARIABLES { applicationName, deviceType }
        DESCRIPTION
            "An Application used an incorrect SMPP password to identify
            himself. This trap is sent on every occurence."
        ::= 51

    applicationIncorrectOutsideUcpPassword TRAP-TYPE
        ENTERPRISE apc
        VARIABLES { applicationName, deviceType }
        DESCRIPTION
            "An Application used an incorrect UCP password to identify
            himself. This trap is sent on every occurence."
        ::= 52

    applicationIncorrectOutsideCimdPassword TRAP-TYPE
        ENTERPRISE apc
        VARIABLES { applicationName, deviceType }
        DESCRIPTION
            "An Application used an incorrect CIMD password to identify
            himself. This trap is sent on every occurence."
        ::= 53

    applicationCorrectOutsideSmppPassword TRAP-TYPE
        ENTERPRISE apc
        VARIABLES { applicationName, deviceType }
        DESCRIPTION
            "An Application used a correct SMPP password to identify
            himself. This is trap is only sent if an 
            applicationIncorrectOutsideSmppPassword for this Application
            was pending."
        ::= 54

    applicationCorrectOutsideUcpPassword TRAP-TYPE
        ENTERPRISE apc
        VARIABLES { applicationName, deviceType }
        DESCRIPTION
            "An Application used a correct UCP password to identify
            himself. This is trap is only sent if an 
            applicationIncorrectOutsideUcpPassword for this Application
            was pending."
        ::= 55

    applicationCorrectOutsideCimdPassword TRAP-TYPE
        ENTERPRISE apc
        VARIABLES { applicationName, deviceType }
        DESCRIPTION
            "An Application used a correct CIMD password to identify
            himself. This is trap is only sent if an 
            applicationIncorrectOutsideCimdPassword for this Application
            was pending."
        ::= 56

    applicationInsideSmppLoginRefused TRAP-TYPE
        ENTERPRISE apc
        VARIABLES { applicationName, serviceCentreName, deviceType }
        DESCRIPTION
            "The TextPass could not login the SMPP Application at the
            Service Centre. This trap is sent on every occurence."
        ::= 61

    applicationInsideUcpLoginRefused TRAP-TYPE
        ENTERPRISE apc
        VARIABLES { applicationName, serviceCentreName, deviceType }
        DESCRIPTION
            "The TextPass could not login the UCP Application at the
            Service Centre. This trap is sent on every occurence."
        ::= 62

    applicationInsideCimdLoginRefused TRAP-TYPE
        ENTERPRISE apc
        VARIABLES { applicationName, serviceCentreName, deviceType }
        DESCRIPTION
            "The TextPass could not login the CIMD Application at the
            Service Centre. This trap is sent on every occurence."
        ::= 63

    applicationInsideSmppLoginSucceeded TRAP-TYPE
        ENTERPRISE apc
        VARIABLES { applicationName, serviceCentreName, deviceType }
        DESCRIPTION
            "The TextPass succeeded to login the SMPP Application at the
            Service Centre. This is trap is only sent if an 
            applicationInsideSmppLoginRefused for this Application and
            Service Centre was pending."
        ::= 64

    applicationInsideUcpLoginSucceeded TRAP-TYPE
        ENTERPRISE apc
        VARIABLES { applicationName, serviceCentreName, deviceType }
        DESCRIPTION
            "The TextPass succeeded to login the UCP Application at the
            Service Centre. This is trap is only sent if an 
            applicationInsideUcpLoginRefused for this Application and
            Service Centre was pending."
        ::= 65

    applicationInsideCimdLoginSucceeded TRAP-TYPE
        ENTERPRISE apc
        VARIABLES { applicationName, serviceCentreName, deviceType }
        DESCRIPTION
            "The TextPass succeeded to login the CIMD Application at the
            Service Centre. This is trap is only sent if an 
            applicationInsideCimdLoginRefused for this Application and
            Service Centre was pending."
        ::= 66

    applicationLearned TRAP-TYPE
        ENTERPRISE apc
        VARIABLES { applicationName, deviceType }
        DESCRIPTION
            "A new Application is added dynamically (Learning)."
        ::= 71

 
    applicationInsideUcpMinimumSessionsNotReached TRAP-TYPE
        ENTERPRISE apc
        VARIABLES {applicationName, applicationInsideUcpSessionsCounter, deviceType }
        DESCRIPTION
            "Number of inside UCP sessions is below the configured 
             applicationInsideMinimumSessionsThreshold value."
        ::= 80

    applicationInsideUcpMinimumSessionsReached TRAP-TYPE
        ENTERPRISE apc
        VARIABLES {applicationName, applicationInsideUcpSessionsCounter, deviceType }
        DESCRIPTION
            "Number of inside UCP sessions is no longer below the configured
             applicationInsideMinimumSessionsThreshold value."
        ::= 81

    applicationOutsideUcpMinimumSessionsNotReached TRAP-TYPE
        ENTERPRISE apc
        VARIABLES { applicationName, applicationOutsideUcpSessionsCounter,  deviceType }
        DESCRIPTION
            "Number of outside UCP sessions is below the configured 
             applicationOutsideMinimumSessionsThreshold value."
        ::= 82

    applicationOutsideUcpMinimumSessionsReached TRAP-TYPE
        ENTERPRISE apc
        VARIABLES {applicationName, applicationOutsideUcpSessionsCounter,  deviceType }
        DESCRIPTION
            "Number of outside UCP sessions is no longer below the configured
             applicationOutsideMinimumSessionsThreshold value."
        ::= 83

    applicationInsideCimdMinimumSessionsNotReached TRAP-TYPE
        ENTERPRISE apc
        VARIABLES {applicationName, applicationInsideCimdSessionsCounter, deviceType }
        DESCRIPTION
            "Number of inside CIMD sessions is below the configured 
             applicationInsideMinimumSessionsThreshold value."
        ::= 84

    applicationInsideCimdMinimumSessionsReached TRAP-TYPE
        ENTERPRISE apc
        VARIABLES {applicationName, applicationInsideCimdSessionsCounter, deviceType }
        DESCRIPTION
            "Number of inside CIMD sessions is no longer below the configured
             applicationInsideMinimumSessionsThreshold value."
        ::= 85

    applicationOutsideCimdMinimumSessionsNotReached TRAP-TYPE
        ENTERPRISE apc
        VARIABLES { applicationName, applicationOutsideCimdSessionsCounter,  deviceType }
        DESCRIPTION
            "Number of outside CIMD sessions is below the configured 
             applicationOutsideMinimumSessionsThreshold value."
        ::= 86

    applicationOutsideCimdMinimumSessionsReached TRAP-TYPE
        ENTERPRISE apc
        VARIABLES {applicationName, applicationOutsideCimdSessionsCounter,  deviceType }
        DESCRIPTION
            "Number of outside CIMD sessions is no longer below the 
             configured applicationOutsideMinimumSessionsThreshold value."
        ::= 87
     
    applicationInsideSmppRxMinimumSessionsNotReached TRAP-TYPE
        ENTERPRISE apc
        VARIABLES {applicationName, applicationInsideSmppReceiversCounter, deviceType }
        DESCRIPTION
            "Number of inside SMPP receiver sessions is below the 
             configured applicationInsideMinimumSessionsThreshold value."
        ::= 88

    applicationInsideSmppRxMinimumSessionsReached TRAP-TYPE
        ENTERPRISE apc
        VARIABLES {applicationName, applicationInsideSmppReceiversCounter, deviceType }
        DESCRIPTION
            "Number of inside SMPP receiver sessions is no longer below the
             configured applicationInsideMinimumSessionsThreshold value."
        ::= 89

    applicationOutsideSmppRxMinimumSessionsNotReached TRAP-TYPE
        ENTERPRISE apc
        VARIABLES { applicationName, applicationOutsideSmppReceiversCounter,  deviceType }
        DESCRIPTION
            "Number of outside SMPP receiver sessions is below the 
             configured applicationOutsideMinimumSessionsThreshold value."
        ::= 90

    applicationOutsideSmppRxMinimumSessionsReached TRAP-TYPE
        ENTERPRISE apc
        VARIABLES {applicationName, applicationOutsideSmppReceiversCounter,  deviceType }
        DESCRIPTION
            "Number of outside SMPP receiver sessions is no longer below the 
             configured applicationOutsideMinimumSessionsThreshold value."
        ::= 91

    applicationInsideSmppTxMinimumSessionsNotReached TRAP-TYPE
        ENTERPRISE apc
        VARIABLES {applicationName, applicationInsideSmppTransmittersCounter, deviceType }
        DESCRIPTION
            "Number of inside SMPP transmitter sessions is below the
             configured applicationInsideMinimumSessionsThreshold value."
        ::= 92

    applicationInsideSmppTxMinimumSessionsReached TRAP-TYPE
        ENTERPRISE apc
        VARIABLES {applicationName, applicationInsideSmppTransmittersCounter, deviceType }
        DESCRIPTION
            "Number of inside SMPP transmitter sessions is no longer below
             the configured applicationInsideMinimumSessionsThreshold value."
        ::= 93

    applicationOutsideSmppTxMinimumSessionsNotReached TRAP-TYPE
        ENTERPRISE apc
        VARIABLES { applicationName, applicationOutsideSmppTransmittersCounter,  deviceType }
        DESCRIPTION
            "Number of outside SMPP transmitter sessions is below the
             configured applicationOutsideMinimumSessionsThreshold value."
        ::= 94

    applicationOutsideSmppTxMinimumSessionsReached TRAP-TYPE
        ENTERPRISE apc
        VARIABLES {applicationName, applicationOutsideSmppTransmittersCounter,  deviceType }
        DESCRIPTION
            "Number of outside SMPP transmitter sessions is no longer 
             below the configured applicationOutsideMinimumSessionsThreshold
             value."
        ::= 95

    applicationInsideSmppTrxMinimumSessionsNotReached TRAP-TYPE
        ENTERPRISE apc
        VARIABLES {applicationName, applicationInsideSmppTransceiversCounter, deviceType }
        DESCRIPTION
            "Number of inside SMPP transceiver sessions is below the 
             configured applicationInsideMinimumSessionsThreshold value."
        ::= 96

    applicationInsideSmppTrxMinimumSessionsReached TRAP-TYPE
        ENTERPRISE apc
        VARIABLES {applicationName, applicationInsideSmppTransceiversCounter, deviceType }
        DESCRIPTION
            "Number of inside SMPP transceiver sessions is no longer below the 
             configured applicationInsideMinimumSessionsThreshold value."
        ::= 97

    applicationOutsideSmppTrxMinimumSessionsNotReached TRAP-TYPE
        ENTERPRISE apc
        VARIABLES { applicationName, applicationOutsideSmppTransceiversCounter,  deviceType }
        DESCRIPTION
            "Number of outside SMPP transceiver sessions is below the 
             configured applicationOutsideMinimumSessionsThreshold value."
        ::= 98

    applicationOutsideSmppTrxMinimumSessionsReached TRAP-TYPE
        ENTERPRISE apc
        VARIABLES {applicationName, applicationOutsideSmppTransceiversCounter,  deviceType }
        DESCRIPTION
            "Number of outside SMPP transceiver sessions is no longer 
             below the configured applicationOutsideMinimumSessionsThreshold
             value."
        ::= 99

END

-------------------------------------------------------------------------------
-- Release Date: <2006/01/26 10:50:30>
--    Version  : Ver.1.10 (Reference NEO Compact MIB ;Ver.1.10)
-- Release Date: <2007/8/2 10:50:30>
--    Version  : Ver.1.20 (Reference NEO Compact MIB ;Ver.1.62)
-- Release Date: <2007/8/7 09:59:30>
--    Version  : Ver.1.30 (Reference NEO Compact MIB ;Ver.1.62)
-- Release Date: <2007/8/7 19:27:30>
--    Version  : Ver.1.31 (Reference NEO Compact MIB ;Ver.1.62)
-- Release Date: <2007/8/23 17:05:30>
--    Version  : Ver.140 (Reference NEO Compact MIB ;Ver.1.62)
-- Release Date: <2007/8/24 11:15:30>
--    Version  : Ver.141 (Reference NEO Compact MIB ;Ver.1.62)
-- Release Date: <2007/11/19 16:15:30>
--    Version  : Ver.142 (Reference NEO Compact MIB ;Ver.1.64)
-- Release Date: <2007/12/12 18:56:30>
--    Version  : Ver.143 (Reference NEO Compact MIB ;Ver.1.64)
-------------------------------------------------------------------------------


MIB-PNMSJ-PASOLINK-NEO-CPV DEFINITIONS ::= BEGIN

-----------------------------------------------
-- INPORTS Definitions
-----------------------------------------------

	IMPORTS
		enterprises,IpAddress,Counter,TimeTicks
			FROM RFC1155-SMI
		DisplayString
			FROM RFC1213-MIB
		OBJECT-TYPE
			FROM RFC-1212
		TEXTUAL-CONVENTION
			FROM SNMPv2-TC
		TRAP-TYPE
			FROM RFC-1215
		pnms
			FROM NEC-SMI;
			
-----------------------------------------------
-- Begin User MIB Object Definitions
-----------------------------------------------

	DATE32	::= TEXTUAL-CONVENTION
		STATUS		current
		DESCRIPTION	"Date Type (32Bit)"
		SYNTAX		INTEGER

	TIME32	::= TEXTUAL-CONVENTION
		STATUS		current
		DESCRIPTION	"Time Type (32Bit)"
		SYNTAX		INTEGER

	DateAndTime	::= TEXTUAL-CONVENTION
		STATUS		current
		DESCRIPTION	"Date and Time Type "
		SYNTAX		OCTET STRING ( SIZE (8) )
					

	SeverityValue	::= TEXTUAL-CONVENTION
		STATUS		current
		DESCRIPTION	"Severity (CCITT Rec. X.733)
					  0:invalid
					  1:clear,
					  2:minor
					  3:major,
					  4:critical
					"
		SYNTAX		INTEGER (0..4)

	AlarmTypeValue	::= TEXTUAL-CONVENTION
		STATUS		current
		DESCRIPTION	"Alaem Type (CCITT Rec. X.733)
					  0:invalid,
					  1:communicationAlarm,
					  2:qualityOfServiceAlarm,
					  3:processingErrorAlarm,
					  4:equipmentAlarm,
					  5:environmentalAlarm,
					  6:integrityViolationAlarm,
					  7:operationalViolationAlarm,
					  8:physicalViolationAlarm,
					  9:securityViolationAlarm,
					  10:timeDomainViolationAlarm
					"
		SYNTAX		INTEGER (0..10)

	ProbableCauseValue	::= TEXTUAL-CONVENTION
		STATUS		current
		DESCRIPTION	"Probable Cause (CCITT Rec. X.733)
					  0:invalid,
					  1:aIS,
					  2:callSetUpFailure,
					  3:degradedSignal,
					  4:farEndReceiverFailure,
					  5:framingError,
					  6:lossOfFrame,
					  7:lossOfPointer,
					  8:lossOfSignal,
					  9:payloadTypeMismatch,
					  10:transmissionError,
					  11:remoteAlarmInterface,
					  12:excessiveBER,
					  13:pathTraceMismatch,
					  51:backplaneFailure,
					  52:dataSetProblem,
					  53:equipmentIdentifierDuplication,
					  54:externalIFDeviceProblem,
					  55:lineCardProblem,
					  56:multiplexerProblem,
					  57:nEIdentifierDuplication,
					  58:powerProblem,
					  59:processorProblem,
					  60:protectionPathFailure,
					  61:receiverFailure,
					  62:replaceableUnitMissing,
					  63:replaceableUnitTypeMismatch,
					  64:synchronizationSourceMismatch,
					  65:terminalProblem,
					  66:timingProblem,
					  67:transmitterFailure,
					  68:trunkCardProblem,
					  69:replaceableUnitProblem,
					  101:airCompressorFailure,
					  102:airConditioningFailure,
					  103:airDryerFailure,
					  104:batteryDischarging,
					  105:batteryFailure,
					  106:commercialPowerFailure,
					  107:coolingFanFailure,
					  108:engineFailure,
					  109:fireDetectorFailure,
					  110:fuseFailure,
					  111:generatorFailure,
					  112:lowBatteryThreshold,
					  113:pumpFailure,
					  114:rectifierFailure,
					  115:rectifierHighVoltage,
					  116:rectifierLowFVoltage,
					  117:ventilationsSystemFailure,
					  118:enclosureDoorOpen,
					  119:explosiveGas,
					  120:fire,
					  121:flood,
					  122:highHumidity,
					  123:highTemperature,
					  124:highWind,
					  125:iceBuildUp,
					  126:intrusionDetection,
					  127:lowFuel,
					  128:lowHumidity,
					  129:lowCablePressure,
					  130:lowTemperature,
					  131:lowWater,
					  132:smoke,
					  133:toxicGas,
					  151:storageCapacityProblem,
					  152:memoryMismatch,
					  153:corruptData,
					  154:outOfCPUCycles,
					  155:sfwrEnvironmentProblem,
					  156:sfwrDownloadFailure,
					  157:communicationsProtocolError,
					  158:congestion,
					  159:heatingOrVentilationOrCoolingSystemProblem,
					  160:lANError,
					  161:performanceDegraded,
					  162:temperatureUnacceptable,
					  163:thresholdCrossed,
					  164:underlyingResourceUnavailable,
					  165:equipmentMalfunction,
					  166:configurationOrCustomizationError,
					  501:duplicateInformation,
					  502:informationMissing,
					  503:informationModificationDetected,
					  504:informationOutOfSequence,
					  505:unexpectedInformation,
					  506:denialOfService,
					  507:outOfService,
					  508:proceduralError,
					  509:cableTamper,
					  510:securityIntrusionDetection,
					  511:authenticationFailure,
					  512:breachOfConfidentiality,
					  513:unauthorisedAccessAttempt,
					  514:delayedInformation,
					  515:keyExpired,
					  516:outOfHoursActivity,
					  517:otherReasons,
					  518:bossHardwareFailure,
					  519:bossSystemSoftwareFailure,
					  520:bossApplicationSoftwareFailure,
					  521:bossDatabaseFailure,
					  522:bossNetworkFailure
					"
		SYNTAX		INTEGER (0..522)

	NormalAlarmValue	::= TEXTUAL-CONVENTION
		STATUS		current
		DESCRIPTION	"Normal/Alarm Type
					  0:Invalid,
					  1:Normal,
					  2:Alarm
					"
		SYNTAX		INTEGER (0..2)

	OffOnValue	::= TEXTUAL-CONVENTION
		STATUS		current
		DESCRIPTION	"Off/On Type
					  0:Invalid,
					  1:Off,
					  2:On
					"
		SYNTAX		INTEGER (0..2)

	NormalSendValue	::= TEXTUAL-CONVENTION
		STATUS		current
		DESCRIPTION	"Normal/Send Type
					  0:Invalid,
					  1:Normal,
					  2:Send
					"
		SYNTAX		INTEGER (0..2)

	NormalRcvdValue	::= TEXTUAL-CONVENTION
		STATUS		current
		DESCRIPTION	"Normal/Rcvd Type
					  0:Invalid,
					  1:Normal,
					  2:Rcvd
					"
		SYNTAX		INTEGER (0..2)

	ConnectDisconnectValue	::= TEXTUAL-CONVENTION
		STATUS		current
		DESCRIPTION	"Connect/Disconnect Type
					  Invalid(0),
					  Disconnect(1),
					  Connect(2)
					"
		SYNTAX		INTEGER (0..2)


-----------------------------------------------
-- enterprises Group Definitions
-----------------------------------------------

	pasolinkNeoCpv OBJECT IDENTIFIER
		::= { pnms 116 }

        pasolinkNeoCpvSystem OBJECT IDENTIFIER
		::= { pasolinkNeoCpv 1 }

	pasolinkNeoCpvInformation OBJECT IDENTIFIER
		::= { pasolinkNeoCpv 2 }


-----------------------------------------------
-- system3 Group Definitions
-----------------------------------------------

	pnSystem OBJECT IDENTIFIER
		::= { pasolinkNeoCpvSystem 1 }

	pnConfiguration OBJECT IDENTIFIER
		::= { pasolinkNeoCpvSystem 2 }

	pnSys3Trap OBJECT IDENTIFIER
		::= { pasolinkNeoCpvSystem 3 }


-----------------------------------------------
-- pnSystem Group Definitions
-----------------------------------------------

	pnSystemInfo OBJECT IDENTIFIER
		::= { pnSystem 1 }

        pnSystemEquipmentConfigTable OBJECT-TYPE
		SYNTAX		SEQUENCE OF PnSystemEquipmentConfigEntry
		ACCESS		not-accessible
		STATUS		mandatory
		DESCRIPTION	"Equipment Config"
		::= { pnSystemInfo 1 }

	pnSystemEquipmentConfigEntry OBJECT-TYPE
		SYNTAX		PnSystemEquipmentConfigEntry
		ACCESS		not-accessible
		STATUS		mandatory
		DESCRIPTION	"Equipment Config Entry"
		INDEX		{
					pnSysPasoIndex
					}
		::= { pnSystemEquipmentConfigTable 1 }

	PnSystemEquipmentConfigEntry ::= SEQUENCE {
		pnSysPasoIndex		IpAddress,
		pnSysEquipmentConfig        INTEGER
	}

	pnSysPasoIndex OBJECT-TYPE
		SYNTAX		IpAddress 
		ACCESS		read-only
		STATUS		mandatory
		DESCRIPTION	"Pasolink IP Address index"
		::= { pnSystemEquipmentConfigEntry 1 }

	pnSysEquipmentConfig OBJECT-TYPE
		SYNTAX		INTEGER (0..12)
		ACCESS		read-only
		STATUS		mandatory
		DESCRIPTION	"Equipment Config
					  0:Invalid,
					  1:1+0,
					  2:1+1,  --Not used
					  3:1+1 HS,
					  4:1+1 TP,
					  5:1+0->1+1,  --Not used
					  7:1+0(4*2M),  -- Not used
					  8:1+0(20*2M),  -- Not used
					  20:1+0 FIX
					"
		::= { pnSystemEquipmentConfigEntry 2 }


-----------------------------------------------
-- pnConfiguration Group Definitions
-----------------------------------------------

	pnCfgAux OBJECT IDENTIFIER
		::= { pnConfiguration 1 }

	pnCfgAuxInTable OBJECT-TYPE
		SYNTAX		SEQUENCE OF PnCfgAuxInEntry
		ACCESS		not-accessible
		STATUS		mandatory
		DESCRIPTION	"Aux Input Table"
		::= { pnCfgAux 1 }

	pnCfgAuxInEntry OBJECT-TYPE
		SYNTAX		PnCfgAuxInEntry
		ACCESS		not-accessible
		STATUS		mandatory
		INDEX		{
                                                pnCfgAuxInPasoIndex,
						pnCfgAuxInIndex
					}
		::= { pnCfgAuxInTable 1 }

	PnCfgAuxInEntry ::= SEQUENCE {
                                          pnCfgAuxInPasoIndex	   IpAddress,	
					  pnCfgAuxInIndex          INTEGER,
					  pnCfgAuxInItemName       DisplayString,
					  pnCfgAuxInItemType       INTEGER,
					  pnCfgAuxInOpenState      DisplayString,
					  pnCfgAuxInCloseState     DisplayString,
					  pnCfgAuxInSeverity       SeverityValue,
					  pnCfgAuxInAlarmType      AlarmTypeValue,
					  pnCfgAuxInProbableCause  ProbableCauseValue
					}

	pnCfgAuxInPasoIndex OBJECT-TYPE
		SYNTAX		IpAddress 
		ACCESS		read-only
		STATUS		mandatory
		DESCRIPTION	"Pasolink IP Address index"
		::= { pnCfgAuxInEntry 1 }

	pnCfgAuxInIndex OBJECT-TYPE
		SYNTAX		INTEGER (1..6)
		ACCESS		read-only
		STATUS		mandatory
		DESCRIPTION	"AUX Input Index"
		::= { pnCfgAuxInEntry 2 }

	pnCfgAuxInItemName OBJECT-TYPE
		SYNTAX		DisplayString (SIZE (0..32))
		ACCESS		read-only
		STATUS		mandatory
		DESCRIPTION	"AUX Input name.
					TRAP=configTrapPnSys3AuxInItemName"
		::= { pnCfgAuxInEntry 3 }

	pnCfgAuxInItemType OBJECT-TYPE
		SYNTAX		INTEGER (0..3)
		ACCESS		read-only
		STATUS		mandatory
		DESCRIPTION	"Configuration for AUX Input.
					  0:Invalid
					  1:Alarm with Open loop,
					  2:Alarm with Close loop,
					  3:Status
					
					TRAP=configTrapPnSys3AuxInItemType"
		::= { pnCfgAuxInEntry 4 }

	pnCfgAuxInOpenState OBJECT-TYPE
		SYNTAX		DisplayString (SIZE (0..32))
		ACCESS		read-only
		STATUS		mandatory
		DESCRIPTION	"Name when AUX Input is open status
					TRAP=configTrapPnSys3AuxInOpenState"
		::= { pnCfgAuxInEntry 5 }

	pnCfgAuxInCloseState OBJECT-TYPE
		SYNTAX		DisplayString (SIZE (0..32))
		ACCESS		read-only
		STATUS		mandatory
		DESCRIPTION	"Name when AUX Input is close status
					TRAP=configTrapPnSys3AuxInCloseState"
		::= { pnCfgAuxInEntry 6 }

	pnCfgAuxInSeverity OBJECT-TYPE
		SYNTAX		SeverityValue
		ACCESS		read-only
		STATUS		mandatory
		DESCRIPTION	"Sevirity when AUX Input is alarm.
					TRAP=configTrapPnSys3AuxInSeverity"
		::= { pnCfgAuxInEntry 7 }

	pnCfgAuxInAlarmType OBJECT-TYPE
		SYNTAX		AlarmTypeValue
		ACCESS		read-only
		STATUS		mandatory
		DESCRIPTION	"Alarm Type when AUX Input is alarm.
					TRAP=configTrapPnSys3AuxInAlarmType"
		::= { pnCfgAuxInEntry 8 }

	pnCfgAuxInProbableCause OBJECT-TYPE
		SYNTAX		ProbableCauseValue
		ACCESS		read-only
		STATUS		mandatory
		DESCRIPTION	"ProbableCause when AUX Input is alarm.
					TRAP=configTrapPnSys3AuxInProbableCause"
		::= { pnCfgAuxInEntry 9 }

	pnCfgAuxOutTable OBJECT-TYPE
		SYNTAX		SEQUENCE OF PnCfgAuxOutEntry
		ACCESS		not-accessible
		STATUS		mandatory
		DESCRIPTION	"AUX Output Table"
		::= { pnCfgAux 2 }

	pnCfgAuxOutEntry OBJECT-TYPE
		SYNTAX		PnCfgAuxOutEntry
		ACCESS		not-accessible
		STATUS		mandatory
		INDEX		{
                                                pnCfgAuxInPasoIndex,
						pnCfgAuxOutIndex
					}
		::= { pnCfgAuxOutTable 1 }

	PnCfgAuxOutEntry ::= SEQUENCE {
                                          pnCfgAuxOutPasoIndex	 IpAddress,
					  pnCfgAuxOutIndex       INTEGER,
					  pnCfgAuxOutItemName    DisplayString,
					  pnCfgAuxOutOpenState   DisplayString,
					  pnCfgAuxOutCloseState  DisplayString
					}

	pnCfgAuxOutPasoIndex OBJECT-TYPE
		SYNTAX		IpAddress 
		ACCESS		read-only
		STATUS		mandatory
		DESCRIPTION	"Pasolink IP Address index"
		::= { pnCfgAuxOutEntry 1 }

	pnCfgAuxOutIndex OBJECT-TYPE
		SYNTAX		INTEGER (1..4)
		ACCESS		read-only
		STATUS		mandatory
		DESCRIPTION	"AUX Output Index"
		::= { pnCfgAuxOutEntry 2 }

	pnCfgAuxOutItemName OBJECT-TYPE
		SYNTAX		DisplayString (SIZE (0..32))
		ACCESS		read-only
		STATUS		mandatory
		DESCRIPTION	"AUX Input name.
					TRAP=configTrapPnSys3AuxOutItemName"
		::= { pnCfgAuxOutEntry 3 }

	pnCfgAuxOutOpenState OBJECT-TYPE
		SYNTAX		DisplayString (SIZE (0..32))
		ACCESS		read-only
		STATUS		mandatory
		DESCRIPTION	"Name when AUX Output is open status
					TRAP=configTrapPnSys3AuxOutOpenState"
		::= { pnCfgAuxOutEntry 4 }

	pnCfgAuxOutCloseState OBJECT-TYPE
		SYNTAX		DisplayString (SIZE (0..32))
		ACCESS		read-only
		STATUS		mandatory
		DESCRIPTION	"Name when AUX Output is close status
					TRAP=configTrapPnSys3AuxOutCloseState"
		::= { pnCfgAuxOutEntry 5 }


-----------------------------------------------
-- pnSys3Trap Group Definitions
-----------------------------------------------

	pnSys3TrapCommon OBJECT IDENTIFIER
		::= { pnSys3Trap 1 }

	pnSys3TrapGenericVars OBJECT IDENTIFIER
		::= { pnSys3TrapCommon 1 }

	sys3PnTrapSequenceNumber OBJECT-TYPE
		SYNTAX		Counter
		ACCESS		read-only
		STATUS		mandatory
		DESCRIPTION	"PTR=trapGroupGroup.trapSequenceNumber"
		::= { pnSys3TrapGenericVars 1 }

	sys3PnTrapDate OBJECT-TYPE
		SYNTAX		DisplayString (SIZE (0..16))
		ACCESS		read-only
		STATUS		mandatory
		DESCRIPTION	"PTR=trapGroupGroup.trapDate"
		::= { pnSys3TrapGenericVars 2 }

	sys3PnTrapTime OBJECT-TYPE
		SYNTAX		DisplayString (SIZE (0..16))
		ACCESS		read-only
		STATUS		mandatory
		DESCRIPTION	"PTR=trapGroupGroup.trapTime"
		::= { pnSys3TrapGenericVars 3 }

	sys3PnTrapSource OBJECT-TYPE
		SYNTAX		OBJECT IDENTIFIER
		ACCESS		read-only
		STATUS		mandatory
		DESCRIPTION	"PTR=trapGroupGroup.trapSource"
		::= { pnSys3TrapGenericVars 4 }

	pnSys3TrapItemVar OBJECT IDENTIFIER
		::= { pnSys3Trap 2 }

	pnSys3ConfigTrapItemVar OBJECT IDENTIFIER
		::= { pnSys3TrapItemVar 1 }

	configItemPnSys3AuxInItemName OBJECT-TYPE
		SYNTAX		DisplayString (SIZE (0..32))
		ACCESS		read-only
		STATUS		mandatory
		DESCRIPTION	"AUX Input name."
		::= { pnSys3ConfigTrapItemVar 4 }

	configItemPnSys3AuxInItemType OBJECT-TYPE
		SYNTAX		INTEGER (0..3)
		ACCESS		read-only
		STATUS		mandatory
		DESCRIPTION	"Configuration for AUX Input.
					  0:Invalid
					  1:Alarm In Open state
					  2:Alarm In Close state
					  3:Status
					FLAG=SUMMARY_AUX"
		::= { pnSys3ConfigTrapItemVar 5 }

	configItemPnSys3AuxInOpenState OBJECT-TYPE
		SYNTAX		DisplayString (SIZE (0..32))
		ACCESS		read-only
		STATUS		mandatory
		DESCRIPTION	"Name of AUX input used in open state."
		::= { pnSys3ConfigTrapItemVar 6 }

	configItemPnSys3AuxInCloseState OBJECT-TYPE
		SYNTAX		DisplayString (SIZE (0..32))
		ACCESS		read-only
		STATUS		mandatory
		DESCRIPTION	"Name of AUX input used in close state."
		::= { pnSys3ConfigTrapItemVar 7 }

	configItemPnSys3AuxInSeverity OBJECT-TYPE
		SYNTAX		SeverityValue
		ACCESS		read-only
		STATUS		mandatory
		DESCRIPTION	"Severity when AUX Input is alarm.
				  Refer to SeverityValue of TEXTUAL-CONVENTION
					FLAG=SUMMARY_AUX"
		::= { pnSys3ConfigTrapItemVar 8 }

	configItemPnSys3AuxInAlarmType OBJECT-TYPE
		SYNTAX		AlarmTypeValue
		ACCESS		read-only
		STATUS		mandatory
		DESCRIPTION	"Alarm Type when AUX Input is alarm.
				  Refer to AlarmTypeValue of TEXTUAL-CONVENTION"
		::= { pnSys3ConfigTrapItemVar 9 }

	configItemPnSys3AuxInProbableCause OBJECT-TYPE
		SYNTAX		ProbableCauseValue
		ACCESS		read-only
		STATUS		mandatory
		DESCRIPTION	"ProbableCause when AUX Input is alarm.
		                      Refer to ProbableCauseValue of TEXTUAL-CONVENTION"
		::= { pnSys3ConfigTrapItemVar 10 }

	configItemPnSys3AuxOutItemName OBJECT-TYPE
		SYNTAX		DisplayString (SIZE (0..32))
		ACCESS		read-only
		STATUS		mandatory
		DESCRIPTION	"AUX Input name."
		::= { pnSys3ConfigTrapItemVar 11 }

	configItemPnSys3AuxOutOpenState OBJECT-TYPE
		SYNTAX		DisplayString (SIZE (0..32))
		ACCESS		read-only
		STATUS		mandatory
		DESCRIPTION	"Name of AUX output used in open state."
		::= { pnSys3ConfigTrapItemVar 12 }

	configItemPnSys3AuxOutCloseState OBJECT-TYPE
		SYNTAX		DisplayString (SIZE (0..32))
		ACCESS		read-only
		STATUS		mandatory
		DESCRIPTION	"Name of AUX output used in close state."
		::= { pnSys3ConfigTrapItemVar 13 }

	configTrapPnSys3AuxInItemName	TRAP-TYPE
		ENTERPRISE	pasolinkNeoCpv
		VARIABLES	{
					  sys3PnTrapSequenceNumber,
					  sys3PnTrapDate,
					  sys3PnTrapTime,
					  sys3PnTrapSource,
					  configItemPnSys3AuxInItemName
					}
		DESCRIPTION "This trap is sent
					  when AUX Input name status is changed."
		::= 704

	configTrapPnSys3AuxInItemType	TRAP-TYPE
		ENTERPRISE	pasolinkNeoCpv
		VARIABLES	{
					  sys3PnTrapSequenceNumber,
					  sys3PnTrapDate,
					  sys3PnTrapTime,
					  sys3PnTrapSource,
					  configItemPnSys3AuxInItemType
					}
		DESCRIPTION "This trap is sent
					  when Configuration for AUX Input status is changed."
		::= 705

	configTrapPnSys3AuxInOpenState	TRAP-TYPE
		ENTERPRISE	pasolinkNeoCpv
		VARIABLES	{
					  sys3PnTrapSequenceNumber,
					  sys3PnTrapDate,
					  sys3PnTrapTime,
					  sys3PnTrapSource,
					  configItemPnSys3AuxInOpenState
					}
		DESCRIPTION "This trap is sent
					  when Name when AUX Input is open status status is changed."
		::= 706

	configTrapPnSys3AuxInCloseState	TRAP-TYPE
		ENTERPRISE	pasolinkNeoCpv
		VARIABLES	{
					  sys3PnTrapSequenceNumber,
					  sys3PnTrapDate,
					  sys3PnTrapTime,
					  sys3PnTrapSource,
					  configItemPnSys3AuxInCloseState
					}
		DESCRIPTION "This trap is sent
					  when Name when AUX Input is close status status is changed."
		::= 707

	configTrapPnSys3AuxInSeverity	TRAP-TYPE
		ENTERPRISE	pasolinkNeoCpv
		VARIABLES	{
					  sys3PnTrapSequenceNumber,
					  sys3PnTrapDate,
					  sys3PnTrapTime,
					  sys3PnTrapSource,
					  configItemPnSys3AuxInSeverity
					}
		DESCRIPTION "This trap is sent
					  when Sevirity when AUX Input is alarm status is changed."
		::= 708

	configTrapPnSys3AuxInAlarmType	TRAP-TYPE
		ENTERPRISE	pasolinkNeoCpv
		VARIABLES	{
					  sys3PnTrapSequenceNumber,
					  sys3PnTrapDate,
					  sys3PnTrapTime,
					  sys3PnTrapSource,
					  configItemPnSys3AuxInAlarmType
					}
		DESCRIPTION "This trap is sent when Alarm Type when AUX Input is alarm status is changed."
		::= 709

	configTrapPnSys3AuxInProbableCause	TRAP-TYPE
		ENTERPRISE	pasolinkNeoCpv
		VARIABLES	{
					  sys3PnTrapSequenceNumber,
					  sys3PnTrapDate,
					  sys3PnTrapTime,
					  sys3PnTrapSource,
					  configItemPnSys3AuxInProbableCause
					}
		DESCRIPTION "This trap is sent
					  when ProbableCause when AUX Input is alarm status is changed."
		::= 710

	configTrapPnSys3AuxOutItemName	TRAP-TYPE
		ENTERPRISE	pasolinkNeoCpv
		VARIABLES	{
					  sys3PnTrapSequenceNumber,
					  sys3PnTrapDate,
					  sys3PnTrapTime,
					  sys3PnTrapSource,
					  configItemPnSys3AuxOutItemName
					}
		DESCRIPTION "This trap is sent
					  when AUX Input name status is changed."
		::= 711

	configTrapPnSys3AuxOutOpenState	TRAP-TYPE
		ENTERPRISE	pasolinkNeoCpv
		VARIABLES	{
					  sys3PnTrapSequenceNumber,
					  sys3PnTrapDate,
					  sys3PnTrapTime,
					  sys3PnTrapSource,
					  configItemPnSys3AuxOutOpenState
					}
		DESCRIPTION "This trap is sent
					  when Name when AUX Output is open status status is changed."
		::= 712

	configTrapPnSys3AuxOutCloseState	TRAP-TYPE
		ENTERPRISE	pasolinkNeoCpv
		VARIABLES	{
					  sys3PnTrapSequenceNumber,
					  sys3PnTrapDate,
					  sys3PnTrapTime,
					  sys3PnTrapSource,
					  configItemPnSys3AuxOutCloseState
					}
		DESCRIPTION "This trap is sent
					  when Name when AUX Output is close status status is changed."
		::= 713


-----------------------------------------------
-- pasoNeoCPV Group Definitions
-----------------------------------------------

	pnSummaryInfoGroup OBJECT IDENTIFIER
		::= { pasolinkNeoCpvInformation 1 }

	pnTrapGroup OBJECT IDENTIFIER
		::= { pasolinkNeoCpvInformation 2 }

	pnAlarmStatusGroup OBJECT IDENTIFIER
		::= { pasolinkNeoCpvInformation 3 }

	pnEquipmentSetUpGroup OBJECT IDENTIFIER
		::= { pasolinkNeoCpvInformation 4 }

	pnProvisioningGroup OBJECT IDENTIFIER
		::= { pasolinkNeoCpvInformation 5 }

	pnMaintenanceGroup OBJECT IDENTIFIER
		::= { pasolinkNeoCpvInformation 6 }

	pnInvEntryGroup OBJECT IDENTIFIER
		::= { pasolinkNeoCpvInformation 7 }

	pnMeteringGroup OBJECT IDENTIFIER
		::= { pasolinkNeoCpvInformation 8 }

	pnPmonGroup OBJECT IDENTIFIER
		::= { pasolinkNeoCpvInformation 9 }

	pnPmonTxRxLevGroup OBJECT IDENTIFIER
		::= { pasolinkNeoCpvInformation 10 }

	pnRmonGroup OBJECT IDENTIFIER
		::= { pasolinkNeoCpvInformation 11 }

	pnGetMeasurementDataGroup OBJECT IDENTIFIER
		::= { pasolinkNeoCpvInformation 12 }


-----------------------------------------------
-- pnSummaryInfoGroup Group Definitions
-----------------------------------------------

	pnSummaryItemTable OBJECT-TYPE
		SYNTAX		SEQUENCE OF PnSummaryItemEntry
		ACCESS		not-accessible
		STATUS		optional
		DESCRIPTION	"Summary Item Table"
		::= { pnSummaryInfoGroup 1 }

	pnSummaryItemEntry OBJECT-TYPE
		SYNTAX		PnSummaryItemEntry
		ACCESS		not-accessible
		STATUS		optional
		DESCRIPTION	"Summary Item Table Entry"
		INDEX		{
					pnSummaryItemPasoIndex	
					}
		::= { pnSummaryItemTable 1 }

	PnSummaryItemEntry ::= SEQUENCE {
					  pnSummaryItemPasoIndex 	IpAddress,
					  pnCtrlSummary			SeverityValue,
					  pnAuxIOSummary 		SeverityValue,
					  pnLinkPMONSummary 		SeverityValue,
					  pnIntfc1Summary 		SeverityValue,
					 }					  
					         
	pnSummaryItemPasoIndex OBJECT-TYPE
		SYNTAX		IpAddress 
		ACCESS		read-only
		STATUS		mandatory
		DESCRIPTION	"Pasolink IP Address Index"
		::= { pnSummaryItemEntry 1 }

	pnCtrlSummary OBJECT-TYPE
		SYNTAX		SeverityValue
		ACCESS		read-only
		STATUS		mandatory
		DESCRIPTION	"CTRL Summary
				  Refer to SeverityValue of TEXTUAL-CONVENTION
					TRAP=partialSummaryTrapCTRL"
		::= { pnSummaryItemEntry 2 }

	pnAuxIOSummary OBJECT-TYPE
		SYNTAX		SeverityValue
		ACCESS		read-only
		STATUS		mandatory
		DESCRIPTION	"AUX IO Summary
				  Refer to SeverityValue of TEXTUAL-CONVENTION
					TRAP=partialSummaryTrapAux"
		::= { pnSummaryItemEntry 3 }

	pnLinkPMONSummary OBJECT-TYPE
		SYNTAX		SeverityValue
		ACCESS		read-only
		STATUS		mandatory
		DESCRIPTION	"Link Pmon Summary
				  Refer to SeverityValue of TEXTUAL-CONVENTION
					TRAP=partialSummaryTrapLpm"
		::= { pnSummaryItemEntry 4 }

	pnIntfc1Summary OBJECT-TYPE
		SYNTAX		SeverityValue
		ACCESS		read-only
		STATUS		mandatory
		DESCRIPTION	"INTFC1 Summary
				  Refer to SeverityValue of TEXTUAL-CONVENTION
					TRAP=partialSummaryTrapINTFC1"
		::= { pnSummaryItemEntry 5 }

	pnSummarySysInfoTable OBJECT-TYPE
		SYNTAX		SEQUENCE OF PnSummarySysInfoEntry
		ACCESS		not-accessible
		STATUS		mandatory
		DESCRIPTION	"Individual Summary"
		::= { pnSummaryInfoGroup 2 }

	pnSummarySysInfoEntry OBJECT-TYPE
		SYNTAX		PnSummarySysInfoEntry
		ACCESS		not-accessible
		STATUS		mandatory
		INDEX		{
					  pnSummarySysInfoPasoIndex,
					  pnSummarySysInfoIndex
					}
		::= { pnSummarySysInfoTable 1 }

	PnSummarySysInfoEntry ::= SEQUENCE {
					  pnSummarySysInfoPasoIndex	IpAddress,
					  pnSummarySysInfoIndex		INTEGER,
					  pnTruSummary			SeverityValue,
					  pnModemSummary		SeverityValue
					}

	pnSummarySysInfoPasoIndex OBJECT-TYPE
		SYNTAX		IpAddress 
		ACCESS		read-only
		STATUS		mandatory
		DESCRIPTION	"Pasolink IP Address Index"
		::= { pnSummarySysInfoEntry 1 }

	pnSummarySysInfoIndex OBJECT-TYPE
		SYNTAX		INTEGER{
					  no1(1),
					  no2(2)
					}
		ACCESS		read-only
		STATUS		mandatory
		DESCRIPTION	"No Index.
					 1:No.1 when EQUIPMENT CONFIG is TERM.
					 2:No.2 when EQUIPMENT CONFIG is TERM."
		::= { pnSummarySysInfoEntry 2 }

	pnTruSummary OBJECT-TYPE
		SYNTAX		SeverityValue
		ACCESS		read-only
		STATUS		mandatory
		DESCRIPTION	"TRU(ODU) Summary
				  Refer to SeverityValue of TEXTUAL-CONVENTION
					TRAP=partialSummaryTrapTRU"
		::= { pnSummarySysInfoEntry 3 }

	pnModemSummary OBJECT-TYPE
		SYNTAX		SeverityValue
		ACCESS		read-only
		STATUS		mandatory
		DESCRIPTION	"Modem Summary
				  Refer to SeverityValue of TEXTUAL-CONVENTION
					TRAP=partialSummaryTrapMODEM"
		::= { pnSummarySysInfoEntry 4 }


-----------------------------------------------
-- pnTrapGroup Group Definitions
-----------------------------------------------

	pnCPVTrapCommon OBJECT IDENTIFIER
		::= { pnTrapGroup 1 }

	pnCPVTrapGenericVars OBJECT IDENTIFIER
		::= { pnCPVTrapCommon 1 }

	pnTrapSequenceNumber OBJECT-TYPE
		SYNTAX		Counter
		ACCESS		read-only
		STATUS		mandatory
		DESCRIPTION	"Trap Sequence number(0..4294967295)"
		::= { pnCPVTrapGenericVars 1 }

	pnTrapDate OBJECT-TYPE
		SYNTAX		DisplayString (SIZE(10))
		ACCESS		read-only
		STATUS		mandatory
		DESCRIPTION	"Trap Generate Date
					 This value shows YYYY/MM/DD.
					 YYYY means 4-digit year.
					 MM means 2-digit month.
					 DD means 2-digit day."
		::= { pnCPVTrapGenericVars 2 }

	pnTrapTime OBJECT-TYPE
		SYNTAX		DisplayString(SIZE(8))
		ACCESS		read-only
		STATUS		mandatory
		DESCRIPTION	"Trap Generate Time
					 This value shows hh:mm:ss.
					 hh means 2-digit hour.
					 mm means 2-digit minute.
					 ss means 2-digit second."
		::= { pnCPVTrapGenericVars 3 }

	pnTrapSource OBJECT-TYPE
		SYNTAX		OBJECT IDENTIFIER
		ACCESS		read-only
		STATUS		mandatory
		DESCRIPTION	"TRAP Source"
		::= { pnCPVTrapGenericVars 4 }

	pnCPVTrapX733Vars OBJECT IDENTIFIER
		::= { pnCPVTrapCommon 2 }

	pnSeverity OBJECT-TYPE
		SYNTAX		SeverityValue
		ACCESS		read-only
		STATUS		mandatory
		DESCRIPTION	"Severity (CCITT Rec. X.733)
			 	  Refer to SeverityValue of TEXTUAL-CONVENTION"
		::= { pnCPVTrapX733Vars 1 }

	pnAlarmType OBJECT-TYPE
		SYNTAX		AlarmTypeValue
		ACCESS		read-only
		STATUS		mandatory
		DESCRIPTION	"Alaem Type (CCITT Rec. X.733)
				  Refer to AlarmTypeValue of TEXTUAL-CONVENTION"
		::= { pnCPVTrapX733Vars 2 }

	pnProbableCause OBJECT-TYPE
		SYNTAX		ProbableCauseValue
		ACCESS		read-only
		STATUS		mandatory
		DESCRIPTION	"Probable Cause (CCITT Rec. X.733)
				  Refer to ProbableCauseValue of TEXTUAL-CONVENTION"
		::= { pnCPVTrapX733Vars 3 }

	pnCPVTrapItemType OBJECT IDENTIFIER
		::= { pnTrapGroup 2 }

	pnCPVStatusTrapItemType OBJECT IDENTIFIER
		::= { pnCPVTrapItemType 1 }

	pnStatusTypeAux OBJECT-TYPE
		SYNTAX		INTEGER (0..3)
		ACCESS		read-only
		STATUS		mandatory
		DESCRIPTION	"Aux Status Type
					  Invalid(0),
					  Alarm In Open state(1),
					  Alarm In Close state(2),
					  Status(3)"
		::= { pnCPVStatusTrapItemType 1 }

	pnStatusTypeAis OBJECT-TYPE
		SYNTAX		INTEGER (0..2)
		ACCESS		read-only
		STATUS		mandatory
		DESCRIPTION	"AIS Status Type
					  Invalid(0),
					  Alarm Type(1),
					  Status Type(2)"
		::= { pnCPVStatusTrapItemType 2 }

	pnCPVTrapItemVar OBJECT IDENTIFIER
		::= { pnTrapGroup 3 }

	pnCPVPartialSummaryTrapItemVar OBJECT IDENTIFIER
		::= { pnCPVTrapItemVar 1 }

	partialSummaryItemTRU OBJECT-TYPE
		SYNTAX		SeverityValue
		ACCESS		read-only
		STATUS		mandatory
		DESCRIPTION	"TRU Summary
				  Refer to SeverityValue of TEXTUAL-CONVENTION"
		::= { pnCPVPartialSummaryTrapItemVar 1 }

	partialSummaryItemINTFC1 OBJECT-TYPE
		SYNTAX		SeverityValue
		ACCESS		read-only
		STATUS		mandatory
		DESCRIPTION	"INTFC1 Summary
				  Refer to SeverityValue of TEXTUAL-CONVENTION"
		::= { pnCPVPartialSummaryTrapItemVar 2 }

	partialSummaryItemCTRL OBJECT-TYPE
		SYNTAX		SeverityValue
		ACCESS		read-only
		STATUS		mandatory
		DESCRIPTION	"CTRL Summary
				  Refer to SeverityValue of TEXTUAL-CONVENTION"
		::= { pnCPVPartialSummaryTrapItemVar 3 }

	partialSummaryItemAux OBJECT-TYPE
		SYNTAX		SeverityValue
		ACCESS		read-only
		STATUS		mandatory
		DESCRIPTION	"AUX Summary
				  Refer to SeverityValue of TEXTUAL-CONVENTION"
		::= { pnCPVPartialSummaryTrapItemVar 4 }

	partialSummaryItemLpm OBJECT-TYPE
		SYNTAX		SeverityValue
		ACCESS		read-only
		STATUS		mandatory
		DESCRIPTION	"LPM(Link Performance Monitor) Summary
				  Refer to SeverityValue of TEXTUAL-CONVENTION"
		::= { pnCPVPartialSummaryTrapItemVar 5 }

	partialSummaryItemMODEM OBJECT-TYPE
		SYNTAX		SeverityValue
		ACCESS		read-only
		STATUS		mandatory
		DESCRIPTION	"MODEM Summary
				  Refer to SeverityValue of TEXTUAL-CONVENTION"
		::= { pnCPVPartialSummaryTrapItemVar 7 }

	pnCPVAlarmTrapItemVar OBJECT IDENTIFIER
		::= { pnCPVTrapItemVar 2 }

	alarmItemPnCPVTxPowerAlarm OBJECT-TYPE
		SYNTAX		NormalAlarmValue
		ACCESS		read-only
		STATUS		mandatory
		DESCRIPTION	"TX POWER
					Refer to NormalAlarmValue of TEXTUAL-CONVENTION
					FLAG=SUMMARY_TRU
					severity=major
					alarmType=equipmentAlarm
					probableCause=transmitterFailure"
		::= { pnCPVAlarmTrapItemVar 1 }

	alarmItemPnCPVTxInputAlarm OBJECT-TYPE
		SYNTAX		NormalAlarmValue
		ACCESS		read-only
		STATUS		mandatory
		DESCRIPTION	"TX INPUT
					Refer to NormalAlarmValue of TEXTUAL-CONVENTION
					FLAG=SUMMARY_TRU
					severity=major
					alarmType=equipmentAlarm
					probableCause=transmitterFailure"
		::= { pnCPVAlarmTrapItemVar 2 }

	alarmItemPnCPVRxLevelAlarm OBJECT-TYPE
		SYNTAX		NormalAlarmValue
		ACCESS		read-only
		STATUS		mandatory
		DESCRIPTION	"RX LEVEL
					Refer to NormalAlarmValue of TEXTUAL-CONVENTION
					FLAG=SUMMARY_TRU
					severity=major
					alarmType=communicationAlarm
					probableCause=receiverFailure"
		::= { pnCPVAlarmTrapItemVar 3 }

	alarmItemPnCPVApcAlarm OBJECT-TYPE
		SYNTAX		NormalAlarmValue
		ACCESS		read-only
		STATUS		mandatory
		DESCRIPTION	"APC
					Refer to NormalAlarmValue of TEXTUAL-CONVENTION
					FLAG=SUMMARY_TRU
					severity=major
					alarmType=equipmentAlarm
					probableCause=equipmentMalfunction"
		::= { pnCPVAlarmTrapItemVar 4 }

	alarmItemPnCPVTRUCPUAlarm OBJECT-TYPE
		SYNTAX		NormalAlarmValue
		ACCESS		read-only
		STATUS		mandatory
		DESCRIPTION	"ODU CPU
					Refer to NormalAlarmValue of TEXTUAL-CONVENTION
					FLAG=SUMMARY_TRU
					severity=major
					alarmType=communicationAlarm
					probableCause=equipmentMalfunction"
		::= { pnCPVAlarmTrapItemVar 5 }

	alarmItemPnCPVModemAlarm OBJECT-TYPE
		SYNTAX		NormalAlarmValue
		ACCESS		read-only
		STATUS		mandatory
		DESCRIPTION	"MODEM MODULE
					Refer to NormalAlarmValue of TEXTUAL-CONVENTION
					FLAG=SUMMARY_MODEM
					severity=major
					alarmType=equipmentAlarm
					probableCause=equipmentMalfunction"
		::= { pnCPVAlarmTrapItemVar 6 }

	alarmItemPnCPVModemUneq OBJECT-TYPE
		SYNTAX		NormalAlarmValue
		ACCESS		read-only
		STATUS		mandatory
		DESCRIPTION	"MODEM UNEQUIPPED
					Refer to NormalAlarmValue of TEXTUAL-CONVENTION
					FLAG=SUMMARY_MODEM
					severity=major
					alarmType=equipmentAlarm
					probableCause=equipmentMalfunction"
		::= { pnCPVAlarmTrapItemVar 7 }

	alarmItemPnCPVHighBERAlarm OBJECT-TYPE
		SYNTAX		NormalAlarmValue
		ACCESS		read-only
		STATUS		mandatory
		DESCRIPTION	"HIGH BER
					Refer to NormalAlarmValue of TEXTUAL-CONVENTION
					FLAG=SUMMARY_MODEM
					severity=major
					alarmType=qualityOfServiceAlarm
					probableCause=excessiveBER"
		::= { pnCPVAlarmTrapItemVar 8 }

	alarmItemPnCPVLowBERAlarm OBJECT-TYPE
		SYNTAX		NormalAlarmValue
		ACCESS		read-only
		STATUS		mandatory
		DESCRIPTION	"LOW BER
					Refer to NormalAlarmValue of TEXTUAL-CONVENTION
					FLAG=SUMMARY_MODEM
					severity=minor
					alarmType=qualityOfServiceAlarm
					probableCause=degradedSignal"
		::= { pnCPVAlarmTrapItemVar 9 }

	alarmItemPnCPVModAlarm OBJECT-TYPE
		SYNTAX		NormalAlarmValue
		ACCESS		read-only
		STATUS		mandatory
		DESCRIPTION	"MOD
					Refer to NormalAlarmValue of TEXTUAL-CONVENTION
					FLAG=SUMMARY_MODEM
					severity=major
					alarmType=equipmentAlarm
					probableCause=transmitterFailure"
		::= { pnCPVAlarmTrapItemVar 10 }

	alarmItemPnCPVDemAlarm OBJECT-TYPE
		SYNTAX		NormalAlarmValue
		ACCESS		read-only
		STATUS		mandatory
		DESCRIPTION	"DEM
					Refer to NormalAlarmValue of TEXTUAL-CONVENTION
					FLAG=SUMMARY_MODEM
					severity=major
					alarmType=equipmentAlarm
					probableCause=receiverFailure"
		::= { pnCPVAlarmTrapItemVar 11 }

	alarmItemPnCPVXIfLevelAlarm OBJECT-TYPE
		SYNTAX		NormalAlarmValue
		ACCESS		read-only
		STATUS		mandatory
		DESCRIPTION	"MODEM TYPE MISMATCH
					Refer to NormalAlarmValue of TEXTUAL-CONVENTION
					FLAG=SUMMARY_MODEM
					severity=major
					alarmType=communicationAlarm
					probableCause=lossOfSignal"
		::= { pnCPVAlarmTrapItemVar 12 }

	alarmItemPnCPVPSAlarm OBJECT-TYPE
		SYNTAX		NormalAlarmValue
		ACCESS		read-only
		STATUS		mandatory
		DESCRIPTION	"POWER SUPPLY
					Refer to NormalAlarmValue of TEXTUAL-CONVENTION
					FLAG=SUMMARY_MODEM
					severity=major
					alarmType=equipmentAlarm
					probableCause=powerProblem"
		::= { pnCPVAlarmTrapItemVar 14 }

	alarmItemPnCPVIfCableShort OBJECT-TYPE
		SYNTAX		NormalAlarmValue
		ACCESS		read-only
		STATUS		mandatory
		DESCRIPTION	"IF CABLE SHORT
					Refer to NormalAlarmValue of TEXTUAL-CONVENTION
					FLAG=SUMMARY_MODEM
					severity=major
					alarmType=equipmentAlarm
					probableCause=equipmentMalfunction"
		::= { pnCPVAlarmTrapItemVar 15 }

	alarmItemPnCPVLof OBJECT-TYPE
		SYNTAX		NormalAlarmValue
		ACCESS		read-only
		STATUS		mandatory
		DESCRIPTION	"LOF
					Refer to NormalAlarmValue of TEXTUAL-CONVENTION
					FLAG=SUMMARY_MODEM
					severity=major
					alarmType=communicationAlarm
					probableCause=lossOfFrame"
		::= { pnCPVAlarmTrapItemVar 16 }

	alarmItemPnCPVCableEQLAlarm OBJECT-TYPE
		SYNTAX		NormalAlarmValue
		ACCESS		read-only
		STATUS		mandatory
		DESCRIPTION	"CABLE EQL
					Refer to NormalAlarmValue of TEXTUAL-CONVENTION
					FLAG=SUMMARY_MODEM
					severity=major
					alarmType=equipmentAlarm
					probableCause=equipmentMalfunction"
		::= { pnCPVAlarmTrapItemVar 17 }

	alarmItemPnCPVIntfcMAlarm OBJECT-TYPE
		SYNTAX		NormalAlarmValue
		ACCESS		read-only
		STATUS		mandatory
		DESCRIPTION	"INTFC MODULE
					Refer to NormalAlarmValue of TEXTUAL-CONVENTION
					FLAG=SUMMARY_INTFC
					severity=major
					alarmType=equipmentAlarm
					probableCause=equipmentMalfunction"
		::= { pnCPVAlarmTrapItemVar 19 }

	alarmItemPnCPVIntfcMUneq OBJECT-TYPE
		SYNTAX		NormalAlarmValue
		ACCESS		read-only
		STATUS		mandatory
		DESCRIPTION	"INTFC UNEQUIPPED
					Refer to NormalAlarmValue of TEXTUAL-CONVENTION
					FLAG=SUMMARY_INTFC
					severity=major
					alarmType=equipmentAlarm
					probableCause=equipmentMalfunction"
		::= { pnCPVAlarmTrapItemVar 20 }

	alarmItemPnCPVInputLos OBJECT-TYPE
		SYNTAX		OCTET STRING (SIZE (6))
		ACCESS		read-only
		STATUS		mandatory
		DESCRIPTION	"INPUT LOS CHxx
					(xx : 1-16)
					  0:Normal,
					  1:Alarm
					
					 [Bit Description]
					  Bit0 = CH01 (0: Normal,1: Alarm)
					  Bit1 = CH02
					  Bit2 = CH03
					  ...
					  Bit14 = CH15
					  Bit15 = CH16
					FLAG=SUMMARY_INTFC
					severity=major
					alarmType=communicationAlarm
					probableCause=lossOfSignal"
		::= { pnCPVAlarmTrapItemVar 21 }

	alarmItemPnCPVUsageError OBJECT-TYPE
		SYNTAX		OCTET STRING (SIZE (6))
		ACCESS		read-only
		STATUS		mandatory
		DESCRIPTION	"USAGE ERROR CHxx
					(xx : 1-16)
					  0:Normal,
					  1:Alarm
					
					 [Bit Description]
					  Bit0 = CH01 (0: Normal,1: Alarm)
					  Bit1 = CH02
					  Bit2 = CH03
					  ...
					  Bit14 = CH15
					  Bit15 = CH16
					FLAG=SUMMARY_INTFC
					severity=major
					alarmType=operationalViolationAlarm
					probableCause=callSetUpFailure"
		::= { pnCPVAlarmTrapItemVar 25 }

	alarmItemPnCPVLink OBJECT-TYPE
		SYNTAX		NormalAlarmValue
		ACCESS		read-only
		STATUS		mandatory
		DESCRIPTION	"LAN LINK PORTx
					(x : 1-2)
					Refer to NormalAlarmValue of TEXTUAL-CONVENTION
					FLAG=SUMMARY_INTFC1
					severity=major
					alarmType=communicationAlarm
					probableCause=lANError"
		::= { pnCPVAlarmTrapItemVar 26 }

	alarmItemPnCPVCTRLAlarm OBJECT-TYPE
		SYNTAX		NormalAlarmValue
		ACCESS		read-only
		STATUS		mandatory
		DESCRIPTION	"CTRL MODULE
					Refer to NormalAlarmValue of TEXTUAL-CONVENTION
					FLAG=SUMMARY_CTRL
					severity=major
					alarmType=equipmentAlarm
					probableCause=equipmentMalfunction"
		::= { pnCPVAlarmTrapItemVar 42 }

	alarmItemPnCPVTcn15minTotalOFS OBJECT-TYPE
		SYNTAX		NormalAlarmValue
		ACCESS		read-only
		STATUS		mandatory
		DESCRIPTION	"TCN-OFS-15min TOTAL
					Refer to NormalAlarmValue of TEXTUAL-CONVENTION
					FLAG=SUMMARY_LPM
					severity=minor
					alarmType=qualityOfServiceAlarm
					probableCause=thresholdCrossed"
		::= { pnCPVAlarmTrapItemVar 46 }

	alarmItemPnCPVTcn15minTotalUAS OBJECT-TYPE
		SYNTAX		NormalAlarmValue
		ACCESS		read-only
		STATUS		mandatory
		DESCRIPTION	"TCN-UAS-15min TOTAL
					Refer to NormalAlarmValue of TEXTUAL-CONVENTION
					FLAG=SUMMARY_LPM
					severity=minor
					alarmType=qualityOfServiceAlarm
					probableCause=thresholdCrossed"
		::= { pnCPVAlarmTrapItemVar 47 }

	alarmItemPnCPVTcn15minTotalES OBJECT-TYPE
		SYNTAX		NormalAlarmValue
		ACCESS		read-only
		STATUS		mandatory
		DESCRIPTION	"TCN-ES-15min TOTAL
					Refer to NormalAlarmValue of TEXTUAL-CONVENTION
					FLAG=SUMMARY_LPM
					severity=minor
					alarmType=qualityOfServiceAlarm
					probableCause=thresholdCrossed"
		::= { pnCPVAlarmTrapItemVar 48 }

	alarmItemPnCPVTcn15minTotalSES OBJECT-TYPE
		SYNTAX		NormalAlarmValue
		ACCESS		read-only
		STATUS		mandatory
		DESCRIPTION	"TCN-SES-15min TOTAL
					Refer to NormalAlarmValue of TEXTUAL-CONVENTION
					FLAG=SUMMARY_LPM
					severity=minor
					alarmType=qualityOfServiceAlarm
					probableCause=thresholdCrossed"
		::= { pnCPVAlarmTrapItemVar 49 }

	alarmItemPnCPVTcn15minTotalBBE OBJECT-TYPE
		SYNTAX		NormalAlarmValue
		ACCESS		read-only
		STATUS		mandatory
		DESCRIPTION	"TCN-BBE-15min TOTAL
					Refer to NormalAlarmValue of TEXTUAL-CONVENTION
					FLAG=SUMMARY_LPM
					severity=minor
					alarmType=qualityOfServiceAlarm
					probableCause=thresholdCrossed"
		::= { pnCPVAlarmTrapItemVar 50 }

	alarmItemPnCPVTcn15minTotalSEP OBJECT-TYPE
		SYNTAX		NormalAlarmValue
		ACCESS		read-only
		STATUS		mandatory
		DESCRIPTION	"TCN-SEP-15min TOTAL
					Refer to NormalAlarmValue of TEXTUAL-CONVENTION
					FLAG=SUMMARY_LPM
					severity=minor
					alarmType=qualityOfServiceAlarm
					probableCause=thresholdCrossed"
		::= { pnCPVAlarmTrapItemVar 51 }

	alarmItemPnCPVTcn15minCHUAS OBJECT-TYPE
		SYNTAX		OCTET STRING (SIZE (1))
		ACCESS		read-only
		STATUS		mandatory
		DESCRIPTION	"This item is not used.
					TCN-UAS-15min CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnCPVAlarmTrapItemVar 53 }

	alarmItemPnCPVTcn15minCHES OBJECT-TYPE
		SYNTAX		OCTET STRING (SIZE (1))
		ACCESS		read-only
		STATUS		mandatory
		DESCRIPTION	"This item is not used.
				TCN-ES-15min CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnCPVAlarmTrapItemVar 54 }

	alarmItemPnCPVTcn15minCHSES OBJECT-TYPE
		SYNTAX		OCTET STRING (SIZE (1))
		ACCESS		read-only
		STATUS		mandatory
		DESCRIPTION	"This item is not used.
				TCN-SES-15min CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnCPVAlarmTrapItemVar 55 }

	alarmItemPnCPVTcn15minCHBBE OBJECT-TYPE
		SYNTAX		OCTET STRING (SIZE (1))
		ACCESS		read-only
		STATUS		mandatory
		DESCRIPTION	"This item is not used.
				TCN-BBE-15min CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnCPVAlarmTrapItemVar 56 }

	alarmItemPnCPVTcn15minCHSEP OBJECT-TYPE
		SYNTAX		OCTET STRING (SIZE (1))
		ACCESS		read-only
		STATUS		mandatory
		DESCRIPTION	"This item is not used.
				TCN-SEP-15min CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnCPVAlarmTrapItemVar 57 }

	alarmItemPnCPVTcn1dayTotalOFS OBJECT-TYPE
		SYNTAX		NormalAlarmValue
		ACCESS		read-only
		STATUS		mandatory
		DESCRIPTION	"TCN-OFS-1day TOTAL
					Refer to NormalAlarmValue of TEXTUAL-CONVENTION
					FLAG=SUMMARY_LPM
					severity=minor
					alarmType=qualityOfServiceAlarm
					probableCause=thresholdCrossed"
		::= { pnCPVAlarmTrapItemVar 58 }

	alarmItemPnCPVTcn1dayTotalUAS OBJECT-TYPE
		SYNTAX		NormalAlarmValue
		ACCESS		read-only
		STATUS		mandatory
		DESCRIPTION	"TCN-UAS-1day TOTAL
					Refer to NormalAlarmValue of TEXTUAL-CONVENTION
					FLAG=SUMMARY_LPM
					severity=minor
					alarmType=qualityOfServiceAlarm
					probableCause=thresholdCrossed"
		::= { pnCPVAlarmTrapItemVar 59 }

	alarmItemPnCPVTcn1dayTotalES OBJECT-TYPE
		SYNTAX		NormalAlarmValue
		ACCESS		read-only
		STATUS		mandatory
		DESCRIPTION	"TCN-ES-1day TOTAL
					Refer to NormalAlarmValue of TEXTUAL-CONVENTION
					FLAG=SUMMARY_LPM
					severity=minor
					alarmType=qualityOfServiceAlarm
					probableCause=thresholdCrossed"
		::= { pnCPVAlarmTrapItemVar 60 }

	alarmItemPnCPVTcn1dayTotalSES OBJECT-TYPE
		SYNTAX		NormalAlarmValue
		ACCESS		read-only
		STATUS		mandatory
		DESCRIPTION	"TCN-SES-1day TOTAL
					Refer to NormalAlarmValue of TEXTUAL-CONVENTION
					FLAG=SUMMARY_LPM
					severity=minor
					alarmType=qualityOfServiceAlarm
					probableCause=thresholdCrossed"
		::= { pnCPVAlarmTrapItemVar 61 }

	alarmItemPnCPVTcn1dayTotalBBE OBJECT-TYPE
		SYNTAX		NormalAlarmValue
		ACCESS		read-only
		STATUS		mandatory
		DESCRIPTION	"TCN-BBE-1day TOTAL
					Refer to NormalAlarmValue of TEXTUAL-CONVENTION
					FLAG=SUMMARY_LPM
					severity=minor
					alarmType=qualityOfServiceAlarm
					probableCause=thresholdCrossed"
		::= { pnCPVAlarmTrapItemVar 62 }

	alarmItemPnCPVTcn1dayTotalSEP OBJECT-TYPE
		SYNTAX		NormalAlarmValue
		ACCESS		read-only
		STATUS		mandatory
		DESCRIPTION	"TCN-SEP-1day TOTAL
					Refer to NormalAlarmValue of TEXTUAL-CONVENTION
					FLAG=SUMMARY_LPM
					severity=minor
					alarmType=qualityOfServiceAlarm
					probableCause=thresholdCrossed"
		::= { pnCPVAlarmTrapItemVar 63 }

	alarmItemPnCPVTcn1dayCHUAS OBJECT-TYPE
		SYNTAX		OCTET STRING (SIZE (1))
		ACCESS		read-only
		STATUS		mandatory
		DESCRIPTION	"This item is not used.
				TCN-UAS-1day CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnCPVAlarmTrapItemVar 65 }

	alarmItemPnCPVTcn1dayCHES OBJECT-TYPE
		SYNTAX		OCTET STRING (SIZE (1))
		ACCESS		read-only
		STATUS		mandatory
		DESCRIPTION	"This item is not used.
				TCN-ES-1day CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnCPVAlarmTrapItemVar 66 }

	alarmItemPnCPVTcn1dayCHSES OBJECT-TYPE
		SYNTAX		OCTET STRING (SIZE (1))
		ACCESS		read-only
		STATUS		mandatory
		DESCRIPTION	"This item is not used.
				TCN-SES-1day CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnCPVAlarmTrapItemVar 67 }

	alarmItemPnCPVTcn1dayCHBBE OBJECT-TYPE
		SYNTAX		OCTET STRING (SIZE (1))
		ACCESS		read-only
		STATUS		mandatory
		DESCRIPTION	"This item is not used.
				TCN-BBE-1day CHxx
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnCPVAlarmTrapItemVar 68 }

	alarmItemPnCPVTcn1dayCHSEP OBJECT-TYPE
		SYNTAX		OCTET STRING (SIZE (1))
		ACCESS		read-only
		STATUS		mandatory
		DESCRIPTION	"This item is not used.
				TCN-SEP-1day CHxx
					  0:Normal,
					  1:Alarm
					
					 [Description]
					 Bit 0 = 1st Selected CH (0:Normal, 1:Alarm)
					 Bit 1 = 2nd Selected CH
					 Bit 2 = 3rd Selected CH
					 Bit 3 = 4th Selected CH
					FLAG=SUMMARY_LPM
					severity=minor
					alarmType=qualityOfServiceAlarm
					probableCause=thresholdCrossed"
		::= { pnCPVAlarmTrapItemVar 69 }

	alarmItemPnCPVTcnTCS15minRxLev OBJECT-TYPE
		SYNTAX		NormalAlarmValue
		ACCESS		read-only
		STATUS		mandatory
		DESCRIPTION	"TCN-RX LEV-15min
					Refer to NormalAlarmValue of TEXTUAL-CONVENTION
					FLAG=SUMMARY_LPM
					severity=minor
					alarmType=qualityOfServiceAlarm
					probableCause=thresholdCrossed"
		::= { pnCPVAlarmTrapItemVar 72 }

	alarmItemPnCPVTcnTCS1dayRxLev OBJECT-TYPE
		SYNTAX		NormalAlarmValue
		ACCESS		read-only
		STATUS		mandatory
		DESCRIPTION	"TCN-RX LEV-1day
					Refer to NormalAlarmValue of TEXTUAL-CONVENTION
					FLAG=SUMMARY_LPM
					severity=minor
					alarmType=qualityOfServiceAlarm
					probableCause=thresholdCrossed"
		::= { pnCPVAlarmTrapItemVar 73 }

	alarmItemPnCPVTRULORefAlarm OBJECT-TYPE
		SYNTAX		NormalAlarmValue
		ACCESS		read-only
		STATUS		mandatory
		DESCRIPTION	"ODU TYPE MISMATCH
					Refer to NormalAlarmValue of TEXTUAL-CONVENTION
					FLAG=SUMMARY_TRU
					severity=minor
					alarmType=equipmentAlarm
					probableCause=equipmentMalfunction"
		::= { pnCPVAlarmTrapItemVar 74 }

	alarmItemPnCPVAuxClusterAlarm OBJECT-TYPE
		SYNTAX		NormalAlarmValue
		ACCESS		read-only
		STATUS		mandatory
		DESCRIPTION	"This item is not used.
				CLUSTERx ALARM
					(x : 1-4)
					Refer to NormalAlarmValue of TEXTUAL-CONVENTION
					FLAG=SUMMARY_AUX
					severity=major
					alarmType=equipmentAlarm
					probableCause=equipmentMalfunction"
		::= { pnCPVAlarmTrapItemVar 84 }

	alarmItemPnCPVLinearizerFail OBJECT-TYPE
		SYNTAX		NormalAlarmValue
		ACCESS		read-only
		STATUS		mandatory
		DESCRIPTION	"LINEARIZER
					Refer to NormalAlarmValue of TEXTUAL-CONVENTION
					FLAG=SUMMARY_MODEM
					severity=major
					alarmType=equipmentAlarm
					probableCause=equipmentMalfunction"
		::= { pnCPVAlarmTrapItemVar 85 }

	alarmItemPnCPVRouteID OBJECT-TYPE
		SYNTAX		NormalAlarmValue
		ACCESS		read-only
		STATUS		mandatory
		DESCRIPTION	"FRAME ID
					Refer to NormalAlarmValue of TEXTUAL-CONVENTION
					FLAG=SUMMARY_MODEM
					severity=major
					alarmType=communicationAlarm
					probableCause=equipmentMalfunction"
		::= { pnCPVAlarmTrapItemVar 86 }

	alarmItemPnCPVEarlyWarning OBJECT-TYPE
		SYNTAX		NormalAlarmValue
		ACCESS		read-only
		STATUS		mandatory
		DESCRIPTION	"EARLY WARNING
					Refer to NormalAlarmValue of TEXTUAL-CONVENTION
					FLAG=SUMMARY_MODEM
					severity=minor
					alarmType=qualityOfServiceAlarm
					probableCause=degradedSignal"
		::= { pnCPVAlarmTrapItemVar 87 }

	alarmItemPnCPVInputVoltage OBJECT-TYPE
		SYNTAX		NormalAlarmValue
		ACCESS		read-only
		STATUS		mandatory
		DESCRIPTION	"INPUT VOLTAGE
					Refer to NormalAlarmValue of TEXTUAL-CONVENTION
					FLAG=SUMMARY_MODEM
					severity=major
					alarmType=equipmentAlarm
					probableCause=powerProblem"
		::= { pnCPVAlarmTrapItemVar 88 }

	alarmItemPnCPVIntfcMTypeMismatch OBJECT-TYPE
		SYNTAX		NormalAlarmValue
		ACCESS		read-only
		STATUS		mandatory
		DESCRIPTION	"INTFC(1) TYPE MISMATCH
					Refer to NormalAlarmValue of TEXTUAL-CONVENTION
					FLAG=SUMMARY_INTFC1
					severity=major
					alarmType=equipmentAlarm
					probableCause=equipmentMalfunction"
		::= { pnCPVAlarmTrapItemVar 89 }

        pnCPVEventTrapItemVar OBJECT IDENTIFIER
		::= { pnCPVTrapItemVar 3 }

	eventItemPnCPVConfigDataValid OBJECT-TYPE
		SYNTAX		INTEGER(0..1)
		ACCESS		read-only
		STATUS		mandatory
		DESCRIPTION	"EQUIPMENT CONFIG AVAILABILITY
					  0:Invalid,
					  1:Valid"
		::= { pnCPVEventTrapItemVar 1 }

	eventItemPnCPVConfigDataUp OBJECT-TYPE
		SYNTAX		INTEGER
		ACCESS		read-only
		STATUS		mandatory
		::= { pnCPVEventTrapItemVar 2 }

	eventItemPnCPVTxMuteStatus OBJECT-TYPE
		SYNTAX		OffOnValue
		ACCESS		read-only
		STATUS		mandatory
		DESCRIPTION	"MUTE STATUS
				Refer to OffOnValue of TEXTUAL-CONVENTION"
		::= { pnCPVEventTrapItemVar 3 }

	eventItemPnCPVTxSWStatus OBJECT-TYPE
		SYNTAX		INTEGER (0..2)
		ACCESS		read-only
		STATUS		mandatory
		DESCRIPTION	"TX SW STATUS
					  0:Invalid,
					  1:No.1,
					  2:No.2"
		::= { pnCPVEventTrapItemVar 4 }

	eventItemPnCPVRxSWStatus OBJECT-TYPE
		SYNTAX		INTEGER (0..2)
		ACCESS		read-only
		STATUS		mandatory
		DESCRIPTION	"RX SW STATUS
					  0:Invalid,
					  1:No.1,
					  2:No.2"
		::= { pnCPVEventTrapItemVar 5 }

	eventItemPnCPVLinearizerFunc OBJECT-TYPE
		SYNTAX		INTEGER (0..3)
		ACCESS		read-only
		STATUS		mandatory
		DESCRIPTION	"LINEARIZER FUNCTION
					  0:Invalid,
					  1:N/A,
					  2:Non Operation,
					  3:Operation"
		::= { pnCPVEventTrapItemVar 7 }

	eventItemPnCPVAisGeneratedCH OBJECT-TYPE
		SYNTAX		OCTET STRING (SIZE (6))
		ACCESS		read-only
		STATUS		mandatory
		DESCRIPTION	"AIS GENERATED CHxx
					(xx : 1-16)
					  0:Normal,
					  1:Generated
					
					 [Bit Description]
					  Bit0 = CH01 (0: Normal,1: Alarm)
					  Bit1 = CH02
					  Bit2 = CH03
					  ...
					  Bit14 = CH15
					  Bit15 = CH16"
		::= { pnCPVEventTrapItemVar 10 }

	eventItemPnCPVAisReceivedCH OBJECT-TYPE
		SYNTAX		OCTET STRING (SIZE (6))
		ACCESS		read-only
		STATUS		mandatory
		DESCRIPTION	"AIS RECEIVED CHxx
					(xx : 1-16)
					  0:Normal,
					  1:Received
					
					 [Bit Description]
					  Bit0 = CH01 (0: Normal,1: Alarm)
					  Bit1 = CH02
					  Bit2 = CH03
					  ...
					  Bit14 = CH15
					  Bit15 = CH16"
		::= { pnCPVEventTrapItemVar 11 }

	eventItemPnCPVLinkLossForward OBJECT-TYPE
		SYNTAX		INTEGER (0..2)
		ACCESS		read-only
		STATUS		mandatory
		DESCRIPTION	"LINK LOSS FORWARDING PORTx
					(x : 1-2)
					  0:Invalid,
					  1:Normal,
					  2:Under Execution"
		::= { pnCPVEventTrapItemVar 12 }

	eventItemPnCPVSpeedDuplex OBJECT-TYPE
		SYNTAX		INTEGER (0..8)
		ACCESS		read-only
		STATUS		mandatory
		DESCRIPTION	"SPEED & DUPLEX PORTx
					(x : 1-2)
					  0:INVALID,
					  1:10M-HALF(MDI),
					  2:10M-FULL(MDI),
					  3:100M-HALF(MDI),
					  4:100M-FULL(MDI),
					  5:10M-HALF(MDIX),
					  6:10M-FULL(MDIX),
					  7:100M-HALF(MDIX),
					  8:100M-FULL(MDIX)"
		::= { pnCPVEventTrapItemVar 13 }

	eventItemPnCPVInphaseWork OBJECT-TYPE
		SYNTAX		INTEGER (0..2)
		ACCESS		read-only
		STATUS		mandatory
		DESCRIPTION	"INTFC INPHASE
					  0:Invalid,
					  1:Out Phase,
					  2:In Phase"
		::= { pnCPVEventTrapItemVar 14 }

	eventItemPnCPVCHUsage OBJECT-TYPE
		SYNTAX		OCTET STRING (SIZE (48))
		ACCESS		read-only
		STATUS		mandatory
		DESCRIPTION	"CH USAGE(CHxx)
					xx=1-16
					  0:Invalid,
					  1:Not Used,
					  2:Used(E1),
					  3:Used(LAN)
					
					  [Description]
					    Byte 0 = CH01(0:Invalid, 1:Not Used, 2:Used(E1), 3:Used(LAN))
					    Byte 1 = CH02
					    ...
					    Byte 14 = CH15
					    Byte 15 = CH16"
		::= { pnCPVEventTrapItemVar 21 }

	eventItemPnCPVCHCondition OBJECT-TYPE
		SYNTAX		OCTET STRING (SIZE (6))
		ACCESS		read-only
		STATUS		mandatory
		DESCRIPTION	"CH USAGE ERROR REPORT
					  0:Invalid, 
					  1:Disabled(Report),
					  2:Enabled(Not Report)
					
				 AIS Activation Condition
					  0:Invalid, 
					  1:LOF+HIGH BER,
					  2:LOF
					 
				 AIS ACTIVATION DELAY --Not Used
					  0:Invalid,
					  1:Off,
					  2:On

				 AIS GENERATED REPORT
					  0:Invalid, 
					  1:Not Report, 
					  2:Report

				 AIS RECEIVED REPORT
					  0:Invalid, 
					  1:Not Report, 
					  2:Report

				 AIS RECEIVED CONDITION
					  0:Invalid, 
					  1:Alarm, 
					  2:Status"
		::= { pnCPVEventTrapItemVar 22 }

	eventItemPnCPVCHImpedance OBJECT-TYPE
		SYNTAX		OCTET STRING (SIZE (10))
		ACCESS		read-only
		STATUS		mandatory
		DESCRIPTION	"E1 PORT IMPEDANCE
					  0:Invalid,
					  1:120[ohm],
					  2:75[ohm]
					
					  [Description]
					    BYTE0 = E1 PORT IMPEDANCE(CH1) (0:Invalid, 1:120[ohm], 2:75[ohm])
					    BYTE1 = E1 PORT IMPEDANCE(CH2)
					    BYTE2 = E1 PORT IMPEDANCE(CH3)
					    BYTE3 = E1 PORT IMPEDANCE(CH4)
					    BYTE4 = E1 PORT IMPEDANCE(CH5-8)
					    BYTE5 = E1 PORT IMPEDANCE(CH9-16)
					"
		::= { pnCPVEventTrapItemVar 23 }

	eventItemPnCPVCHDISetting OBJECT-TYPE
		SYNTAX		OCTET STRING (SIZE (48))
		ACCESS		read-only
		STATUS		mandatory
		DESCRIPTION	"MAIN PORT D/I SETTING
					  0:Invalid,
					  1:Disabled,
					  2:Through
					
					  [Description]
					    Byte 0 = CH01(0:Invalid, 1:, 2:Through)
					    Byte 1 = CH02
					    ...
					    Byte 14 = CH15
					    Byte 15 = CH16"
		::= { pnCPVEventTrapItemVar 26 }

	eventItemPnCPVBERThreshold OBJECT-TYPE
		SYNTAX		OCTET STRING (SIZE (8))
		ACCESS		read-only
		STATUS		mandatory
		DESCRIPTION	"BER THRESHOLD SETTING
					  [Description]
					    Byte 0 = HIGH BER THRESHOLD
					                (0:INVALID, 1:1E-3, 2:1E-4, 3:1E-5)
					    Byte 1 = HIGH BER THRESHOLD(DIR-B)  --Not used
					                (0:INVALID, 1:1E-3, 2:1E-4, 3:1E-5)
					    Byte 2 = LOW BER THRESHOLD
					                (0:INVALID, 1:1E-6, 2:1E-7, 3:1E-8, 4:1E-9)
					    Byte 3 = LOW BER THRESHOLD(DIR-B) --Not used
					                (0:INVALID, 1:1E-6, 2:1E-7, 3:1E-8, 4:1E-9)
					    Byte 4 = E-BER(DMR) --Not used
					                (0:INVALID, 1:1E-3, 2:1E-4, 3:1E-5)
					    Byte 5 = SD(DMR) --Not used
					                (0:INVALID, 1:1E-6, 2:1E-7, 3:1E-8, 4:1E-9)
					    Byte 6 = E-BER(MUX) --Not used
					                 (0:INVALID, 1:1E-3, 2:1E-4, 3:1E-5)
					    Byte 7 = SD(MUX) --Not used
					                (0:INVALID, 1:1E-6, 2:1E-7, 3:1E-8, 4:1E-9)"
		::= { pnCPVEventTrapItemVar 28 }

	eventItemPnCPVSCAssign OBJECT-TYPE
		SYNTAX		OCTET STRING (SIZE (8))
		ACCESS		read-only
		STATUS		mandatory
		DESCRIPTION	"SC ASSIGNMENT
					  [Description]
					    Byte 0 = RS-232C-1
					         (0:INVALID, 1:NOT USED, 2:SC1)
					    Byte 1 = RS-232C-2
					         (0:INVALID, 1:NOT USED, 3:SC2)
					    Byte 2 = V11-1
					         (0:INVALID, 1:NOT USED, 2:SC1)
					    Byte 3 = V11-2
					         (0:INVALID, 1:NOT USED,22:SC3-4)
					    Byte 4 = SC LAN1
					         (0:INVALID, 1:NOT USED, 2:SC1, 10:SC1-2,
					          14:SC1-4)
					    Byte 5 = SC LAN2
					    Byte 6 = V11-1 DIRECTION SETTING
					         (0:INVALID, 1:CO-DIRECTIONAL, 2:CONTRA-DIRECTIONAL)
					    Byte 7 = V11-2 DIRECTION SETTING--Not Used
					"
		::= { pnCPVEventTrapItemVar 30 }

	eventItemPnCPVLanPortSetting OBJECT-TYPE
		SYNTAX		OCTET STRING (SIZE (36))
		ACCESS		read-only
		STATUS		mandatory
		DESCRIPTION	"LAN PORT SETTING
					  [Description]
					  Byte 0 = SWITCHING FUNCTION
					       (0:INVALID, 1:DISABLED(Report), 2:ENABLED(Not Report))
					
					  Byte 1 = SPEED & DUPLEX PORT1
					  Byte 2 = SPEED & DUPLEX PORT2
					  Byte 3 = SPEED & DUPLEX PORT3 --Not used
					  Byte 4 = SPEED & DUPLEX PORT4 --Not used
					  Byte 5 = INTFC(2) SPEED & DUPLEX PORT1 --Not used
					  Byte 6 = INTFC(2) SPEED & DUPLEX PORT2 --Not used
					       (0:INVALID, 1:AUTONEG(AUTO-MDI/MDIX),
					        2:10M-HALF(MDI), 3:10M-FULL(MDI), 
					        4:100M-HALF(MDI), 5:100M-FULL(MDI), 
					        6:10M-HALF(MDIX), 7:10M-FULL(MDIX), 
					        8:100M-HALF(MDIX), 9:100M-FULL(MDIX))
					
					  Byte 7 = FLOW CONTROL PORT1
					  Byte 8 = FLOW CONTROL PORT2
					  Byte 9 = FLOW CONTROL PORT3 --Not used
					  Byte 10 = FLOW CONTROL PORT4 --Not used
					  Byte 11 = INTFC(2) FLOW CONTROL PORT1 --Not used
					  Byte 12 = INTFC(2) FLOW CONTROL PORT2 --Not used
					       (0:INVALID, 1:OFF, 2:ON)
					
					  Byte 13 = COLLISION REPORT PORT1
					  Byte 14 = COLLISION REPORT PORT2
					  Byte 15 = COLLISION REPORT PORT3 --Not used
					  Byte 16 = COLLISION REPORT PORT4 --Not used
					  Byte 17 = INTFC(2) COLLISION REPORT PORT1 --Not used
					  Byte 18 = INTFC(2) COLLISION REPORT PORT2 --Not used
					       (0:INVALID, 1:DISABLED, 2:ENABLED)
					
					  Byte 19 = LINK LOSS FORWARDING PORT1
					  Byte 20 = LINK LOSS FORWARDING PORT2
					  Byte 21 = LINK LOSS FORWARDING PORT3 --Not used
					  Byte 22 = LINK LOSS FORWARDING PORT4 --Not used
					  Byte 23 = INTFC(2) LINK LOSS FWD PORT1 --Not used
					  Byte 24 = INTFC(2) LINK LOSS FWD PORT2 --Not used
					       (0:INVALID, 1:DISABLED, 2:ENABLED)
					
					  Byte 25 = LOCK SOURCE SETTING --Not used
					       (0:INVALID, 1:INTERNAL CLOCK,  --Not used
					        2:DMR -> INTERNAL CLOCK) --Not used
					
					  Byte 26 = 2M FRAMING PORT1
					  Byte 27 = 2M FRAMING PORT2
					  Byte 28 = 2M FRAMING PORT3 --Not used
					  Byte 29 = 2M FRAMING PORT4 --Not used
					       (0:INVALID, 1:UNFRAMED,2:PCM31C(FAS+CRC)                                                                       
					        3:PCM31(FAS),4:PCM30C(MFAS+CRC)                                                                                   
					        5:PCM30(MFAS))                                                                                                    
					
					  Byte 30 = PORT1 USAGE
					  Byte 31 = PORT2 USAGE
					  Byte 32 = PORT3 USAGE --Not used
					  Byte 33 = PORT4 USAGE --Not used
					  Byte 34 = INTFC(2) PORT1 USAGE --Not used
					  Byte 35 = INTFC(2) PORT2 USAGE --Not used
					       (0:INVALID, 1:NOT USED, 2:USED)"
		::= { pnCPVEventTrapItemVar 31 }

	eventItemPnCPVTxPowerContValue OBJECT-TYPE
		SYNTAX		OCTET STRING (SIZE (9))
		ACCESS		read-only
		STATUS		mandatory
		DESCRIPTION	"TX POWER CTRL
					  [Description]
					  Byte 0 = MTPC TX POWER 
					      (0 - 255)
					  Byte 1 = ATPC THRESHOLD LEVEL integral number(signed char) 
					      (-128 - 127)
					  Byte 2 = ATPC THRESHOLD LEVEL a place of decimal
					      (0 - 9) 
					  Byte 3 = ADDITIONAL ATT 
					      (0 - 255)
					  Byte 4 = ATPC(MAX)
					      (0 - 255)
					  Byte 5 = ATPC(MIN)
					      (0 - 255)
					  Byte 6 = HYSTERESIS
					      (0 - 255)
					  Byte 7 = ATPC POWER MODE
					      (0:INVALID, 1:HOLD, 2:MAX, 3:MIN)
					  Byte 8 = ODU COMM ALARM MODE
					      (0:INVALID, 1:HOLD, 2:MUTE)"
		::= { pnCPVEventTrapItemVar 33 }

	eventItemPnCPVAtpcPowerMode OBJECT-TYPE
		SYNTAX		INTEGER (0..3)
		ACCESS		read-only
		STATUS		mandatory
		DESCRIPTION	"ATPC POWER MODE
					  0:Invalid,
					  1:Hold,
					  3:MIN
				Number 2 is not used."
		::= { pnCPVEventTrapItemVar 34 }

	eventItemPnCPVCommAlarmMode OBJECT-TYPE
		SYNTAX		INTEGER (0..2)
		ACCESS		read-only
		STATUS		mandatory
		DESCRIPTION	"This item is not used.
				ODU COMM ALARM MODE
					  0:Invalid,
					  1:Hold,
					  2:Mute"
		::= { pnCPVEventTrapItemVar 35 }

	eventItemPnCPVSWCondTxRx OBJECT-TYPE
		SYNTAX		OCTET STRING (SIZE (5))
		ACCESS		read-only
		STATUS		mandatory
		DESCRIPTION	"CONDITION
					for TX/RX SW 
					  
					  [Description]
					  Byte 0 = TX SW PRIORITY
					      (0:INVALID, 1:NON PRIORITY, 2:PRIORITY No.1)
					  Byte 1 = RX SW PRIORITY
					      (0:INVALID, 1:NON PRIORITY, 2:PRIORITY No.1)
					  Byte 2 = RX SW MAINTENANCE MODE
					      (0:INVALID, 1:MANUAL, 2:FORCED)
					  Byte 3 = RX SW CONDITION-EARLY WARNING
					      (0:INVALID, 1:INCLUDED EW, 2:EXCLUDED EW)"

		::= { pnCPVEventTrapItemVar 36 }

	eventItemPnCPVRelayConfigData OBJECT-TYPE
		SYNTAX		OCTET STRING (SIZE (48))
		ACCESS		read-only
		STATUS		mandatory
		DESCRIPTION	"RELAY CONFIGURATION CHANGED
					  [Description]
					  (Relay x (x:1~6))
					   [START BIT] = 64 * (x - 1)
					
					    Bit (0 + [START BIT]) = MAINT (Remark1)
					    Bit (1 + [START BIT]) = PS ALARM1 (Remark2)
					    Bit (2 + [START BIT]) = PS ALARM2 (Remark2)
					    Bit (3 + [START BIT]) = (FIXED to 0)
					    Bit (4 + [START BIT]) = (FIXED to 0)
					    Bit (5 + [START BIT]) = (FIXED to 0)
					    Bit (6 + [START BIT]) = (FIXED to 0)
					    Bit (7 + [START BIT]) = CPU ALARM (Remark2)
					    Bit (8 + [START BIT]) = ODU ALARM1 (Remark7)
					    Bit (9 + [START BIT]) = ODU ALARM2 (Remark7)
					    Bit (10 + [START BIT]) = IDU ALARM (Remark7)
					    Bit (11 + [START BIT]) = (FIXED to 0)
					    Bit (12 + [START BIT]) = (FIXED to 0)
					    Bit (13 + [START BIT]) = (FIXED to 0)
					    Bit (14 + [START BIT]) = (FIXED to 0)
					    Bit (15 + [START BIT]) = (FIXED to 0)
					    Bit (16 + [START BIT]) = TX POWER ALARM1 (Remark7)
					    Bit (17 + [START BIT]) = TX POWER ALARM2 (Remark7)
					    Bit (18 + [START BIT]) = TX IN LEV ALARM1 (Remark7)
					    Bit (19 + [START BIT]) = TX IN LEV ALARM2 (Remark7)
					    Bit (20 + [START BIT]) = RX LEV ALARM1 (Remark7)
					    Bit (21 + [START BIT]) = RX LEV ALARM2 (Remark7)
					    Bit (22 + [START BIT]) = APC ALARM1 (Remark7)
					    Bit (23 + [START BIT]) = APC ALARM2 (Remark7)
					    Bit (24 + [START BIT]) = IF CABLE SHORT ALARM1 (Remark7)
					    Bit (25 + [START BIT]) = IF CABLE SHORT ALARM2 (Remark7)
					    Bit (26 + [START BIT]) = ODU CPU ALARM1 (Remark7)
					    Bit (27 + [START BIT]) = ODU CPU ALARM2 (Remark7)
					    Bit (28 + [START BIT]) = (FIXED to 0)
					    Bit (29 + [START BIT]) = (FIXED to 0)
					    Bit (30 + [START BIT]) = (FIXED to 0)
					    Bit (31 + [START BIT]) = (FIXED to 0)
					    Bit (32 + [START BIT]) = MOD ALARM1 (Remark7)
					    Bit (33 + [START BIT]) = MOD ALARM2 (Remark7)
					    Bit (34 + [START BIT]) = DEM ALARM1 (Remark7)
					    Bit (35 + [START BIT]) = DEM ALARM2 (Remark7)
					    Bit (36 + [START BIT]) = CH INPUT LOSS (Remark7)
					    Bit (37 + [START BIT]) = CH AIS RECEIVED (Remark7)
					    Bit (38 + [START BIT]) = CH AIS GENERATED (Remark7)
					    Bit (39 + [START BIT]) = CH USAGE ERROR (Remark7)
					    Bit (40 + [START BIT]) = LOW BER ALARM1 (Remark7)
					    Bit (41 + [START BIT]) = LOW BER ALARM2 (Remark7)
					    Bit (42 + [START BIT]) = HIGH BER ALARM1 (Remark7)
					    Bit (43 + [START BIT]) = HIGH BER ALARM2 (Remark7)
					    Bit (44 + [START BIT]) = STM-1 TF ALARM (Remark7) -- Not Used
					    Bit (45 + [START BIT]) = STM-1 SLOS (Remark7) -- Not Used
					    Bit (46 + [START BIT]) = STM-1 RLOS (Remark7) -- Not Used
					    Bit (47 + [START BIT]) = LAN LINK ALARM (Remark7)
					    Bit (48 + [START BIT]) = LOF1 (Remark7)
					    Bit (49 + [START BIT]) = LOF2 (Remark7)
					    Bit (50 + [START BIT]) = X REF ALARM1 (Remark7) -- Not Used
					    Bit (51 + [START BIT]) = X REF ALARM2 (Remark7) -- Not Used
					    Bit (52 + [START BIT]) = X CTRL ALARM1 (Remark7) -- Not Used
					    Bit (53 + [START BIT]) = X CTRL ALARM2 (Remark7) -- Not Used
					    Bit (54 + [START BIT]) = SC LAN LINK ALARM (Remark7) -- Not Used
					    Bit (55 + [START BIT]) = WS INPUT LOSS (Remark7) -- Not Used
					    Bit (56 + [START BIT]) = CLUSTER ALARM1 (Remark6)
					    Bit (57 + [START BIT]) = CLUSTER ALARM2 (Remark5)
					    Bit (58 + [START BIT]) = CLUSTER ALARM3 (Remark4)
					    Bit (59 + [START BIT]) = CLUSTER ALARM4 (Remark3)
					    Bit (60 + [START BIT]) = HK1 OUTPUT (Remark6)
					    Bit (61 + [START BIT]) = HK2 OUTPUT (Remark5)
					    Bit (62 + [START BIT]) = HK3 OUTPUT (Remark4)
					    Bit (63 + [START BIT]) = HK4 OUTPUT (Remark3)
					
					  Remark1 : The value of Relay 1 is fixed to  1. 
					            The value of the other Relay is fixed to 0.
					  Remark2 : The value of Relay 3 is fixed to 1. 
					            The value of the other Relay is fixed to 0.
					  Remark3 : The value of Relay 3 is fixed to 1. 
					            The value of the other Relay is fixed to 0.
					  Remark4 : The value of Relay 4 is fixed to 1. 
					            The value of the other Relay is fixed to 0.
					  Remark5 : The value of Relay 5 is fixed to 1. 
					            The value of the other Relay is fixed to 0.
					  Remark6 : The value of Relay 6 is fixed to 1. 
					            The value of the other Relay is fixed to 0.
					  Remark7 : The value of Relay 1 and Relay 2 is fixed to 0. 
					            The value of the other Relay is 0 and 1.
					"
		::= { pnCPVEventTrapItemVar 38 }

	eventItemPnCPVRelayClusterAssign OBJECT-TYPE
		SYNTAX		OCTET STRING (SIZE (4))
		ACCESS		read-only
		STATUS		mandatory
		DESCRIPTION	"CLUSTER INPUT
					  0:Invalid,
					  1:Disabled,
					  2:Enabled)
					
					  [Description]
					  Byte 0 = CLUSTER1 INPUT (0:Invalid, 1:Disabled, 2:Enabled)
					  Byte 1 = CLUSTER2 INPUT
					  Byte 2 = CLUSTER3 INPUT
					  Byte 3 = CLUSTER4 INPUT"
		::= { pnCPVEventTrapItemVar 39 }

	eventItemPnCPVTCNTreshold15minTotal OBJECT-TYPE
		SYNTAX		OCTET STRING (SIZE (24))
		ACCESS		read-only
		STATUS		mandatory
		DESCRIPTION	"TCN THRESHOLD 15MIN TOTAL
					  [Description]
					  (Byte 0 - Byte 3)   = OFS TCN THRESHOLD TOTAL-15min (0 - 900)
					  (Byte 4 - Byte 7)   = UAS TCN THRESHOLD TOTAL-15min (0 - 900)
					  (Byte 8 - Byte 11)  = ES TCN THRESHOLD TOTAL-15min  (0 - 900)
					  (Byte 12 - Byte 15) = SES TCN THRESHOLD TOTAL-15min (0 - 900)
					  (Byte 16 - Byte 19) = BBE TCN THRESHOLD TOTAL-15min 
					                        (PDH(Bit Rate = 10MB)  : 0 - 804600  
					                        PDH(Bit Rate = 20MB)  : 0 - 804600
					                        PDH(Bit Rate = 40MB)  : 0 - 804600)
					  (Byte 20 - Byte 23) = SEP TCN THRESHOLD TOTAL-15min (0 - 900)"
		::= { pnCPVEventTrapItemVar 40 }

	eventItemPnCPVTCNTreshold15minCH OBJECT-TYPE
		SYNTAX		OCTET STRING (SIZE (24))
		ACCESS		read-only
		STATUS		mandatory
		DESCRIPTION	"This item is not used.
				  TCN THRESHOLD 15MIN CH
				  This item is available in PDH system.
					  [Description]
					  (Byte 0 - Byte 3)   = (Fixed to 0)
					  (Byte 4 - Byte 7)   = UAS TCN THRESHOLD TOTAL-15min (0 - 900)
					  (Byte 8 - Byte 11)  = ES TCN THRESHOLD TOTAL-15min  (0 - 900)
					  (Byte 12 - Byte 15) = SES TCN THRESHOLD TOTAL-15min (0 - 900)
					  (Byte 16 - Byte 19) = BBE TCN THRESHOLD TOTAL-15min (0 - 402300)
					  (Byte 20 - Byte 23) = SEP TCN THRESHOLD TOTAL-15min (0 - 900)"
		::= { pnCPVEventTrapItemVar 41 }

	eventItemPnCPVTCNTreshold1dayTotal OBJECT-TYPE
		SYNTAX		OCTET STRING (SIZE (24))
		ACCESS		read-only
		STATUS		mandatory
		DESCRIPTION	"TCN THRESHOLD 1DAY TOTAL
					  [Description]
					  (Byte 0 - Byte 3) = OFS TCN THRESHOLD TOTAL-1day (0 - 86400)
					  (Byte 4 - Byte 7) = UAS TCN THRESHOLD TOTAL-1day (0 - 86400)
					  (Byte 8 - Byte 11) = ES TCN THRESHOLD TOTAL-1day (0 - 86400)
					  (Byte 12 - Byte 15) = SES TCN THRESHOLD TOTAL-1day (0 - 86400)
					  (Byte 16 - Byte 19) = BBE TCN THRESHOLD TOTAL-1day 
					                        (PDH(Bit Rate = 10MB)  : 0 - 77241600
					                        PDH(Bit Rate = 20MB)  : 0 - 77241600
					                        PDH(Bit Rate = 40MB)  : 0 - 77241600)
					  (Byte 20 - Byte 23) = SEP TCN THRESHOLD TOTAL-1day (0 - 86400)"
		::= { pnCPVEventTrapItemVar 42 }

	eventItemPnCPVTCNTreshold1dayCH OBJECT-TYPE
		SYNTAX		OCTET STRING (SIZE (24))
		ACCESS		read-only
		STATUS		mandatory
		DESCRIPTION	"This item is not used.
				TCN THRESHOLD 1DAY CH
				 This item is available in PDH system.
					
					  [Description]
					  (Byte 0 - Byte 3)   = (Fixed to 0)
					  (Byte 4 - Byte 7)   = UAS TCN THRESHOLD TOTAL-1day (0 - 86400)
					  (Byte 8 - Byte 11)  = ES TCN THRESHOLD TOTAL-1day  (0 - 86400)
					  (Byte 12 - Byte 15) = SES TCN THRESHOLD TOTAL-1day (0 - 86400)
					  (Byte 16 - Byte 19) = BBE TCN THRESHOLD TOTAL-1day (0 - 38620800)
					  (Byte 20 - Byte 23) = SEP TCN THRESHOLD TOTAL-1day (0 - 86400)"

		::= { pnCPVEventTrapItemVar 43 }















	eventItemPnCPVEOWIntfcType OBJECT-TYPE
		SYNTAX		INTEGER (0..2)
		ACCESS		read-only
		STATUS		mandatory
		DESCRIPTION	"EOW2 EXTERNAL SETTING
					  0:Invalid,
					  1:Normal,
					  2:Invert"
		::= { pnCPVEventTrapItemVar 46 }

	eventItemPnCPVAlarmCorrelation OBJECT-TYPE
		SYNTAX		INTEGER (0..2)
		ACCESS		read-only
		STATUS		mandatory
		DESCRIPTION	"ALARM CORRELATION CAPABILITY
					  0:Invalid,
					  1:Off,
					  2:On"
		::= { pnCPVEventTrapItemVar 47 }

	eventItemPnCPVPmonSelect OBJECT-TYPE
		SYNTAX		OCTET STRING (SIZE (10))
		ACCESS		read-only
		STATUS		mandatory
		DESCRIPTION	"PMON SELECT
					  [Description]
					  Byte 0 = SES COUNT ACTIVATION (1:30[%], 2:15[%])
					  Byte 1 = SES COUNT ACTIVATION (1:30[%], 2:15[%]) --Not used
					  Byte 2 = PMON E1-A SELECT (0:Not Select, x: CHx(x:1-16))
					  Byte 3 = PMON E1-B SELECT (0:Not Select, x: CHx(x:1-16))
					  Byte 4 = PMON E1-C SELECT (0:Not Select, x: CHx(x:1-16))
					  Byte 5 = PMON E1-D SELECT (0:Not Select, x: CHx(x:1-16))
					  Byte 6 = RX LEVEL TCN THRESHOLD(No.1) integral number
					           (signed char: -128 - 127)
					  Byte 7 = RX LEVEL TCN THRESHOLD(No.1)a place of decimal
					           (0-9)
					  Byte 6 = RX LEVEL TCN THRESHOLD(No.2) integral number
					           (signed char: -128 - 127)
					  Byte 7 = RX LEVEL TCN THRESHOLD(No.2)a place of decimal
					           (0-9)
					
					  *) The values of No.2 side are fixed to 0 when
					     Redundancy is 1+0 TERM."
		::= { pnCPVEventTrapItemVar 48 }

	eventItemPnCPVMaintMode OBJECT-TYPE
		SYNTAX		OffOnValue
		ACCESS		read-only
		STATUS		mandatory
		DESCRIPTION	"MAINTENANCE
					  0:Invalid,
					  1:Off,
					  2:On"
		::= { pnCPVEventTrapItemVar 49 }

	eventItemPnCPVMaintLoopback1CH OBJECT-TYPE
		SYNTAX		OCTET STRING (SIZE (6))
		ACCESS		read-only
		STATUS		mandatory
		DESCRIPTION	"MAIN CH LOOPBACK-1(CHxx)
					(xx:01-16)
					  0:Off,
					  1:On
					
					  [Description]
					  Bit 0 = MAIN CH LOOPBACK-1(CH01) (0:Off, 1:On)
					  Bit 1 = MAIN CH LOOPBACK-1(CH02)
					  ...
					  Bit 14 = MAIN CH LOOPBACK-1(CH15) for E1 interface
					  Bit 15 = MAIN CH LOOPBACK-1(CH16) for E1 interface
					
					  *) The value of CHxx is fixed to 0, when CHxx Usage is not used. (xx: 01 - 16)"
		::= { pnCPVEventTrapItemVar 53 }

	eventItemPnCPVMaintLoopback2CH OBJECT-TYPE
		SYNTAX		OCTET STRING (SIZE (6))
		ACCESS		read-only
		STATUS		mandatory
		DESCRIPTION	"MAIN CH LOOPBACK-2(CHxx)
					(xx:01-16)
					  0:Off,
					  1:On
					
					  [Description]
					  Bit 0 = MAIN CH LOOPBACK-2(CH01) (0:Off, 1:On)
					  Bit 1 = MAIN CH LOOPBACK-2(CH02)
					  ...
					  Bit 14 = MAIN CH LOOPBACK-2(CH15) for E1 interface
					  Bit 15 = MAIN CH LOOPBACK-2(CH16) for E1 interface
					
					  *) The value of CHxx is fixed to 0, when CHxx Usage is not used. (xx: 01 - 16)"
		::= { pnCPVEventTrapItemVar 54 }

	eventItemPnCPVMaintDADEAdjust OBJECT-TYPE
		SYNTAX		INTEGER (0..3)
		ACCESS		read-only
		STATUS		mandatory
		DESCRIPTION	"This item is not used. 
					  DADE ADJUST
					  0:Invalid,
					  1:DADE,
					  2:Off Set DADE,
					  3:DADE OFF"
		::= { pnCPVEventTrapItemVar 57 }

	eventItemPnCPVMaintDADEAdjustEn OBJECT-TYPE
		SYNTAX		INTEGER (0..2)
		ACCESS		read-only
		STATUS		mandatory
		DESCRIPTION	"This item is not used.   
					  DADE ADJUST ENABLE
					  0:Invalid,
					  1:Off,
					  2:Executing DADE Adjust"
		::= { pnCPVEventTrapItemVar 58 }

	eventItemPnCPVMaintLanDeviceReset OBJECT-TYPE
		SYNTAX		INTEGER (0..7)
		ACCESS		read-only
		STATUS		mandatory
		DESCRIPTION	"This item is not used.  
					  LAN DEVICE RESET
					  0:Invalid,
					  1:Not Selected,
					  2:INTFC1(Port1),
					  3:INTFC1(Port2),
				 This item is available for LAN interface."
		::= { pnCPVEventTrapItemVar 59 }

	eventItemPnCPVMaintATPCManualControl OBJECT-TYPE
		SYNTAX		OffOnValue
		ACCESS		read-only
		STATUS		mandatory
		DESCRIPTION	"ATPC MANUAL CONTROL
				 Refer to OffOnValue of TEXTUAL-CONVENTION"
		::= { pnCPVEventTrapItemVar 62 }

	eventItemPnCPVMaintATPCManualContPower OBJECT-TYPE
		SYNTAX		INTEGER
		ACCESS		read-only
		STATUS		mandatory
		DESCRIPTION	"ATPC MANUAL POWER[dB]"
		::= { pnCPVEventTrapItemVar 63 }

	eventItemPnCPVMaintTxMuteControl OBJECT-TYPE
		SYNTAX		OffOnValue
		ACCESS		read-only
		STATUS		mandatory
		DESCRIPTION	"TX MUTE CONTROL
				 Refer to OffOnValue of TEXTUAL-CONVENTION"
		::= { pnCPVEventTrapItemVar 64 }

	eventItemPnCPVMaintTxMuteContReleaseTime OBJECT-TYPE
		SYNTAX		INTEGER
		ACCESS		read-only
		STATUS		mandatory
		DESCRIPTION	"TX MUTE OFF TIMER[sec]"
		::= { pnCPVEventTrapItemVar 65 }

	eventItemPnCPVMaintCW OBJECT-TYPE
		SYNTAX		OffOnValue
		ACCESS		read-only
		STATUS		mandatory
		DESCRIPTION	"CW CONTROL
				Refer to OffOnValue of TEXTUAL-CONVENTION "
		::= { pnCPVEventTrapItemVar 66 }

	eventItemPnCPVMaintForcedLinearizerCont OBJECT-TYPE
		SYNTAX		INTEGER (0..2)
		ACCESS		read-only
		STATUS		mandatory
		DESCRIPTION	"LINEARIZER CONTROL
					  0:Invalid,
					  1:Auto,
					  2:Force Reset"
		::= { pnCPVEventTrapItemVar 69 }

	eventItemPnCPVMaintRFShiftFreqSet OBJECT-TYPE
		SYNTAX		DisplayString (SIZE (4))
		ACCESS		read-only
		STATUS		mandatory
		DESCRIPTION	"This item is not used.  
					 RF SHIFT FREQUENCY[MHz]
					 This value is only 1008 or 1010"
		::= { pnCPVEventTrapItemVar 71 }

	eventItemPnCPVMaintAntennaAlignMode OBJECT-TYPE
		SYNTAX		OffOnValue
		ACCESS		read-only
		STATUS		mandatory
		DESCRIPTION	"ANTENNA ALIGNMENT MODE
				Refer to OffOnValue of TEXTUAL-CONVENTION "
		::= { pnCPVEventTrapItemVar 72 }

	eventItemPnCPVinvUpdateMainWorkModule OBJECT-TYPE
		SYNTAX		INTEGER (0..12)
		ACCESS		read-only
		STATUS		mandatory
		DESCRIPTION	"Main Work Module
					  0:INVALID, 
					  1:BLANK,
					  2:16xE1 BASIC PKG,
					  3:16xE1 STANDARD PKG(E/W LAN),
					  14:5xE1 BASIC PGK"
		::= { pnCPVEventTrapItemVar 73 }

	eventItemPnCPVinvUpdateSummary OBJECT-TYPE
		SYNTAX		OCTET STRING (SIZE (2))
		ACCESS		read-only
		STATUS		mandatory
		DESCRIPTION	"Update Summary
					
					  [Description]
					  Bit 0 = CTRL (0:Not Update, 1:Updated)
					  Bit 1 = MODEM1
					  Bit 2 = MODEM2
					  Bit 3 = INTFC
					  Bit 5 = ODU1
					  Bit 6 = ODU2
					  Bit 7 = CTRL PROGRAM VERSION
					  Bit 8 = TRU PROVISIONING INFO
					  Bit 9 = TRU FREQ INFO
					  Bit 10 = SUPPORTABILITY
					  Bit 11 = (FIXED to 0)
					  Bit 12 = (FIXED to 0)
					  Bit 13 = (FIXED to 0)
					  Bit 14 = (FIXED to 0)
					  Bit 15 = (FIXED to 0)"
		::= { pnCPVEventTrapItemVar 75 }

	eventItemPnCPVLanCollision OBJECT-TYPE
		SYNTAX		INTEGER (0..2)
		ACCESS		read-only
		STATUS		mandatory
		DESCRIPTION	"LAN COLLISION PORTx
					(x : 1-2)
					  0:Invalid,
					  1:Normal,
					  2:Collision"
		::= { pnCPVEventTrapItemVar 76 }

	eventItemPnCPVAtpcPowerModeStatus OBJECT-TYPE
		SYNTAX		INTEGER (0..2)
		ACCESS		read-only
		STATUS		mandatory
		DESCRIPTION	"ATPC POWER MODE
					  0:Invalid,
					  1:Active,
					  2:Stop"
		::= { pnCPVEventTrapItemVar 80 }

	eventItemPnCPVAuxOutput OBJECT-TYPE
		SYNTAX		INTEGER (0..2)
		ACCESS		read-only
		STATUS		mandatory
		DESCRIPTION	"ITEM NAME(OUTPUT-x)
					(x : 1-4)
					  0:Invalid,
					  1:(OFF),
					  2:(ON)"
		::= { pnCPVEventTrapItemVar 81 }

	eventItemPnCPVMMCMount OBJECT-TYPE
		SYNTAX		OffOnValue
		ACCESS		read-only
		STATUS		mandatory
		DESCRIPTION	"MMC MOUNT
				 Refer to OffOnValue of TEXTUAL-CONVENTION"
		::= { pnCPVEventTrapItemVar 82 }

	eventItemPnCPVMaintTxSWMode OBJECT-TYPE
		SYNTAX		INTEGER (0..2)
		ACCESS		read-only
		STATUS		mandatory
		DESCRIPTION     "TX SW MODE
					  0:Invalid,
					  1:Auto(No.1),
					  2:Auto(No.2),
					  3:Manual(No.1),
					  4:Manual(No.2)"
		::= { pnCPVEventTrapItemVar 85 }

	eventItemPnCPVMaintRxSWMode OBJECT-TYPE
		SYNTAX		INTEGER (0..2)
		ACCESS		read-only
		STATUS		mandatory
		DESCRIPTION     "RX SW MODE
					  0:Invalid,
					  1:Auto(No.1),
					  2:Auto(No.2),
					  3:Manual(No.1),
					  4:Manual(No.2)"
		::= { pnCPVEventTrapItemVar 86 }

	pnCPVStatusTrapItemVar OBJECT IDENTIFIER
		::= { pnCPVTrapItemVar 4 }

	statusItemPnCPVAuxInput OBJECT-TYPE
		SYNTAX		INTEGER (0..2)
		ACCESS		read-only
		STATUS		mandatory
		DESCRIPTION	"ITEM NAME(INPUT-x)
					(x : 1-6)
					  0:Invalid,
					  1:Open State,
					  2:Close State
					FLAG=SUMMARY_AUX
					probableCause=invalid"
		::= { pnCPVStatusTrapItemVar 1 }

	pnCPVSystemTrapItemVar OBJECT IDENTIFIER
		::= { pnCPVTrapItemVar 5 }

	systemItemPnCPVLocalUpdate OBJECT-TYPE
		SYNTAX		INTEGER (0..2)
		ACCESS		read-only
		STATUS		mandatory
		DESCRIPTION	"EQUIPMENT CONFIGURATION
					  0:Invalid,
					  1:NO CHANGE,
					  2:UPDATED"
		::= { pnCPVSystemTrapItemVar 2 }

	partialSummaryTrapTRU	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  partialSummaryItemTRU
					}
		DESCRIPTION "This trap is sent
					  when TRU(ODU) Summary status is changed."
		::= 201

	partialSummaryTrapINTFC1	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  partialSummaryItemINTFC1
					}
		DESCRIPTION "This trap is sent
					  when INTFC1 Summary status is changed."
		::= 202

	partialSummaryTrapCTRL	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  partialSummaryItemCTRL
					}
		DESCRIPTION "This trap is sent
					  when CTRL Summary status is changed."
		::= 203

	partialSummaryTrapAux	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  partialSummaryItemAux
					}
		DESCRIPTION "This trap is sent
					  when AUX IO Summary status is changed."
		::= 204

	partialSummaryTrapLpm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  partialSummaryItemLpm
					}
		DESCRIPTION "This trap is sent
					  when Link Pmon Summary status is changed."
		::= 205

	partialSummaryTrapMODEM	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  partialSummaryItemMODEM
					}
		DESCRIPTION "This trap is sent
					  when Modem Summary status is changed."
		::= 207

	alarmTrapPnCPVTxPowerAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTxPowerAlarm
					}
		DESCRIPTION "This trap is sent
					  when TX POWER status is changed."
		::= 301

	alarmTrapPnCPVTxInputAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTxInputAlarm
					}
		DESCRIPTION "This trap is sent
					  when TX INPUT status is changed."
		::= 302

	alarmTrapPnCPVRxLevelAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVRxLevelAlarm
					}
		DESCRIPTION "This trap is sent
					  when RX LEVEL status is changed."
		::= 303

	alarmTrapPnCPVApcAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVApcAlarm
					}
		DESCRIPTION "This trap is sent
					  when APC status is changed."
		::= 304

	alarmTrapPnCPVTRUCPUAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTRUCPUAlarm
					}
		DESCRIPTION "This trap is sent
					  when ODU CPU/CABLE OPEN status is changed."
		::= 305

	alarmTrapPnCPVModemAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVModemAlarm
					}
		DESCRIPTION "This trap is sent
					  when MODEM MODULE status is changed."
		::= 306

	alarmTrapPnCPVModemUneq	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVModemUneq
					}
		DESCRIPTION "This trap is sent
					  when MODEM UNEQUIPPED status is changed."
		::= 307

	alarmTrapPnCPVHighBERAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVHighBERAlarm
					}
		DESCRIPTION "This trap is sent
					  when HIGH BER status is changed."
		::= 308

	alarmTrapPnCPVLowBERAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVLowBERAlarm
					}
		DESCRIPTION "This trap is sent
					  when LOW BER status is changed."
		::= 309

	alarmTrapPnCPVModAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVModAlarm
					}
		DESCRIPTION "This trap is sent
					  when MOD status is changed."
		::= 310

	alarmTrapPnCPVDemAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVDemAlarm
					}
		DESCRIPTION "This trap is sent
					  when DEM status is changed."
		::= 311

	alarmTrapPnCPVXIfLevelAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVXIfLevelAlarm
					}
		DESCRIPTION "This trap is sent
					  when MODEM TYPE MISMATCH status is changed."
		::= 312

	alarmTrapPnCPVPSAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVPSAlarm
					}
		DESCRIPTION "This trap is sent
					  when POWER SUPPLY status is changed."
		::= 314

	alarmTrapPnCPVIfCableShort	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVIfCableShort
					}
		DESCRIPTION "This trap is sent
					  when IF CABLE SHORT status is changed."
		::= 315

	alarmTrapPnCPVLof	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVLof
					}
		DESCRIPTION "This trap is sent
					  when LOF status is changed."
		::= 316

	alarmTrapPnCPVCableEQLAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVCableEQLAlarm
					}
		DESCRIPTION "This trap is sent
					  when CABLE EQL status is changed."
		::= 317

	alarmTrapPnCPVIntfcMAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVIntfcMAlarm
					}
		DESCRIPTION "This trap is sent
					  when INTFC MODULE status is changed."
		::= 319

	alarmTrapPnCPVIntfcMUneq	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVIntfcMUneq
					}
		DESCRIPTION "This trap is sent
					  when INTFC UNEQUIPPED status is changed."
		::= 320

	alarmTrapPnCPVInputLos	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVInputLos
					}
		DESCRIPTION "This trap is sent
					  when INPUT LOS CHxx(xx : 1-16) status is changed."
		::= 321

	alarmTrapPnCPVUsageError	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVUsageError
					}
		DESCRIPTION "This trap is sent
					  when USAGE ERROR CHxx(xx : 1-16) status is changed."
		::= 325

	alarmTrapPnCPVLink	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVLink
					}
		DESCRIPTION "This trap is sent
					  when LAN LINK PORTx(x : 1-2) status is changed."
		::= 326

	alarmTrapPnCPVCTRLAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVCTRLAlarm
					}
		DESCRIPTION "This trap is sent
					  when CTRL/CTRL MODULE status is changed."
		::= 342

	alarmTrapPnCPVTcn15minTotalOFS	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn15minTotalOFS
					}
		DESCRIPTION "This trap is sent
					  when TCN-OFS-15min TOTAL status is changed."
		::= 346

	alarmTrapPnCPVTcn15minTotalUAS	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn15minTotalUAS
					}
		DESCRIPTION "This trap is sent
					  when TCN-UAS-15min TOTAL status is changed."
		::= 347

	alarmTrapPnCPVTcn15minTotalES	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn15minTotalES
					}
		DESCRIPTION "This trap is sent
					  when TCN-ES-15min TOTAL status is changed."
		::= 348

	alarmTrapPnCPVTcn15minTotalSES	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn15minTotalSES
					}
		DESCRIPTION "This trap is sent
					  when TCN-SES-15min TOTAL status is changed."
		::= 349

	alarmTrapPnCPVTcn15minTotalBBE	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn15minTotalBBE
					}
		DESCRIPTION "This trap is sent
					  when TCN-BBE-15min TOTAL status is changed."
		::= 350

	alarmTrapPnCPVTcn15minTotalSEP	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn15minTotalSEP
					}
		DESCRIPTION "This trap is sent
					  when TCN-SEP-15min TOTAL status is changed."
		::= 351

	alarmTrapPnCPVTcn15minCHUAS	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn15minCHUAS
					}
		DESCRIPTION "This item is not used.
					 This trap is sent
					  when TCN-UAS-15min CHxx(xx : 1-16 only selected 4ch.)
					  status is changed."
		::= 353

	alarmTrapPnCPVTcn15minCHES	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn15minCHES
					}
		DESCRIPTION "This item is not used. 
					 This trap is sent
					  when TCN-ES-15min CHxx(xx : 1-16 only selected 4ch.)
					  status is changed."
		::= 354

	alarmTrapPnCPVTcn15minCHSES	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn15minCHSES
					}
		DESCRIPTION "This item is not used. 
					 This trap is sent
					  when TCN-SES-15min CHxx(xx : 1-16 only selected 4ch.)
					  status is changed."
		::= 355

	alarmTrapPnCPVTcn15minCHBBE	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn15minCHBBE
					}
		DESCRIPTION "This item is not used. 
					 This trap is sent
					  when TCN-BBE-15min CHxx(xx : 1-16 only selected 4ch.)
					  status is changed."
		::= 356

	alarmTrapPnCPVTcn15minCHSEP	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn15minCHSEP
					}
		DESCRIPTION "This item is not used. 
					 This trap is sent
					  when TCN-SEP-15min CHxx(xx : 1-16 only selected 4ch.)
					  status is changed."
		::= 357

	alarmTrapPnCPVTcn1dayTotalOFS	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn1dayTotalOFS
					}
		DESCRIPTION "This trap is sent
					  when TCN-OFS-1day TOTAL status is changed."
		::= 358

	alarmTrapPnCPVTcn1dayTotalUAS	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn1dayTotalUAS
					}
		DESCRIPTION "This trap is sent
					  when TCN-UAS-1day TOTAL status is changed."
		::= 359

	alarmTrapPnCPVTcn1dayTotalES	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn1dayTotalES
					}
		DESCRIPTION "This trap is sent
					  when TCN-ES-1day TOTAL status is changed."
		::= 360

	alarmTrapPnCPVTcn1dayTotalSES	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn1dayTotalSES
					}
		DESCRIPTION "This trap is sent
					  when TCN-SES-1day TOTAL status is changed."
		::= 361

	alarmTrapPnCPVTcn1dayTotalBBE	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn1dayTotalBBE
					}
		DESCRIPTION "This trap is sent
					  when TCN-BBE-1day TOTAL status is changed."
		::= 362

	alarmTrapPnCPVTcn1dayTotalSEP	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn1dayTotalSEP
					}
		DESCRIPTION "This trap is sent
					  when TCN-SEP-1day TOTAL status is changed."
		::= 363

	alarmTrapPnCPVTcn1dayCHUAS	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn1dayCHUAS
					}
		DESCRIPTION "This item is not used. 
					 This trap is sent
					  when TCN-UAS-1day CHxx(xx : 1-16 only selected 4ch.)
					  status is changed."
		::= 365

	alarmTrapPnCPVTcn1dayCHES	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn1dayCHES
					}
		DESCRIPTION "This item is not used. 
					 This trap is sent
					  when TCN-ES-1day CHxx(xx : 1-16 only selected 4ch.)
					  status is changed."
		::= 366

	alarmTrapPnCPVTcn1dayCHSES	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn1dayCHSES
					}
		DESCRIPTION "This item is not used.
					 This trap is sent
					  when TCN-SES-1day CHxx(xx : 1-16 only selected 4ch.)
					  status is changed."
		::= 367

	alarmTrapPnCPVTcn1dayCHBBE	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn1dayCHBBE
					}
		DESCRIPTION "This item is not used. 
					 This trap is sent
					  when TCN-BBE-1day CHxx(xx : 1-16 only selected 4ch.)
					  status is changed."
		::= 368

	alarmTrapPnCPVTcn1dayCHSEP	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcn1dayCHSEP
					}
		DESCRIPTION "This item is not used. 
					 This trap is sent
					  when TCN-SEP-1day CHxx(xx : 1-16 only selected 4ch.)
					  status is changed."
		::= 369

	alarmTrapPnCPVTcnTCS15minRxLev	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcnTCS15minRxLev
					}
		DESCRIPTION "This trap is sent
					  when TCN-RX LEV-15min status is changed."
		::= 372

	alarmTrapPnCPVTcnTCS1dayRxLev	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTcnTCS1dayRxLev
					}
		DESCRIPTION "This trap is sent
					  when TCN-RX LEV-1day status is changed."
		::= 373

	alarmTrapPnCPVTRULORefAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVTRULORefAlarm
					}
		DESCRIPTION "This trap is sent
					  when ODU TYPE MISMATCH status is changed."
		::= 374

	alarmTrapPnCPVAuxClusterAlarm	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVAuxClusterAlarm
					}
		DESCRIPTION "This trap is sent
					  when AUX Cluster Alarm Index status is changed.
					 This is not used. 
					  when CLUSTERx ALARM(x : 1-4) status is changed."
		::= 384

	alarmTrapPnCPVLinearizerFail	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVLinearizerFail
					}
		DESCRIPTION "This trap is sent
					  when LINEARIZER status is changed."
		::= 385

	alarmTrapPnCPVRouteID	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVRouteID
					}
		DESCRIPTION "This trap is sent
					  when FRAME ID status is changed."
		::= 386

	alarmTrapPnCPVEarlyWarning	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVEarlyWarning
					}
		DESCRIPTION "This trap is sent
					  when EARLY WARNING status is changed."
		::= 387

	alarmTrapPnCPVInputVoltage	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVInputVoltage
					}
		DESCRIPTION "This trap is sent
					  when INPUT VOLTAGE status is changed."
		::= 388

	alarmTrapPnCPVIntfcMTypeMismatch	TRAP-TYPE
		ENTERPRISE	pasolinkNeoCpv
		VARIABLES	{
					  pnTrapSequenceNumber,
					  pnTrapDate,
					  pnTrapTime,
					  pnSeverity,
					  pnAlarmType,
					  pnProbableCause,
					  pnTrapSource,
					  alarmItemPnCPVIntfcMTypeMismatch
					}
		DESCRIPTION "This trap is sent
					  when INTFC TYPE MISMATCH status is changed."
		::= 389

	eventTrapPnCPVTxMuteStatus	TRAP-TYPE
		ENTERPRISE	pasolinkNeoCpv
		VARIABLES	{
					  pnTrapSequenceNumber,
					  pnTrapDate,
					  pnTrapTime,
					  pnTrapSource,
					  eventItemPnCPVTxMuteStatus
					}
		DESCRIPTION "This trap is sent
					  when MUTE STATUS status is changed."
		::= 403

	eventTrapPnCPVTxSWStatus	TRAP-TYPE
		ENTERPRISE	pasolinkNeoCpv
		VARIABLES	{
					  pnTrapSequenceNumber,
					  pnTrapDate,
					  pnTrapTime,
					  pnTrapSource,
					  eventItemPnCPVTxSWStatus
					}
		DESCRIPTION "This trap is sent
					  when TX SW STATUS status is changed."
		::= 404

	eventTrapPnCPVRxSWStatus	TRAP-TYPE
		ENTERPRISE	pasolinkNeoCpv
		VARIABLES	{
					  pnTrapSequenceNumber,
					  pnTrapDate,
					  pnTrapTime,
					  pnTrapSource,
					  eventItemPnCPVRxSWStatus
					}
		DESCRIPTION "This trap is sent
					  when RX SW STATUS status is changed."
		::= 406

	eventTrapPnCPVLinearizerFunc	TRAP-TYPE
		ENTERPRISE	pasolinkNeoCpv
		VARIABLES	{
					  pnTrapSequenceNumber,
					  pnTrapDate,
					  pnTrapTime,
					  pnTrapSource,
					  eventItemPnCPVLinearizerFunc
					}
		DESCRIPTION "This trap is sent
					  when LINEARIZER FUNCTION status is changed."
		::= 408

	eventTrapPnCPVAisGeneratedCH	TRAP-TYPE
		ENTERPRISE	pasolinkNeoCpv
		VARIABLES	{
					  pnTrapSequenceNumber,
					  pnTrapDate,
					  pnTrapTime,
					  pnTrapSource,
					  eventItemPnCPVAisGeneratedCH
					}
		DESCRIPTION "This trap is sent
					  when AIS GENERATED CHxx(xx : 1-16) status is changed."
		::= 411

	eventTrapPnCPVAisReceivedCH	TRAP-TYPE
		ENTERPRISE	pasolinkNeoCpv
		VARIABLES	{
					  pnTrapSequenceNumber,
					  pnTrapDate,
					  pnTrapTime,
					  pnTrapSource,
					  eventItemPnCPVAisReceivedCH
					}
		DESCRIPTION "This trap is sent
					  when AIS RECEIVED CHxx(xx : 1-16) status is changed."
		::= 412

	eventTrapPnCPVLinkLossForward	TRAP-TYPE
		ENTERPRISE	pasolinkNeoCpv
		VARIABLES	{
					  pnTrapSequenceNumber,
					  pnTrapDate,
					  pnTrapTime,
					  pnTrapSource,
					  eventItemPnCPVLinkLossForward
					}
		DESCRIPTION "This trap is sent
					  when LLF PORTx(x : 1-2) status is changed."
		::= 413

	eventTrapPnCPVSpeedDuplex	TRAP-TYPE
		ENTERPRISE	pasolinkNeoCpv
		VARIABLES	{
					  pnTrapSequenceNumber,
					  pnTrapDate,
					  pnTrapTime,
					  pnTrapSource,
					  eventItemPnCPVSpeedDuplex
					}
		DESCRIPTION "This trap is sent
					  when LAN MODE PORTx(x : 1-2) status is changed."
		::= 414

	eventTrapPnCPVInphaseWork	TRAP-TYPE
		ENTERPRISE	pasolinkNeoCpv
		VARIABLES	{
					  pnTrapSequenceNumber,
					  pnTrapDate,
					  pnTrapTime,
					  pnTrapSource,
					  eventItemPnCPVInphaseWork
					}
		DESCRIPTION "This trap is sent
					  when INTFC INPHASE status is changed."
		::= 415

	eventTrapPnCPVCHUsage	TRAP-TYPE
		ENTERPRISE	pasolinkNeoCpv
		VARIABLES	{
					  pnTrapSequenceNumber,
					  pnTrapDate,
					  pnTrapTime,
					  pnTrapSource,
					  eventItemPnCPVCHUsage
					}
		DESCRIPTION "This trap is sent
					  when CH USAGE(CHxx)(xx : 1-16) status is changed."
		::= 420

	eventTrapPnCPVCHCondition	TRAP-TYPE
		ENTERPRISE	pasolinkNeoCpv
		VARIABLES	{
					  pnTrapSequenceNumber,
					  pnTrapDate,
					  pnTrapTime,
					  pnTrapSource,
					  eventItemPnCPVCHCondition
					}
		DESCRIPTION "This trap is sent
					  when CH CONDITION status is changed."
		::= 421

	eventTrapPnCPVCHImpedance	TRAP-TYPE
		ENTERPRISE	pasolinkNeoCpv
		VARIABLES	{
					  pnTrapSequenceNumber,
					  pnTrapDate,
					  pnTrapTime,
					  pnTrapSource,
					  eventItemPnCPVCHImpedance
					}
		DESCRIPTION "This trap is sent
					  when E1 PORT IMPEDANCE status is changed."
		::= 422

	eventTrapPnCPVBERThreshold	TRAP-TYPE
		ENTERPRISE	pasolinkNeoCpv
		VARIABLES	{
					  pnTrapSequenceNumber,
					  pnTrapDate,
					  pnTrapTime,
					  pnTrapSource,
					  eventItemPnCPVBERThreshold
					}
		DESCRIPTION "This trap is sent
					  when BER THRESHOLD SETTING status is changed."
		::= 427

	eventTrapPnCPVSCAssign	TRAP-TYPE
		ENTERPRISE	pasolinkNeoCpv
		VARIABLES	{
					  pnTrapSequenceNumber,
					  pnTrapDate,
					  pnTrapTime,
					  pnTrapSource,
					  eventItemPnCPVSCAssign
					}
		DESCRIPTION "This trap is sent
					  when SC ASSIGNMENT status is changed."
		::= 429

	eventTrapPnCPVLanPortSetting	TRAP-TYPE
		ENTERPRISE	pasolinkNeoCpv
		VARIABLES	{
					  pnTrapSequenceNumber,
					  pnTrapDate,
					  pnTrapTime,
					  pnTrapSource,
					  eventItemPnCPVLanPortSetting
					}
		DESCRIPTION "This trap is sent
					  when LAN PORT SETTING status is changed."
		::= 430

	eventTrapPnCPVTxPowerContValue	TRAP-TYPE
		ENTERPRISE	pasolinkNeoCpv
		VARIABLES	{
					  pnTrapSequenceNumber,
					  pnTrapDate,
					  pnTrapTime,
					  pnTrapSource,
					  eventItemPnCPVTxPowerContValue
					}
		DESCRIPTION "This trap is sent
					  when TX POWER CTRL status is changed."
		::= 432

	eventTrapPnCPVSWCondTxRx	TRAP-TYPE
		ENTERPRISE	pasolinkNeoCpv
		VARIABLES	{
					  pnTrapSequenceNumber,
					  pnTrapDate,
					  pnTrapTime,
					  pnTrapSource,
					  eventItemPnCPVSWCondTxRx
					}
		DESCRIPTION "This trap is sent
					  when CONDITION for TX/RX SW status is changed."
		::= 436

	eventTrapPnCPVRelayConfigData	TRAP-TYPE
		ENTERPRISE	pasolinkNeoCpv
		VARIABLES	{
					  pnTrapSequenceNumber,
					  pnTrapDate,
					  pnTrapTime,
					  pnTrapSource,
					  eventItemPnCPVRelayConfigData
					}
		DESCRIPTION "This trap is sent
					  when RELAY CONFIGURATION status is changed."
		::= 438

	eventTrapPnCPVRelayClusterAssign	TRAP-TYPE
		ENTERPRISE	pasolinkNeoCpv
		VARIABLES	{
					  pnTrapSequenceNumber,
					  pnTrapDate,
					  pnTrapTime,
					  pnTrapSource,
					  eventItemPnCPVRelayClusterAssign
					}
		DESCRIPTION "This trap is sent
					  when CLUSTER INPUT status is changed."
		::= 439

	eventTrapPnCPVTCNTreshold15minTotal	TRAP-TYPE
		ENTERPRISE	pasolinkNeoCpv
		VARIABLES	{
					  pnTrapSequenceNumber,
					  pnTrapDate,
					  pnTrapTime,
					  pnTrapSource,
					  eventItemPnCPVTCNTreshold15minTotal
					}
		DESCRIPTION "This trap is sent
					  when TCN THRESHOLD 15MIN TOTAL status is changed."
		::= 440

	eventTrapPnCPVTCNTreshold15minCH	TRAP-TYPE
		ENTERPRISE	pasolinkNeoCpv
		VARIABLES	{
					  pnTrapSequenceNumber,
					  pnTrapDate,
					  pnTrapTime,
					  pnTrapSource,
					  eventItemPnCPVTCNTreshold15minCH
					}
		DESCRIPTION "This item is not used. 
					 This trap is sent
					  when TCN THRESHOLD 15MIN CH status is changed."
		::= 441

	eventTrapPnCPVTCNTreshold1dayTotal	TRAP-TYPE
		ENTERPRISE	pasolinkNeoCpv
		VARIABLES	{
					  pnTrapSequenceNumber,
					  pnTrapDate,
					  pnTrapTime,
					  pnTrapSource,
					  eventItemPnCPVTCNTreshold1dayTotal
					}
		DESCRIPTION "This trap is sent
					  when TCN THRESHOLD 1DAY TOTAL status is changed."
		::= 442

	eventTrapPnCPVTCNTreshold1dayCH	TRAP-TYPE
		ENTERPRISE	pasolinkNeoCpv
		VARIABLES	{
					  pnTrapSequenceNumber,
					  pnTrapDate,
					  pnTrapTime,
					  pnTrapSource,
					  eventItemPnCPVTCNTreshold1dayCH
					}
		DESCRIPTION "This item is not used. 
					 This trap is sent
					  when TCN THRESHOLD 1day CH status is changed."
		::= 443















	eventTrapPnCPVEOWIntfcType	TRAP-TYPE
		ENTERPRISE	pasolinkNeoCpv
		VARIABLES	{
					  pnTrapSequenceNumber,
					  pnTrapDate,
					  pnTrapTime,
					  pnTrapSource,
					  eventItemPnCPVEOWIntfcType
					}
		DESCRIPTION "This trap is sent
					  when EOW2 EXTERNAL SETTING status is changed."
		::= 446

	eventTrapPnCPVAlarmCorrelation	TRAP-TYPE
		ENTERPRISE	pasolinkNeoCpv
		VARIABLES	{
					  pnTrapSequenceNumber,
					  pnTrapDate,
					  pnTrapTime,
					  pnTrapSource,
					  eventItemPnCPVAlarmCorrelation
					}
		DESCRIPTION "This trap is sent
					  when ALARM CORRELATION CAPABILITY status is changed."
		::= 447

	eventTrapPnCPVPmonSelect	TRAP-TYPE
		ENTERPRISE	pasolinkNeoCpv
		VARIABLES	{
					  pnTrapSequenceNumber,
					  pnTrapDate,
					  pnTrapTime,
					  pnTrapSource,
					  eventItemPnCPVPmonSelect
					}
		DESCRIPTION "This trap is sent
					  when PMON SELECT status is changed."
		::= 448

	eventTrapPnCPVMaintMode	TRAP-TYPE
		ENTERPRISE	pasolinkNeoCpv
		VARIABLES	{
					  pnTrapSequenceNumber,
					  pnTrapDate,
					  pnTrapTime,
					  pnTrapSource,
					  eventItemPnCPVMaintMode
					}
		DESCRIPTION "This trap is sent
					  when MAINTENANCE status is changed."
		::= 449

	eventTrapPnCPVMaintLoopback1CH	TRAP-TYPE
		ENTERPRISE	pasolinkNeoCpv
		VARIABLES	{
					  pnTrapSequenceNumber,
					  pnTrapDate,
					  pnTrapTime,
					  pnTrapSource,
					  eventItemPnCPVMaintLoopback1CH
					}
		DESCRIPTION "This trap is sent
					  when MAIN CH LOOPBACK-1(CHxx)(xx:01-16) status is changed."
		::= 453

	eventTrapPnCPVMaintLoopback2CH	TRAP-TYPE
		ENTERPRISE	pasolinkNeoCpv
		VARIABLES	{
					  pnTrapSequenceNumber,
					  pnTrapDate,
					  pnTrapTime,
					  pnTrapSource,
					  eventItemPnCPVMaintLoopback2CH
					}
		DESCRIPTION "This trap is sent
					  when MAIN CH LOOPBACK-2(CHxx)(xx:01-16)
					  status is changed."
		::= 454

	eventTrapPnCPVMaintDADEAdjust	TRAP-TYPE
		ENTERPRISE	pasolinkNeoCpv
		VARIABLES	{
					  pnTrapSequenceNumber,
					  pnTrapDate,
					  pnTrapTime,
					  pnTrapSource,
					  eventItemPnCPVMaintDADEAdjust
					}
		DESCRIPTION "This item is not used. 
					 This trap is sent
					  when DADE ADJUST status is changed."
		::= 457

	eventTrapPnCPVMaintDADEAdjustEn	TRAP-TYPE
		ENTERPRISE	pasolinkNeoCpv
		VARIABLES	{
					  pnTrapSequenceNumber,
					  pnTrapDate,
					  pnTrapTime,
					  pnTrapSource,
					  eventItemPnCPVMaintDADEAdjustEn
					}
		DESCRIPTION "This item is not used. 
					 This trap is sent
					  when DADE ADJUST ENABLE status is changed."
		::= 458

	eventTrapPnCPVMaintLanDeviceReset	TRAP-TYPE
		ENTERPRISE	pasolinkNeoCpv
		VARIABLES	{
					  pnTrapSequenceNumber,
					  pnTrapDate,
					  pnTrapTime,
					  pnTrapSource,
					  eventItemPnCPVMaintLanDeviceReset
					}
		DESCRIPTION "This item is not used. 
					 This trap is sent
					  when LAN DEVICE RESET status is changed."
		::= 459

	eventTrapPnCPVMaintATPCManualControl	TRAP-TYPE
		ENTERPRISE	pasolinkNeoCpv
		VARIABLES	{
					  pnTrapSequenceNumber,
					  pnTrapDate,
					  pnTrapTime,
					  pnTrapSource,
					  eventItemPnCPVMaintATPCManualControl
					}
		DESCRIPTION "This trap is sent
					  when ATPC MANUAL CONTROL status is changed."
		::= 462

	eventTrapPnCPVMaintATPCManualContPower	TRAP-TYPE
		ENTERPRISE	pasolinkNeoCpv
		VARIABLES	{
					  pnTrapSequenceNumber,
					  pnTrapDate,
					  pnTrapTime,
					  pnTrapSource,
					  eventItemPnCPVMaintATPCManualContPower
					}
		DESCRIPTION "This trap is sent
					  when ATPC MANUAL POWER[dB] status is changed."
		::= 463

	eventTrapPnCPVMaintTxMuteControl	TRAP-TYPE
		ENTERPRISE	pasolinkNeoCpv
		VARIABLES	{
					  pnTrapSequenceNumber,
					  pnTrapDate,
					  pnTrapTime,
					  pnTrapSource,
					  eventItemPnCPVMaintTxMuteControl
					}
		DESCRIPTION "This trap is sent
					  when TX MUTE CONTROL status is changed."
		::= 464

	eventTrapPnCPVMaintTxMuteContReleaseTime	TRAP-TYPE
		ENTERPRISE	pasolinkNeoCpv
		VARIABLES	{
					  pnTrapSequenceNumber,
					  pnTrapDate,
					  pnTrapTime,
					  pnTrapSource,
					  eventItemPnCPVMaintTxMuteContReleaseTime
					}
		DESCRIPTION "This trap is sent
					  when TX MUTE OFF TIMER[sec] status is changed."
		::= 465

	eventTrapPnCPVMaintCW	TRAP-TYPE
		ENTERPRISE	pasolinkNeoCpv
		VARIABLES	{
					  pnTrapSequenceNumber,
					  pnTrapDate,
					  pnTrapTime,
					  pnTrapSource,
					  eventItemPnCPVMaintCW
					}
		DESCRIPTION "This trap is sent
					  when CW CONTROL status is changed."
		::= 466

	eventTrapPnCPVMaintForcedLinearizerCont	TRAP-TYPE
		ENTERPRISE	pasolinkNeoCpv
		VARIABLES	{
					  pnTrapSequenceNumber,
					  pnTrapDate,
					  pnTrapTime,
					  pnTrapSource,
					  eventItemPnCPVMaintForcedLinearizerCont
					}
		DESCRIPTION "This trap is sent
					  when LINEARIZER CONTROL status is changed."
		::= 469

	eventTrapPnCPVMaintRFShiftFreqSet	TRAP-TYPE
		ENTERPRISE	pasolinkNeoCpv
		VARIABLES	{
					  pnTrapSequenceNumber,
					  pnTrapDate,
					  pnTrapTime,
					  pnTrapSource,
					  eventItemPnCPVMaintRFShiftFreqSet
					}
		DESCRIPTION "This item is not used.  
					  This trap is sent
					  when RF SHIFT FREQUENCY[MHz] status is changed."
		::= 471

	eventTrapPnCPVMaintAntennaAlignMode	TRAP-TYPE
		ENTERPRISE	pasolinkNeoCpv
		VARIABLES	{
					  pnTrapSequenceNumber,
					  pnTrapDate,
					  pnTrapTime,
					  pnTrapSource,
					  eventItemPnCPVMaintAntennaAlignMode
					}
		DESCRIPTION "This trap is sent
					  when ANTENNA ALIGNMENT MODE status is changed."
		::= 472

	eventTrapPnCPVinvUpdateMainWorkModule	TRAP-TYPE
		ENTERPRISE	pasolinkNeoCpv
		VARIABLES	{
					  pnTrapSequenceNumber,
					  pnTrapDate,
					  pnTrapTime,
					  pnTrapSource,
					  eventItemPnCPVinvUpdateMainWorkModule
					}
		DESCRIPTION "This trap is sent
					  when INTFC(1) PKG CHANGED status is changed."
		::= 473

	eventTrapPnCPVinvUpdateSummary	TRAP-TYPE
		ENTERPRISE	pasolinkNeoCpv
		VARIABLES	{
					  pnTrapSequenceNumber,
					  pnTrapDate,
					  pnTrapTime,
					  pnTrapSource,
					  eventItemPnCPVinvUpdateSummary
					}
		DESCRIPTION "This trap is sent
					  when INVENTORY UPDATE INFO SUMMARY status is changed."
		::= 475

	eventTrapPnCPVLanCollision	TRAP-TYPE
		ENTERPRISE	pasolinkNeoCpv
		VARIABLES	{
					  pnTrapSequenceNumber,
					  pnTrapDate,
					  pnTrapTime,
					  pnTrapSource,
					  eventItemPnCPVLanCollision
					}
		DESCRIPTION "This trap is sent
					  when LAN COLLISION PORTx(x : 1-2) status is changed."
		::= 476

	eventTrapPnCPVAtpcPowerModeStatus	TRAP-TYPE
		ENTERPRISE	pasolinkNeoCpv
		VARIABLES	{
					  pnTrapSequenceNumber,
					  pnTrapDate,
					  pnTrapTime,
					  pnTrapSource,
					  eventItemPnCPVAtpcPowerModeStatus
					}
		DESCRIPTION "This trap is sent
					  when ATPC POWER MODE status is changed."
		::= 480

	eventTrapPnCPVAuxOutput	TRAP-TYPE
		ENTERPRISE	pasolinkNeoCpv
		VARIABLES	{
					  pnTrapSequenceNumber,
					  pnTrapDate,
					  pnTrapTime,
					  pnTrapSource,
					  eventItemPnCPVAuxOutput
					}
		DESCRIPTION "This trap is sent
					  when ITEM NAME(OUTPUT-x)(x : 1-4) status is changed."
		::= 481

	eventTrapPnCPVMMCMount	TRAP-TYPE
		ENTERPRISE	pasolinkNeoCpv
		VARIABLES	{
					  pnTrapSequenceNumber,
					  pnTrapDate,
					  pnTrapTime,
					  pnTrapSource,
					  eventItemPnCPVMMCMount
					}
		DESCRIPTION "This trap is sent
					  when MMC MOUNT status is changed."
		::= 482

	eventTrapPnCPVMaintTxSWMode	TRAP-TYPE
		ENTERPRISE	pasolinkNeoCpv
		VARIABLES	{
					  pnTrapSequenceNumber,
					  pnTrapDate,
					  pnTrapTime,
					  pnTrapSource,
					  eventItemPnCPVMaintTxSWMode
					}
		DESCRIPTION "This trap is sent
					  when TX SW MODE status is changed."
		::= 485

	eventTrapPnCPVMaintRxSWMode	TRAP-TYPE
		ENTERPRISE	pasolinkNeoCpv
		VARIABLES	{
					  pnTrapSequenceNumber,
					  pnTrapDate,
					  pnTrapTime,
					  pnTrapSource,
					  eventItemPnCPVMaintRxSWMode
					}
		DESCRIPTION "This trap is sent
					  when RX SW MODE status is changed."
		::= 486

	statusTrapPnCPVAuxInput	TRAP-TYPE
		ENTERPRISE	pasolinkNeoCpv
		VARIABLES	{
					  pnTrapSequenceNumber,
					  pnTrapDate,
					  pnTrapTime,
					  pnTrapSource,
					  pnSeverity,
					  pnAlarmType,
					  pnProbableCause,
					  pnStatusTypeAux,
					  statusItemPnCPVAuxInput
					}
		DESCRIPTION "This trap is sent
					  when ITEM NAME(INPUT-x)(x : 1-6) status is changed."
		::= 501

	systemTrapPnCPVGetResult TRAP-TYPE
		ENTERPRISE  pasolinkNeoCpv
		VARIABLES   {
					  pnTrapSequenceNumber,
					  pnTrapDate,
					  pnTrapTime,
					  pngmiRequestID,
					  pngmiTargetPasolink,
					  pngmiDataStatus
					}
		::= 601

-----------------------------------------------
-- pnAlarmStatusGroup Group Definitions
-----------------------------------------------

	pnAsTrGroup OBJECT IDENTIFIER
		::= { pnAlarmStatusGroup 1 }

	pnTrSysGroupTable OBJECT-TYPE
		SYNTAX		SEQUENCE OF PnTrSysGroupEntry
		ACCESS		not-accessible
		STATUS		mandatory
		DESCRIPTION	"TR SYS Group Table"
		::= { pnAsTrGroup 1 }

	pnTrSysGroupEntry OBJECT-TYPE
		SYNTAX		PnTrSysGroupEntry
		ACCESS		not-accessible
		STATUS		mandatory
		INDEX		{
		                                pnTrGroupPasoIndex,
						pnTrGroupIndex
					}
		::= { pnTrSysGroupTable 1 }

	PnTrSysGroupEntry ::= SEQUENCE {
	                                  pnTrGroupPasoIndex	IpAddress,
					  pnTrGroupIndex   INTEGER,
					  pnTxPowerAlarm   NormalAlarmValue,
					  pnTxInputAlarm   NormalAlarmValue,
					  pnRxLevelAlarm   NormalAlarmValue,
					  pnApcAlarm       NormalAlarmValue,
					  pnTruCpuAlarm    NormalAlarmValue,
					  pnTruLORefAlarm  NormalAlarmValue,
					  pnMuteStatus     OffOnValue
					}

	pnTrGroupPasoIndex OBJECT-TYPE
		SYNTAX		IpAddress 
		ACCESS		read-only
		STATUS		mandatory
		DESCRIPTION	"Pasolink IP Address Index"
		::= { pnTrSysGroupEntry 1 }

	pnTrGroupIndex OBJECT-TYPE
		SYNTAX		INTEGER{
					  no1(1),
					  no2(2)
					}
		ACCESS		read-only
		STATUS		mandatory
		DESCRIPTION	"TR Group Index
					  1:No.1
					  2:No.2
				 No.2 is available for 1+1 system."
		::= { pnTrSysGroupEntry 2 }

	pnTxPowerAlarm OBJECT-TYPE
		SYNTAX		NormalAlarmValue
		ACCESS		read-only
		STATUS		mandatory
		DESCRIPTION	"TX POWER
				 Refer to NormalAlarmValue of TEXTUAL-CONVENTION
					TRAP=alarmTrapPnCPVTxPowerAlarm"
		::= { pnTrSysGroupEntry 3 }

	pnTxInputAlarm OBJECT-TYPE
		SYNTAX		NormalAlarmValue
		ACCESS		read-only
		STATUS		mandatory
		DESCRIPTION	"TX INPUT
				 Refer to NormalAlarmValue of TEXTUAL-CONVENTION
					TRAP=alarmTrapPnCPVTxInputAlarm"
		::= { pnTrSysGroupEntry 4 }

	pnRxLevelAlarm OBJECT-TYPE
		SYNTAX		NormalAlarmValue
		ACCESS		read-only
		STATUS		mandatory
		DESCRIPTION	"RX LEVEL
				  Refer to NormalAlarmValue of TEXTUAL-CONVENTION
					TRAP=alarmTrapPnCPVRxLevelAlarm"
		::= { pnTrSysGroupEntry 5 }

	pnApcAlarm OBJECT-TYPE
		SYNTAX		NormalAlarmValue
		ACCESS		read-only
		STATUS		mandatory
		DESCRIPTION	"APC
				  Refer to NormalAlarmValue of TEXTUAL-CONVENTION
					TRAP=alarmTrapPnCPVApcAlarm"
		::= { pnTrSysGroupEntry 6 }

	pnTruCpuAlarm OBJECT-TYPE
		SYNTAX		NormalAlarmValue
		ACCESS		read-only
		STATUS		mandatory
		DESCRIPTION	"ODU CPU/CABLE OPEN
				 Refer to NormalAlarmValue of TEXTUAL-CONVENTION
					TRAP=alarmTrapPnCPVTRUCPUAlarm"
		::= { pnTrSysGroupEntry 7 }

	pnTruLORefAlarm OBJECT-TYPE
		SYNTAX		NormalAlarmValue
		ACCESS		read-only
		STATUS		mandatory
		DESCRIPTION	"ODU TYPE MISMATCH
				  Refer to NormalAlarmValue of TEXTUAL-CONVENTION
					TRAP=alarmTrapPnCPVTRULORefAlarm"
		::= { pnTrSysGroupEntry 8 }

	pnMuteStatus OBJECT-TYPE
		SYNTAX		OffOnValue
		ACCESS		read-only
		STATUS		mandatory
		DESCRIPTION	"MUTE STATUS
				 Refer to OffOnValue of TEXTUAL-CONVENTION
					TRAP=eventTrapPnCPVTxMuteStatus"
		::= { pnTrSysGroupEntry 9 }

	pnTrSysGroupComTable OBJECT-TYPE
		SYNTAX		SEQUENCE OF PnTrSysGroupComEntry
		ACCESS		not-accessible
		STATUS		mandatory
		DESCRIPTION	"TR SYS Group Table"
		::= { pnAsTrGroup 2 }

	pnTrSysGroupComEntry OBJECT-TYPE
		SYNTAX		PnTrSysGroupComEntry
		ACCESS		not-accessible
		STATUS		mandatory
		INDEX		{
		                                pnTrGroupComPasoIndex
					}
		::= { pnTrSysGroupComTable 1 }

	PnTrSysGroupComEntry ::= SEQUENCE {
	                                  pnTrGroupComPasoIndex	IpAddress,
                                          pnTxSWStatus 	INTEGER,
                                          pnRxSWStatus 	INTEGER
					}

	pnTrGroupComPasoIndex OBJECT-TYPE
		SYNTAX		IpAddress 
		ACCESS		read-only
		STATUS		mandatory
		DESCRIPTION	"Pasolink IP Address Index"
		::= { pnTrSysGroupComEntry 1 }

	pnTxSWStatus OBJECT-TYPE
		SYNTAX		INTEGER (0..2)
		ACCESS		read-only
		STATUS		mandatory
		DESCRIPTION	"TX SW STATUS
					  0:Invalid,
					  1:No.1
					  2:No.2
				 This item is available for Hot stand-by system.
					TRAP=eventTrapPnCPVTxSWStatus"
		::= { pnTrSysGroupComEntry 2 }

	pnRxSWStatus OBJECT-TYPE
		SYNTAX		INTEGER (0..2)
		ACCESS		read-only
		STATUS		mandatory
		DESCRIPTION	"RX SW STATUS
					  0:Invalid,
					  1:No.1
					  2:No.2
				 This item is available for 1+1 system.
					TRAP=eventTrapPnCPVRxSWStatus"
		::= { pnTrSysGroupComEntry 3 }

	pnAsModemGroup OBJECT IDENTIFIER
		::= { pnAlarmStatusGroup 2 }

	pnModemSysGroupTable OBJECT-TYPE
		SYNTAX		SEQUENCE OF PnModemSysGroupEntry
		ACCESS		not-accessible
		STATUS		mandatory
		DESCRIPTION	"Modem Sys Group Table"
		::= { pnAsModemGroup 1 }

	pnModemSysGroupEntry OBJECT-TYPE
		SYNTAX		PnModemSysGroupEntry
		ACCESS		not-accessible
		STATUS		mandatory
		INDEX		{
                                                pnTrGroupComPasoIndex,
						pnModemSyGroupIndex
					}
		::= { pnModemSysGroupTable 1 }

	PnModemSysGroupEntry ::= SEQUENCE {
	                                  pnModemSysGroupPasoIndex	IpAddress,
					  pnModemSyGroupIndex    INTEGER,
					  pnModemAlarm           NormalAlarmValue,
					  pnModemUnequipped      NormalAlarmValue,
					  pnHighBERAlarm         NormalAlarmValue,
					  pnLowBERAlarm          NormalAlarmValue,
					  pnModAlarm             NormalAlarmValue,
					  pnDemAlarm             NormalAlarmValue,
					  pnXIFLevelAlarm        NormalAlarmValue,
					  pnPowerSupplyAlarm     NormalAlarmValue,
					  pnIfCableShortAlarm    NormalAlarmValue,
					  pnLof                  NormalAlarmValue,
					  pnLinearizerFunc       INTEGER,
					  pnCableEQLAlarm        NormalAlarmValue,

					  pnLinearizerFail       NormalAlarmValue,
					  pnRouteId              NormalAlarmValue,
					  pnEarlyWarning         NormalAlarmValue,
					  pnAtpcPowerModeStatus  INTEGER,
					  pnInputVoltageAlarm	 INTEGER
					}

	pnModemSysGroupPasoIndex OBJECT-TYPE
		SYNTAX		IpAddress 
		ACCESS		read-only
		STATUS		mandatory
		DESCRIPTION	"Pasolink IP Address Index"
		::= { pnModemSysGroupEntry 1 }

	pnModemSyGroupIndex OBJECT-TYPE
		SYNTAX		INTEGER{
					  no1(1),
					  no2(2)
					}
		ACCESS		not-accessible
		STATUS		mandatory
		DESCRIPTION	"Modem Group Index
					  1:No.1
					  2:No.2
				 No.2 is available for 1+1 system."
		::= { pnModemSysGroupEntry 2 }

	pnModemAlarm OBJECT-TYPE
		SYNTAX		NormalAlarmValue
		ACCESS		read-only
		STATUS		mandatory
		DESCRIPTION	"MODEM MODULE
				 Refer to NormalAlarmValue of TEXTUAL-CONVENTION
					TRAP=alarmTrapPnCPVModemAlarm"
		::= { pnModemSysGroupEntry 3 }

	pnModemUnequipped OBJECT-TYPE
		SYNTAX		NormalAlarmValue
		ACCESS		read-only
		STATUS		mandatory
		DESCRIPTION	"MODEM UNEQUIPPED
				 Refer to NormalAlarmValue of TEXTUAL-CONVENTION
					TRAP=alarmTrapPnCPVModemUneq"
		::= { pnModemSysGroupEntry 4 }

	pnHighBERAlarm OBJECT-TYPE
		SYNTAX		NormalAlarmValue
		ACCESS		read-only
		STATUS		mandatory
		DESCRIPTION	"HIGH BER
				 Refer to NormalAlarmValue of TEXTUAL-CONVENTION
					TRAP=alarmTrapPnCPVHighBERAlarm"
		::= { pnModemSysGroupEntry 5 }

	pnLowBERAlarm OBJECT-TYPE
		SYNTAX		NormalAlarmValue
		ACCESS		read-only
		STATUS		mandatory
		DESCRIPTION	"LOW BER
				 Refer to NormalAlarmValue of TEXTUAL-CONVENTION
					TRAP=alarmTrapPnCPVLowBERAlarm"
		::= { pnModemSysGroupEntry 6 }

	pnModAlarm OBJECT-TYPE
		SYNTAX		NormalAlarmValue
		ACCESS		read-only
		STATUS		mandatory
		DESCRIPTION	"MOD
				 Refer to NormalAlarmValue of TEXTUAL-CONVENTION
					TRAP=alarmTrapPnCPVModAlarm"
		::= { pnModemSysGroupEntry 7 }

	pnDemAlarm OBJECT-TYPE
		SYNTAX		NormalAlarmValue
		ACCESS		read-only
		STATUS		mandatory
		DESCRIPTION	"DEM
				 Refer to NormalAlarmValue of TEXTUAL-CONVENTION
					TRAP=alarmTrapPnCPVDemAlarm"
		::= { pnModemSysGroupEntry 8 }

	pnXIFLevelAlarm OBJECT-TYPE
		SYNTAX		NormalAlarmValue
		ACCESS		read-only
		STATUS		mandatory
		DESCRIPTION	"MODEM TYPE MISMATCH
					TRAP=alarmTrapPnCPVXIfLevelAlarm"
		::= { pnModemSysGroupEntry 9 }

	pnPowerSupplyAlarm OBJECT-TYPE
		SYNTAX		NormalAlarmValue
		ACCESS		read-only
		STATUS		mandatory
		DESCRIPTION	"POWER SUPPLY
				 Refer to NormalAlarmValue of TEXTUAL-CONVENTION
					TRAP=alarmTrapPnCPVPSAlarm"
		::= { pnModemSysGroupEntry 12 }

	pnIfCableShortAlarm OBJECT-TYPE
		SYNTAX		NormalAlarmValue
		ACCESS		read-only
		STATUS		mandatory
		DESCRIPTION	"IF CABLE SHORT
				 Refer to NormalAlarmValue of TEXTUAL-CONVENTION
					TRAP=alarmTrapPnCPVIfCableShort"
		::= { pnModemSysGroupEntry 13 }

	pnLof OBJECT-TYPE
		SYNTAX		NormalAlarmValue
		ACCESS		read-only
		STATUS		mandatory
		DESCRIPTION	"LOF
				 Refer to NormalAlarmValue of TEXTUAL-CONVENTION
					TRAP=alarmTrapPnCPVLof"
		::= { pnModemSysGroupEntry 14 }

	pnLinearizerFunc OBJECT-TYPE
		SYNTAX		INTEGER (0..3)
		ACCESS		read-only
		STATUS		mandatory
		DESCRIPTION	"LINEARIZER FUNCTION
					  0:Invalid,
					  1:N/A,
					  2:NON Operation,
					  3:Operation
					TRAP=eventTrapPnCPVLinearizerFunc"
		::= { pnModemSysGroupEntry 15 }

	pnCableEQLAlarm OBJECT-TYPE
		SYNTAX		NormalAlarmValue
		ACCESS		read-only
		STATUS		mandatory
		DESCRIPTION	"CABLE EQL
				 Refer to NormalAlarmValue of TEXTUAL-CONVENTION
					TRAP=alarmTrapPnCPVCableEQLAlarm"
		::= { pnModemSysGroupEntry 16 }

	pnLinearizerFail OBJECT-TYPE
		SYNTAX		NormalAlarmValue
		ACCESS		read-only
		STATUS		mandatory
		DESCRIPTION	"LINEARIZER
				 Refer to NormalAlarmValue of TEXTUAL-CONVENTION
					TRAP=alarmTrapPnCPVLinearizerFail"
		::= { pnModemSysGroupEntry 19 }

	pnRouteId OBJECT-TYPE
		SYNTAX		NormalAlarmValue
		ACCESS		read-only
		STATUS		mandatory
		DESCRIPTION	"FRAME ID
				 Refer to NormalAlarmValue of TEXTUAL-CONVENTION
					TRAP=alarmTrapPnCPVRouteID"
		::= { pnModemSysGroupEntry 20 }

	pnEarlyWarning OBJECT-TYPE
		SYNTAX		NormalAlarmValue
		ACCESS		read-only
		STATUS		mandatory
		DESCRIPTION	"EARLY WARNING
				 Refer to NormalAlarmValue of TEXTUAL-CONVENTION
					TRAP=alarmTrapPnCPVEarlyWarning"
		::= { pnModemSysGroupEntry 21 }

	pnAtpcPowerModeStatus OBJECT-TYPE
		SYNTAX		INTEGER(0..2)
		ACCESS		read-only
		STATUS		mandatory
		DESCRIPTION	"ATPC POWER MODE
					  0:Invalid,
					  1:Active,
					  2:Stop
					TRAP=eventTrapPnCPVAtpcPowerModeStatus"
		::= { pnModemSysGroupEntry 22 }

	pnInputVoltageAlarm OBJECT-TYPE
		SYNTAX		NormalAlarmValue
		ACCESS		read-only
		STATUS		mandatory
		DESCRIPTION	"INPUT VOLTAGE
				 Refer to NormalAlarmValue of TEXTUAL-CONVENTION
					TRAP=alarmTrapPnCPVInputVoltage"
		::= { pnModemSysGroupEntry 23 }

	pnAsIntfcMainWorkGroup OBJECT IDENTIFIER
		::= { pnAlarmStatusGroup 3 }

	pnAsIntfcMainWorkGroupTable OBJECT-TYPE
		SYNTAX		SEQUENCE OF PnAsIntfcMainWorkGroupEntry
		ACCESS		not-accessible
		STATUS		mandatory
		DESCRIPTION	"INTFC Main Work Group"
		::= { pnAsIntfcMainWorkGroup 1 }

	pnAsIntfcMainWorkGroupEntry OBJECT-TYPE
		SYNTAX		PnAsIntfcMainWorkGroupEntry
		ACCESS		not-accessible
		STATUS		mandatory
		INDEX		{
                                                pnAsIntfcMainWorkPasoIndex
					}
		::= { pnAsIntfcMainWorkGroupTable 1 }

	PnAsIntfcMainWorkGroupEntry ::= SEQUENCE {
	                                  pnAsIntfcMainWorkPasoIndex	IpAddress,
					  pnIntfcMAlarm	NormalAlarmValue,
					  pnIntfcMUnequipped	NormalAlarmValue,
					  pnInputLoss	OCTET STRING,
					  pnUsageError	OCTET STRING,
					  pnAisGeneratedCH	OCTET STRING,
					  pnAisReceivedCH	OCTET STRING,
					  pnInPhaseWork	NormalAlarmValue,
					  pnIntfcMTypeMismatch NormalAlarmValue
					}

	pnAsIntfcMainWorkPasoIndex OBJECT-TYPE
		SYNTAX		IpAddress 
		ACCESS		read-only
		STATUS		mandatory
		DESCRIPTION	"Pasolink IP Address Index"
		::= { pnAsIntfcMainWorkGroupEntry 1 }

	pnIntfcMAlarm OBJECT-TYPE
		SYNTAX		NormalAlarmValue
		ACCESS		read-only
		STATUS		mandatory
		DESCRIPTION	"INTFC(1) MODULE
				 Refer to NormalAlarmValue of TEXTUAL-CONVENTION
					TRAP=alarmTrapPnCPVIntfcMAlarm"
		::= { pnAsIntfcMainWorkGroupEntry 2 }

	pnIntfcMUnequipped OBJECT-TYPE
		SYNTAX		NormalAlarmValue
		ACCESS		read-only
		STATUS		mandatory
		DESCRIPTION	"INTFC(1) UNEQUIPPED
				 Refer to NormalAlarmValue of TEXTUAL-CONVENTION
					TRAP=alarmTrapPnCPVIntfcMUneq"
		::= { pnAsIntfcMainWorkGroupEntry 3 }

	pnInputLoss OBJECT-TYPE
		SYNTAX		OCTET STRING (SIZE (6))
		ACCESS		read-only
		STATUS		mandatory
		DESCRIPTION	"INPUT LOS CHxx
					(xx : 1-16)
					  0:Normal,
					  1:Alarm
					
					 [Bit Description]
					  Bit0 = CH01 (0: Normal,1: Alarm)
					  Bit1 = CH02
					  Bit2 = CH03
					  ...
					  Bit14 = CH15
					  Bit15 = CH16
					TRAP=alarmTrapPnCPVInputLos"
		::= { pnAsIntfcMainWorkGroupEntry 4 }

	pnUsageError OBJECT-TYPE
		SYNTAX		OCTET STRING (SIZE (6))
		ACCESS		read-only
		STATUS		mandatory
		DESCRIPTION	"USAGE ERROR CHxx
					(xx : 1-16)
					  0:Normal,
					  1:Alarm
					
					 [Bit Description]
					  Bit0 = CH01 (0: Normal,1: Alarm)
					  Bit1 = CH02
					  Bit2 = CH03
					  ...
					  Bit14 = CH15
					  Bit15 = CH16
					TRAP=alarmTrapPnCPVUsageError"
		::= { pnAsIntfcMainWorkGroupEntry 10 }

	pnAisGeneratedCH OBJECT-TYPE
		SYNTAX		OCTET STRING (SIZE (6))
		ACCESS		read-only
		STATUS		mandatory
		DESCRIPTION	"AIS GENERATED CHxx
					(xx : 1-16)
					  0:Normal,
					  1:Generated
					
					 [Bit Description]
					  Bit0 = CH01 (0: Normal,1: Generated)
					  Bit1 = CH02
					  Bit2 = CH03
					  ...
					  Bit14 = CH15
					  Bit15 = CH16
					TRAP=eventTrapPnCPVAisGeneratedCH"
		::= { pnAsIntfcMainWorkGroupEntry 11 }

	pnAisReceivedCH OBJECT-TYPE
		SYNTAX		OCTET STRING (SIZE (6))
		ACCESS		read-only
		STATUS		mandatory
		DESCRIPTION	"AIS RECEIVED CHxx
					(xx : 1-16)
					  0:Normal,
					  1:Received
					
					 [Bit Description]
					  Bit0 = CH01 (0: Normal,1: Received)
					  Bit1 = CH02
					  Bit2 = CH02
					  ...
					  Bit14 = CH15
					  Bit15 = CH16
					TRAP=eventTrapPnCPVAisReceivedCH"
		::= { pnAsIntfcMainWorkGroupEntry 12 }

	pnInPhaseWork OBJECT-TYPE
		SYNTAX		INTEGER(0..1)
		ACCESS		read-only
		STATUS		mandatory
		DESCRIPTION	"INTFC(1) INPHASE
					  0:Invalid,
					  1:OUTPHASE,
					  2:INPHASE
					TRAP=eventTrapPnCPVInphaseWork"
		::= { pnAsIntfcMainWorkGroupEntry 17 }

	pnIntfcMTypeMismatch OBJECT-TYPE
		SYNTAX		NormalAlarmValue
		ACCESS		read-only
		STATUS		mandatory
		DESCRIPTION	"INTFC(1) TYPE MISMATCH
				 Refer to NormalAlarmValue of TEXTUAL-CONVENTION
					TRAP=alarmTrapPnCPVIntfcMTypeMismatch"
		::= { pnAsIntfcMainWorkGroupEntry 19 }

	pnLanStatusTable OBJECT-TYPE
		SYNTAX		SEQUENCE OF PnLanStatusEntry
		ACCESS		not-accessible
		STATUS		mandatory
		DESCRIPTION	"LAN Status Table"
		::= { pnAsIntfcMainWorkGroup 2 }

	pnLanStatusEntry OBJECT-TYPE
		SYNTAX		PnLanStatusEntry
		ACCESS		not-accessible
		STATUS		mandatory
		INDEX		{
		                pnLanstatusPasoIndex,                 
						pnLanStatusIndex
					}
		::= { pnLanStatusTable 1 }

	PnLanStatusEntry ::= SEQUENCE {
	                  pnLanstatusPasoIndex	IpAddress,
					  pnLanStatusIndex      INTEGER,
					  pnLink                INTEGER,
					  pnCollision           INTEGER,
					  pnLinkLossForwarding  INTEGER,
					  pnSpeedDuplex         INTEGER
					}

	pnLanstatusPasoIndex OBJECT-TYPE
		SYNTAX		IpAddress 
		ACCESS		read-only
		STATUS		mandatory
		DESCRIPTION	"Pasolink IP Address Index"
		::= { pnLanStatusEntry 1 }

	pnLanStatusIndex OBJECT-TYPE
		SYNTAX		INTEGER{
					  port1(1),
					  port2(2)
					}
		ACCESS		read-only
		STATUS		mandatory
		DESCRIPTION	"PORTx(x:1-2) Index
					  1: Port 1
					  2: Port 2"
		::= { pnLanStatusEntry 2 }

	pnLink OBJECT-TYPE
		SYNTAX		INTEGER(0..2)
		ACCESS		read-only
		STATUS		mandatory
		DESCRIPTION	"LAN LINK PORTx
					(x : 1-2)
					  0:Invalid,
					  1:Normal,
					  2:Alarm
					TRAP=alarmTrapPnCPVLink"
		::= { pnLanStatusEntry 3 }

	pnCollision OBJECT-TYPE
		SYNTAX		INTEGER(0..2)
		ACCESS		read-only
		STATUS		mandatory
		DESCRIPTION	"LAN COLLISION PORTx
					(x : 1-2)
					  0:Invalid,
					  1:Normal,
					  2:Collision
					TRAP=eventTrapPnCPVLanCollision"
		::= { pnLanStatusEntry 4 }

	pnLinkLossForwarding OBJECT-TYPE
		SYNTAX		INTEGER(0..2)
		ACCESS		read-only
		STATUS		mandatory
		DESCRIPTION	"LLF PORTx
					(x : 1-2)
					  0:Invalid,
					  1:Normal,
					  2:Under Execution
					TRAP=eventTrapPnCPVLinkLossForward"
		::= { pnLanStatusEntry 5 }

	pnSpeedDuplex OBJECT-TYPE
		SYNTAX		INTEGER(0..8)
		ACCESS		read-only
		STATUS		mandatory
		DESCRIPTION	"LAN MODE PORTx
					(x : 1-2)
				 Speed & Duplex
					  0:INVALID,
					  1:10M-HALF(MDI),
					  2:10M-FULL(MDI),
					  3:100M-HALF(MDI),
					  4:100M-FULL(MDI),
					  5:10M-HALF(MDIX),
					  6:10M-FULL(MDIX),
					  7:100M-HALF(MDIX),
					  8:100M-FULL(MDIX)
					TRAP=eventTrapPnCPVSpeedDuplex"
		::= { pnLanStatusEntry 6 }

	pnAsCtrlGroup OBJECT IDENTIFIER
		::= { pnAlarmStatusGroup 5 }

	pnAsCtrlGroupTable OBJECT-TYPE
		SYNTAX		SEQUENCE OF PnAsCtrlGroupEntry
		ACCESS		not-accessible
		STATUS		mandatory
		DESCRIPTION	"CTRL Group Table"
		::= { pnAsCtrlGroup 1 }

	pnAsCtrlGroupEntry OBJECT-TYPE
		SYNTAX		PnAsCtrlGroupEntry
		ACCESS		not-accessible
		STATUS		mandatory
		INDEX		{
		                                pnAsCtrlGroupPasoIndex
					}
		::= { pnAsCtrlGroupTable 1 }

	PnAsCtrlGroupEntry ::= SEQUENCE {
					  pnAsCtrlGroupPasoIndex	IpAddress,
					  pnCtrlAlarm	NormalAlarmValue,
					  pnMultiMediaCardMount	OffOnValue,
					  pnSvLineAlarm	NormalAlarmValue
					}

	pnAsCtrlGroupPasoIndex OBJECT-TYPE
		SYNTAX		IpAddress 
		ACCESS		read-only
		STATUS		mandatory
		DESCRIPTION	"Pasolink IP Address Index"
		::= { pnAsCtrlGroupEntry 1 }

	pnCtrlAlarm OBJECT-TYPE
		SYNTAX		NormalAlarmValue
		ACCESS		read-only
		STATUS		mandatory
		DESCRIPTION	"CTRL MODULE
				 Refer to NormalAlarmValue of TEXTUAL-CONVENTION
					TRAP=alarmTrapPnCPVCTRLAlarm"
		::= { pnAsCtrlGroupEntry 2 }

	pnMultiMediaCardMount OBJECT-TYPE
		SYNTAX		OffOnValue
		ACCESS		read-only
		STATUS		mandatory
		DESCRIPTION	"MMC MOUNT
				 Refer to OffOnValue of TEXTUAL-CONVENTION
					TRAP=eventTrapPnCPVMMCMount"
		::= { pnAsCtrlGroupEntry 3 }

	pnSvLineAlarm OBJECT-TYPE
		SYNTAX		NormalAlarmValue
		ACCESS		read-only
		STATUS		mandatory
		DESCRIPTION	"This item is not used.   
				 SV LINE
				 Refer to NormalAlarmValue of TEXTUAL-CONVENTION
				This item is not used."
		::= { pnAsCtrlGroupEntry 5 }

	pnAsTcnGroup OBJECT IDENTIFIER
		::= { pnAlarmStatusGroup 6 }

	pnTcn15minCurrentTotalTable OBJECT-TYPE
		SYNTAX		SEQUENCE OF PnTcn15minCurrentTotalEntry
		ACCESS		not-accessible
		STATUS		mandatory
		DESCRIPTION	"TCN 15min Current Total Table"
		::= { pnAsTcnGroup 1 }

	pnTcn15minCurrentTotalEntry OBJECT-TYPE
		SYNTAX		PnTcn15minCurrentTotalEntry
		ACCESS		not-accessible
		STATUS		mandatory
		INDEX		{
		                                pnTcn15minCurrentTotalPasoIndex,
						pnTcn15minCurrentTotalWPIndex
					}
		::= { pnTcn15minCurrentTotalTable 1 }

	PnTcn15minCurrentTotalEntry ::= SEQUENCE {
					  pnTcn15minCurrentTotalPasoIndex IpAddress,
					  pnTcn15minCurrentTotalWPIndex  INTEGER,
					  pnTcn15minCurrentTotalOFS      NormalAlarmValue,
					  pnTcn15minCurrentTotalUAS      NormalAlarmValue,
					  pnTcn15minCurrentTotalES       NormalAlarmValue,
					  pnTcn15minCurrentTotalSES      NormalAlarmValue,
					  pnTcn15minCurrentTotalBBE      NormalAlarmValue,
					  pnTcn15minCurrentTotalSEP      NormalAlarmValue
					}

	pnTcn15minCurrentTotalPasoIndex OBJECT-TYPE
		SYNTAX		IpAddress 
		ACCESS		read-only
		STATUS		mandatory
		DESCRIPTION	"Pasolink IP Address Index"
		::= { pnTcn15minCurrentTotalEntry 1 }

	pnTcn15minCurrentTotalWPIndex OBJECT-TYPE
		SYNTAX		INTEGER{
					  working-MUX(1), --Not Used
					  protection-MUX(2), --Not Used
					  working-DMR(3),
					  protection-DMR(4) --Not Used
					}
		ACCESS		read-only
		STATUS		mandatory
		DESCRIPTION	"TCN 15min Current Total Index
					  1:Working - MUX,--Not Used
					  2:Protection - MUX,--Not Used
					  3:Working - DMR,
					  4:Protection - DMR--Not Used"
					
		::= { pnTcn15minCurrentTotalEntry 2 }

	pnTcn15minCurrentTotalOFS OBJECT-TYPE
		SYNTAX		NormalAlarmValue
		ACCESS		read-only
		STATUS		mandatory
		DESCRIPTION	"TCN-OFS-15min TOTAL
				 Refer to NormalAlarmValue of TEXTUAL-CONVENTION
					TRAP=alarmTrapPnCPVTcn15minTotalOFS"
		::= { pnTcn15minCurrentTotalEntry 3 }

	pnTcn15minCurrentTotalUAS OBJECT-TYPE
		SYNTAX		NormalAlarmValue
		ACCESS		read-only
		STATUS		mandatory
		DESCRIPTION	"TCN-UAS-15min TOTAL
				 Refer to NormalAlarmValue of TEXTUAL-CONVENTION
					TRAP=alarmTrapPnCPVTcn15minTotalUAS"
		::= { pnTcn15minCurrentTotalEntry 4 }

	pnTcn15minCurrentTotalES OBJECT-TYPE
		SYNTAX		NormalAlarmValue
		ACCESS		read-only
		STATUS		mandatory
		DESCRIPTION	"TCN-ES-15min TOTAL
				 Refer to NormalAlarmValue of TEXTUAL-CONVENTION
					TRAP=alarmTrapPnCPVTcn15minTotalES"
		::= { pnTcn15minCurrentTotalEntry 5 }

	pnTcn15minCurrentTotalSES OBJECT-TYPE
		SYNTAX		NormalAlarmValue
		ACCESS		read-only
		STATUS		mandatory
		DESCRIPTION	"TCN-SES-15min TOTAL
				 Refer to NormalAlarmValue of TEXTUAL-CONVENTION
					TRAP=alarmTrapPnCPVTcn15minTotalSES"
		::= { pnTcn15minCurrentTotalEntry 6 }

	pnTcn15minCurrentTotalBBE OBJECT-TYPE
		SYNTAX		NormalAlarmValue
		ACCESS		read-only
		STATUS		mandatory
		DESCRIPTION	"TCN-BBE-15min TOTAL
				 Refer to NormalAlarmValue of TEXTUAL-CONVENTION
					TRAP=alarmTrapPnCPVTcn15minTotalBBE"
		::= { pnTcn15minCurrentTotalEntry 7 }

	pnTcn15minCurrentTotalSEP OBJECT-TYPE
		SYNTAX		NormalAlarmValue
		ACCESS		read-only
		STATUS		mandatory
		DESCRIPTION	"TCN-SEP-15min TOTAL
				 Refer to NormalAlarmValue of TEXTUAL-CONVENTION
					TRAP=alarmTrapPnCPVTcn15minTotalSEP"
		::= { pnTcn15minCurrentTotalEntry 8 }

	pnTcn15minCurrentCHTable OBJECT-TYPE
		SYNTAX		SEQUENCE OF PnTcn15minCurrentCHEntry
		ACCESS		not-accessible
		STATUS		mandatory
		DESCRIPTION	"TCN 15min Current CH Table"
		::= { pnAsTcnGroup 2 }

	pnTcn15minCurrentCHEntry OBJECT-TYPE
		SYNTAX		PnTcn15minCurrentCHEntry
		ACCESS		not-accessible
		STATUS		mandatory
		INDEX		{
		                                pnTcn15minCurrentCHPasoIndex
					}
		::= { pnTcn15minCurrentCHTable 1 }

	PnTcn15minCurrentCHEntry ::= SEQUENCE {
					  pnTcn15minCurrentCHPasoIndex	IpAddress,
					  pnTcn15minCurrentCHUAS      OCTET STRING,
					  pnTcn15minCurrentCHES       OCTET STRING,
					  pnTcn15minCurrentCHSES      OCTET STRING,
					  pnTcn15minCurrentCHBBE      OCTET STRING,
					  pnTcn15minCurrentCHSEP      OCTET STRING
					}

	pnTcn15minCurrentCHPasoIndex OBJECT-TYPE
		SYNTAX		IpAddress 
		ACCESS		read-only
		STATUS		mandatory
		DESCRIPTION	"Pasolink IP Address Index"
		::= { pnTcn15minCurrentCHEntry 1 }

	pnTcn15minCurrentCHUAS OBJECT-TYPE
		SYNTAX		OCTET STRING (SIZE (1))
		ACCESS		read-only
		STATUS		mandatory
		DESCRIPTION	"This item is not used.
				 TCN-UAS-15min CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnCPVTcn15minCHUAS"
		::= { pnTcn15minCurrentCHEntry  2 }

	pnTcn15minCurrentCHES OBJECT-TYPE
		SYNTAX		OCTET STRING (SIZE (1))
		ACCESS		read-only
		STATUS		mandatory
		DESCRIPTION	"This item is not used.
				 TCN-ES-15min CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnCPVTcn15minCHES"
		::= { pnTcn15minCurrentCHEntry  3 }

	pnTcn15minCurrentCHSES OBJECT-TYPE
		SYNTAX		OCTET STRING (SIZE (1))
		ACCESS		read-only
		STATUS		mandatory
		DESCRIPTION	"This item is not used.
				 TCN-SES-15min CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnCPVTcn15minCHSES"
		::= { pnTcn15minCurrentCHEntry  4 }

	pnTcn15minCurrentCHBBE OBJECT-TYPE
		SYNTAX		OCTET STRING (SIZE (1))
		ACCESS		read-only
		STATUS		mandatory
		DESCRIPTION	"This item is not used.
				 TCN-BBE-15min CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnCPVTcn15minCHBBE"
		::= { pnTcn15minCurrentCHEntry  5 }

	pnTcn15minCurrentCHSEP OBJECT-TYPE
		SYNTAX		OCTET STRING (SIZE (1))
		ACCESS		read-only
		STATUS		mandatory
		DESCRIPTION	"This item is not used.
				 TCN-SEP-15min CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnCPVTcn15minCHSEP"
		::= { pnTcn15minCurrentCHEntry  6 }

	pnTcn1dayCurrentTotalTable OBJECT-TYPE
		SYNTAX		SEQUENCE OF PnTcn1dayCurrentTotalEntry
		ACCESS		not-accessible
		STATUS		mandatory
		DESCRIPTION	"1day Current Total Table"
		::= { pnAsTcnGroup 3 }

	pnTcn1dayCurrentTotalEntry OBJECT-TYPE
		SYNTAX		PnTcn1dayCurrentTotalEntry
		ACCESS		not-accessible
		STATUS		mandatory
		INDEX		{
						pnTcn1dayCurrentTotalPasoIndex,
						pnTcn1dayCurrentTotalWPIndex
					}
		::= { pnTcn1dayCurrentTotalTable 1 }

	PnTcn1dayCurrentTotalEntry ::= SEQUENCE {
					  pnTcn1dayCurrentTotalPasoIndex IpAddress,
					  pnTcn1dayCurrentTotalWPIndex  INTEGER,
					  pnTcn1dayCurrentTotalOFS      NormalAlarmValue,
					  pnTcn1dayCurrentTotalUAS      NormalAlarmValue,
					  pnTcn1dayCurrentTotalES       NormalAlarmValue,
					  pnTcn1dayCurrentTotalSES      NormalAlarmValue,
					  pnTcn1dayCurrentTotalBBE      NormalAlarmValue,
					  pnTcn1dayCurrentTotalSEP      NormalAlarmValue
					}

	pnTcn1dayCurrentTotalPasoIndex OBJECT-TYPE
		SYNTAX		IpAddress 
		ACCESS		read-only
		STATUS		mandatory
		DESCRIPTION	"Pasolink IP Address Index"
		::= { pnTcn1dayCurrentTotalEntry 1 }

	pnTcn1dayCurrentTotalWPIndex OBJECT-TYPE
		SYNTAX		INTEGER{
					  working-MUX(1),
					  protection-MUX(2),
					  working-DMR(3),
					  protection-DMR(4)
					}
		ACCESS		read-only
		STATUS		mandatory
		DESCRIPTION	"TCN 1day Current Total Index
					  1:Working(MUX),
					  2:Protection(MUX),
					  3:Working(DMR),
					  4:Protection(DMR)"

		::= { pnTcn1dayCurrentTotalEntry 2 }

	pnTcn1dayCurrentTotalOFS OBJECT-TYPE
		SYNTAX		NormalAlarmValue
		ACCESS		read-only
		STATUS		mandatory
		DESCRIPTION	"TCN-OFS-1day TOTAL
				 Refer to NormalAlarmValue of TEXTUAL-CONVENTION
					TRAP=alarmTrapPnCPVTcn1dayTotalOFS"
		::= { pnTcn1dayCurrentTotalEntry 3 }

	pnTcn1dayCurrentTotalUAS OBJECT-TYPE
		SYNTAX		NormalAlarmValue
		ACCESS		read-only
		STATUS		mandatory
		DESCRIPTION	"TCN-UAS-1day TOTAL
				 Refer to NormalAlarmValue of TEXTUAL-CONVENTION
					TRAP=alarmTrapPnCPVTcn1dayTotalUAS"
		::= { pnTcn1dayCurrentTotalEntry 4 }

	pnTcn1dayCurrentTotalES OBJECT-TYPE
		SYNTAX		NormalAlarmValue
		ACCESS		read-only
		STATUS		mandatory
		DESCRIPTION	"TCN-ES-1day TOTAL
				 Refer to NormalAlarmValue of TEXTUAL-CONVENTION
					TRAP=alarmTrapPnCPVTcn1dayTotalES"
		::= { pnTcn1dayCurrentTotalEntry 5 }

	pnTcn1dayCurrentTotalSES OBJECT-TYPE
		SYNTAX		NormalAlarmValue
		ACCESS		read-only
		STATUS		mandatory
		DESCRIPTION	"TCN-SES-1day TOTAL
				 Refer to NormalAlarmValue of TEXTUAL-CONVENTION
					TRAP=alarmTrapPnCPVTcn1dayTotalSES"
		::= { pnTcn1dayCurrentTotalEntry 6 }

	pnTcn1dayCurrentTotalBBE OBJECT-TYPE
		SYNTAX		NormalAlarmValue
		ACCESS		read-only
		STATUS		mandatory
		DESCRIPTION	"TCN-BBE-1day TOTAL
				 Refer to NormalAlarmValue of TEXTUAL-CONVENTION
					TRAP=alarmTrapPnCPVTcn1dayTotalBBE"
		::= { pnTcn1dayCurrentTotalEntry 7 }

	pnTcn1dayCurrentTotalSEP OBJECT-TYPE
		SYNTAX		NormalAlarmValue
		ACCESS		read-only
		STATUS		mandatory
		DESCRIPTION	"TCN-SEP-1day TOTAL
				 Refer to NormalAlarmValue of TEXTUAL-CONVENTION
					TRAP=alarmTrapPnCPVTcn1dayTotalSEP"
		::= { pnTcn1dayCurrentTotalEntry 8 }

	pnTcn1dayCurrentCHTable OBJECT-TYPE
		SYNTAX		SEQUENCE OF PnTcn1dayCurrentCHEntry
		ACCESS		not-accessible
		STATUS		mandatory
		DESCRIPTION	"TCN 1day Current CH Table"
		::= { pnAsTcnGroup 4 }

	pnTcn1dayCurrentCHEntry OBJECT-TYPE
		SYNTAX		PnTcn1dayCurrentCHEntry
		ACCESS		not-accessible
		STATUS		mandatory
		INDEX		{
		                                pnTcn1dayCurrentCHPasoIndex
					}
		::= { pnTcn1dayCurrentCHTable 1 }

	PnTcn1dayCurrentCHEntry ::= SEQUENCE {
					  pnTcn1dayCurrentCHPasoIndex IpAddress,
					  pnTcn1dayCurrentCHUAS      OCTET STRING,
					  pnTcn1dayCurrentCHES       OCTET STRING,
					  pnTcn1dayCurrentCHSES      OCTET STRING,
					  pnTcn1dayCurrentCHBBE      OCTET STRING,
					  pnTcn1dayCurrentCHSEP      OCTET STRING
					}

	pnTcn1dayCurrentCHPasoIndex OBJECT-TYPE
		SYNTAX		IpAddress 
		ACCESS		read-only
		STATUS		mandatory
		DESCRIPTION	"Pasolink IP Address Index"
		::= { pnTcn1dayCurrentCHEntry 1 }

	pnTcn1dayCurrentCHUAS OBJECT-TYPE
		SYNTAX		OCTET STRING (SIZE (1))
		ACCESS		read-only
		STATUS		mandatory
		DESCRIPTION	"This item is not used.
				 TCN-UAS-1day CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnCPVTcn1dayCHUAS"
		::= { pnTcn1dayCurrentCHEntry  2 }

	pnTcn1dayCurrentCHES OBJECT-TYPE
		SYNTAX		OCTET STRING (SIZE (1))
		ACCESS		read-only
		STATUS		mandatory
		DESCRIPTION	"This item is not used.
				 TCN-ES-1day CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnCPVTcn1dayCHES"
		::= { pnTcn1dayCurrentCHEntry  3 }

	pnTcn1dayCurrentCHSES OBJECT-TYPE
		SYNTAX		OCTET STRING (SIZE (1))
		ACCESS		read-only
		STATUS		mandatory
		DESCRIPTION	"This item is not used.
				 TCN-SES-1day CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnCPVTcn1dayCHSES"
		::= { pnTcn1dayCurrentCHEntry  4 }

	pnTcn1dayCurrentCHBBE OBJECT-TYPE
		SYNTAX		OCTET STRING (SIZE (1))
		ACCESS		read-only
		STATUS		mandatory
		DESCRIPTION	"This item is not used.
				 TCN-BBE-1day CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnCPVTcn1dayCHBBE"
		::= { pnTcn1dayCurrentCHEntry  5 }

	pnTcn1dayCurrentCHSEP OBJECT-TYPE
		SYNTAX		OCTET STRING (SIZE (1))
		ACCESS		read-only
		STATUS		mandatory
		DESCRIPTION	"This item is not used.
				 TCN-SEP-1day CHxx
					(xx : 1-16 only selected 4ch.)
					  0:Normal,
					  1:Alarm
					
					 [Description]
					 Bit 0 = 1st Selected CH (0:Normal, 1:Alarm)
					 Bit 1 = 2nd Selected CH
					 Bit 2 = 3rd Selected CH
					 Bit 3 = 4th Selected CH
					TRAP=alarmTrapPnCPVTcn1dayCHSEP"
		::= { pnTcn1dayCurrentCHEntry  6 }

	pnTcnCurrentUAETable OBJECT-TYPE
		SYNTAX		SEQUENCE OF PnTcnCurrentUAEEntry
		ACCESS		not-accessible
		STATUS		mandatory
		DESCRIPTION	"TCN Current UAE"
		::= { pnAsTcnGroup 5 }

	pnTcnCurrentUAEEntry OBJECT-TYPE
		SYNTAX		PnTcnCurrentUAEEntry
		ACCESS		not-accessible
		STATUS		mandatory
		INDEX		{
		                                pnTcnCurrentUAEPasoIndex
					}
		::= { pnTcnCurrentUAETable 1 }

	PnTcnCurrentUAEEntry ::= SEQUENCE {
					  pnTcnCurrentUAEPasoIndex	IpAddress,
					}

	pnTcnCurrentUAEPasoIndex OBJECT-TYPE
		SYNTAX		IpAddress 
		ACCESS		read-only
		STATUS		mandatory
		DESCRIPTION	"Pasolink IP Address Index"
		::= { pnTcnCurrentUAEEntry 1 }

	pnTcnTCSTable OBJECT-TYPE
		SYNTAX		SEQUENCE OF PnTcnTCSEntry
		ACCESS		not-accessible
		STATUS		mandatory
		DESCRIPTION	"TCN TCS Table"
		::= { pnAsTcnGroup 6 }

	pnTcnTCSEntry OBJECT-TYPE
		SYNTAX		PnTcnTCSEntry
		ACCESS		not-accessible
		STATUS		mandatory
		INDEX		{
						pnTcnTCSPasoIndex,
						pnTcnTCSSysIndex
					}
		::= { pnTcnTCSTable 1 }

	PnTcnTCSEntry ::= SEQUENCE {
	                                  pnTcnTCSPasoIndex IpAddress,
					  pnTcnTCSSysIndex    INTEGER,
					  pnTcnTCS15minRxLev  NormalAlarmValue,
					  pnTcnTCS1dayRxLev   NormalAlarmValue
					}

	pnTcnTCSPasoIndex OBJECT-TYPE
		SYNTAX		IpAddress 
		ACCESS		read-only
		STATUS		mandatory
		DESCRIPTION	"Pasolink IP Address Index"
		::= { pnTcnTCSEntry 1 }

	pnTcnTCSSysIndex OBJECT-TYPE
		SYNTAX		INTEGER{
					  no1(1),
					  no2(2)
					}
		ACCESS		read-only
		STATUS		mandatory
		DESCRIPTION	"TCN TCS System Index
					  1:No.1
					  2:No.2
				 *)No.2 is available for 1+1 system."
		::= { pnTcnTCSEntry 2 }

	pnTcnTCS15minRxLev OBJECT-TYPE
		SYNTAX		NormalAlarmValue
		ACCESS		read-only
		STATUS		mandatory
		DESCRIPTION	"TCN-RX LEV-15min
				 Refer to NormalAlarmValue of TEXTUAL-CONVENTION
					TRAP=alarmTrapPnCPVTcnTCS15minRxLev"
		::= { pnTcnTCSEntry 3 }

	pnTcnTCS1dayRxLev OBJECT-TYPE
		SYNTAX		NormalAlarmValue
		ACCESS		read-only
		STATUS		mandatory
		DESCRIPTION	"TCN-RX LEV-1day
				 Refer to NormalAlarmValue of TEXTUAL-CONVENTION
					TRAP=alarmTrapPnCPVTcnTCS1dayRxLev"
		::= { pnTcnTCSEntry 4 }

	pnAsAuxIOGroup OBJECT IDENTIFIER
		::= { pnAlarmStatusGroup 7 }

	pnAuxInputStatusTable OBJECT-TYPE
		SYNTAX		SEQUENCE OF PnAuxInputStatusEntry
		ACCESS		not-accessible
		STATUS		mandatory
		DESCRIPTION	"AUX Input Status Table"
		::= { pnAsAuxIOGroup 1 }

	pnAuxInputStatusEntry OBJECT-TYPE
		SYNTAX		PnAuxInputStatusEntry
		ACCESS		not-accessible
		STATUS		mandatory
		INDEX		{
						pnAuxInputStatusPasoIndex,
						pnAuxInputStatusIndex
					}
		::= { pnAuxInputStatusTable 1 }

	PnAuxInputStatusEntry ::= SEQUENCE {
                                          pnAuxInputStatusPasoIndex IpAddress,
					  pnAuxInputStatusIndex  INTEGER,
					  pnAuxInputStatusValue  INTEGER
					}

	pnAuxInputStatusPasoIndex OBJECT-TYPE
		SYNTAX		IpAddress 
		ACCESS		read-only
		STATUS		mandatory
		DESCRIPTION	"Pasolink IP Address Index"
		::= { pnAuxInputStatusEntry 1 }

	pnAuxInputStatusIndex OBJECT-TYPE
		SYNTAX		INTEGER{
					  auxInput1(1),
					  auxInput2(2),
					  auxInput3(3),
					  auxInput4(4),
					  auxInput5(5),
					  auxInput6(6)
					}
		ACCESS		read-only
		STATUS		mandatory
		DESCRIPTION	"AUX Input Status Index
					  1:Input 1
					  2:Input 2
					  3:Input 3
					  4:Input 4
					  5:Input 5
					  6:Input 6"
		::= { pnAuxInputStatusEntry 2 }

	pnAuxInputStatusValue OBJECT-TYPE
		SYNTAX		INTEGER(0..2)
		ACCESS		read-only
		STATUS		mandatory
		DESCRIPTION	"ITEM NAME(INPUT-x)
					(x : 1-6)
					  0:Invalid,
					  1:Open State,
					  2:Close State
					TRAP=statusTrapPnCPVAuxInput"
		::= { pnAuxInputStatusEntry 3 }

	pnAuxOutputStatusTable OBJECT-TYPE
		SYNTAX		SEQUENCE OF PnAuxOutputStatusEntry
		ACCESS		not-accessible
		STATUS		mandatory
		DESCRIPTION	"AUX Output Status Table"
		::= { pnAsAuxIOGroup 2 }

	pnAuxOutputStatusEntry OBJECT-TYPE
		SYNTAX		PnAuxOutputStatusEntry
		ACCESS		not-accessible
		STATUS		mandatory
		INDEX		{
					        pnAuxOutputStatusPasoIndex,
						pnAuxOutputStatusIndex
					}
		::= { pnAuxOutputStatusTable 1 }

	PnAuxOutputStatusEntry ::= SEQUENCE {
					  pnAuxOutputStatusPasoIndex IpAddress,
					  pnAuxOutputStatusIndex  INTEGER,
					  pnAuxOutputStatusValue  INTEGER
					}

	pnAuxOutputStatusPasoIndex OBJECT-TYPE
		SYNTAX		IpAddress 
		ACCESS		read-only
		STATUS		mandatory
		DESCRIPTION	"Pasolink IP Address Index"
		::= { pnAuxOutputStatusEntry 1 }

	pnAuxOutputStatusIndex OBJECT-TYPE
		SYNTAX		INTEGER{
					  auxOutput1(1),
					  auxOutput2(2),
					  auxOutput3(3),
					  auxOutput4(4)
					}
		ACCESS		read-only
		STATUS		mandatory
		DESCRIPTION	"AUX Output Status Index
					  1:Output 1
					  2:Output 2
					  3:Output 3
					  4:Output 4"
		::= { pnAuxOutputStatusEntry 2 }

	pnAuxOutputStatusValue OBJECT-TYPE
		SYNTAX		INTEGER(0..2)
		ACCESS		read-only
		STATUS		mandatory
		DESCRIPTION	"ITEM NAME(OUTPUT-x)
					(x : 1-4)
					  0:Invalid,
					  1:Open state,
					  2:Close state

					*) This value is for control house keeping
					TRAP=eventTrapPnCPVAuxOutput"
		::= { pnAuxOutputStatusEntry 3 }

	pnAuxClusterAlarmTable OBJECT-TYPE
		SYNTAX		SEQUENCE OF PnAuxClusterAlarmEntry
		ACCESS		not-accessible
		STATUS		mandatory
		DESCRIPTION	"AUX Cluster Alarm Table"
		::= { pnAsAuxIOGroup 3 }

	pnAuxClusterAlarmEntry OBJECT-TYPE
		SYNTAX		PnAuxClusterAlarmEntry
		ACCESS		not-accessible
		STATUS		mandatory
		INDEX		{
						pnAuxClusterAlarmPasoIndex,
						pnAuxClusterAlarmIndex
					}
		::= { pnAuxClusterAlarmTable 1 }

	PnAuxClusterAlarmEntry ::= SEQUENCE {
					  pnAuxClusterAlarmPasoIndex  IpAddress,
					  pnAuxClusterAlarmIndex  INTEGER,
					  pnAuxClusterAlarmValue  NormalAlarmValue
					}

	pnAuxClusterAlarmPasoIndex OBJECT-TYPE
		SYNTAX		IpAddress 
		ACCESS		read-only
		STATUS		mandatory
		DESCRIPTION	"Pasolink IP Address Index"
		::= { pnAuxClusterAlarmEntry 1 }

	pnAuxClusterAlarmIndex OBJECT-TYPE
		SYNTAX		INTEGER{
					  clusterAlarm1(1),
					  clusterAlarm2(2),
					  clusterAlarm3(3),
					  clusterAlarm4(4)
					}
		ACCESS		read-only
		STATUS		mandatory
		DESCRIPTION	"
					AUX Cluster Alarm Index
					  1:Cluster Alarm 1
					  2:Cluster Alarm 2
					  3:Cluster Alarm 3
					  4:Cluster Alarm 4"
					

		::= { pnAuxClusterAlarmEntry 2 }

	pnAuxClusterAlarmValue OBJECT-TYPE
		SYNTAX		NormalAlarmValue
		ACCESS		read-only
		STATUS		mandatory
		DESCRIPTION	"This is not used.
				 CLUSTERx ALARM
					(x : 1-4)
					TRAP=alarmTrapPnCPVAuxClusterAlarm"
		::= { pnAuxClusterAlarmEntry 3 }

-----------------------------------------------
-- pnEquipmentSetUpGroup Group Definitions
-----------------------------------------------

	pnEsCommonTable OBJECT-TYPE
		SYNTAX		SEQUENCE OF PnEsCommonEntry
		ACCESS		not-accessible
		STATUS		mandatory
		DESCRIPTION	"Es Common Table"
		::= { pnEquipmentSetUpGroup 1 }

	pnEsCommonEntry OBJECT-TYPE
		SYNTAX		PnEsCommonEntry
		ACCESS		not-accessible
		STATUS		mandatory
		INDEX		{
		                          pnEsCommonPasoIndex
					}
		::= { pnEsCommonTable 1 }

	PnEsCommonEntry ::= SEQUENCE {
		                          pnEsCommonPasoIndex IpAddress,
					  pnEsSystemArchitecture	INTEGER,
					  pnEsRedundancy	INTEGER,
					  pnEsIntfcMainWorkSelect	INTEGER,
					  pnEsModulationScheme	INTEGER,
					  pnEsTransmissionCapacity	INTEGER ,
					  pnEsLANPortUsage	INTEGER,
					  pnEsTxSWType	INTEGER,

					  pnEsLan2mCapacityDirA	INTEGER,
					  pnEsLanScAssignmentDirA	INTEGER
					}

	pnEsCommonPasoIndex OBJECT-TYPE
		SYNTAX		IpAddress 
		ACCESS		read-only
		STATUS		mandatory
		DESCRIPTION	"Pasolink IP Address Index"
		::= { pnEsCommonEntry 1 }

	pnEsSystemArchitecture OBJECT-TYPE
		SYNTAX		INTEGER (0..255)
		ACCESS		read-only
		STATUS		mandatory
		DESCRIPTION	"USER INTERFACE
					  0:Invalid,
					  1:PDH E1,
					  2:PDH E1 with LAN"
		::= { pnEsCommonEntry 2 }

	pnEsRedundancy OBJECT-TYPE
		SYNTAX		INTEGER (0..7)
		ACCESS		read-only
		STATUS		mandatory
		DESCRIPTION	"REDUNDANCY SETTING
					  0:Invalid,
					  1:1+0(TERM),
					  2:1+1(HOT STANDBY TERM),
					  3:1+1(TWINPATH TERM),
					  20:1+0 FIX"
		::= { pnEsCommonEntry 3 }


	pnEsIntfcMainWorkSelect OBJECT-TYPE
		SYNTAX		INTEGER (0..255)
		ACCESS		read-only
		STATUS		mandatory
		DESCRIPTION	"INTFC
					  0:BLANK, 
					  1.16xE1 BASIC PKG,
					  2.16xE1 STANDARD PKG(E/W LAN),
					  14.5xE1 BASIC PKG"
		::= { pnEsCommonEntry 6 }


	pnEsModulationScheme OBJECT-TYPE
		SYNTAX		INTEGER (0..6)
		ACCESS		read-only
		STATUS		mandatory
		DESCRIPTION	"MODULATION SCHEME
					  0:Invalid,
					  1:QPSK,
					  2:16QAM"
					
		::= { pnEsCommonEntry 8 }

	pnEsTransmissionCapacity OBJECT-TYPE
		SYNTAX		INTEGER  (0..8)
		ACCESS		read-only
		STATUS		mandatory
		DESCRIPTION	"TRANSMISSION CAPACITY
					  0:Invalid,
					  2:10MB
					  3:20MB
					  4:40MB"
					
		::= { pnEsCommonEntry 9 }

	pnEsLANPortUsage OBJECT-TYPE
		SYNTAX		INTEGER (0..14)
		ACCESS		read-only
		STATUS		mandatory
		DESCRIPTION	"LAN PORT USAGE
					  0:INVALID,
					  1:NOT USED ,
					  2:P1-2 SHARED/1PORT ONLY(MAIN),
					  3:P1-2 SEPARATED(MAIN),
					  4:P1-2 SHARED/1PORT ONLY(SC),
					
					  *) The values from 1 to 9 and 15 are only for PDH.
					      The values from 11 to 14 are only for SDH.
					      This value is fixed to 0 when LAN is not used."
		::= { pnEsCommonEntry 10 }

	pnEsTxSWType OBJECT-TYPE
		SYNTAX		INTEGER (0..2)
		ACCESS		read-only
		STATUS		mandatory
		DESCRIPTION	"TX SW TYPE
					 0:Invalid,
					 1:MUTE,
					 2:RF SW TYPE--Not used"
		::= { pnEsCommonEntry 11 }









	pnEsLan2mCapacityDirA OBJECT-TYPE
		SYNTAX		INTEGER (0..100)
		ACCESS		read-only
		STATUS		mandatory
		DESCRIPTION	"LAN & 2M CAPACITY[Mbps]
					
					  *)This Value is fixed 0 when Main CH isn't used by LAN."
		::= { pnEsCommonEntry 14 }

	pnEsLanScAssignmentDirA OBJECT-TYPE
		SYNTAX		INTEGER (0..3)
		ACCESS		read-only
		STATUS		mandatory
		DESCRIPTION	"LAN & SC ASSIGNMENT
					  0:INVALID,
					  1:64Kbp,
					  2:128Kbps,
					  3:256Kbps
					
					  *)This Value is fixed to 0 when SC isn't used by LAN.  "
		::= { pnEsCommonEntry 15 }

	pnEsSysTable OBJECT-TYPE
		SYNTAX		SEQUENCE OF PnEsSysEntry
		ACCESS		not-accessible
		STATUS		mandatory
		DESCRIPTION	"Sys Item Table"
		::= { pnEquipmentSetUpGroup 2 }

	pnEsSysEntry OBJECT-TYPE
		SYNTAX		PnEsSysEntry
		ACCESS		not-accessible
		STATUS		mandatory
		INDEX		{
						pnEsSysPasoIndex,
						pnEsSysIndex
					}
		::= { pnEsSysTable 1 }

	PnEsSysEntry ::= SEQUENCE {
					  pnEsSysPasoIndex    IpAddress,
					  pnEsSysIndex        INTEGER,
					  pnEsSysTxFreq       DisplayString,
					  pnEsSysRxFreq       DisplayString,
					  pnEsSysTxPowerCont  INTEGER,
					  pnEsSysFrameID      INTEGER
					}

	pnEsSysPasoIndex OBJECT-TYPE
		SYNTAX		IpAddress 
		ACCESS		read-only
		STATUS		mandatory
		DESCRIPTION	"Pasolink IP Address Index"
		::= { pnEsSysEntry 1 }

	pnEsSysIndex OBJECT-TYPE
		SYNTAX		INTEGER{
					  no1(1),
					  no2(2)
					}
		ACCESS		read-only
		STATUS		mandatory
		::= { pnEsSysEntry 2 }

	pnEsSysTxFreq OBJECT-TYPE
		SYNTAX		DisplayString (SIZE (0..9))
		ACCESS		read-only
		STATUS		mandatory
		DESCRIPTION	"TX RF FREQUENCY(No.x) [MHz]  x=1 or 2
					  *)No.2 is available when Redundancy is 1+1(HS) or 1+1(TP)."
		::= { pnEsSysEntry 3 }

	pnEsSysRxFreq OBJECT-TYPE
		SYNTAX		DisplayString (SIZE (0..9))
		ACCESS		read-only
		STATUS		mandatory
		DESCRIPTION	"RX RF FREQUENCY(No.x) [MHz]   x=1 or 2
					  *)No.2 is available when Redundancy is 1+1(HS) or 1+1(TP)."
		::= { pnEsSysEntry 4 }

	pnEsSysTxPowerCont OBJECT-TYPE
		SYNTAX		INTEGER (0..2)
		ACCESS		read-only
		STATUS		mandatory
		DESCRIPTION	"TX POWER CONTROL
					  0:Invalid,
					  1:MTPC,
					  2:ATPC
					
					  *)No.2 is not used."
		::= { pnEsSysEntry 5 }

	pnEsSysFrameID OBJECT-TYPE
		SYNTAX		INTEGER (0..32)
		ACCESS		read-only
		STATUS		mandatory
		DESCRIPTION	"FRAME ID(No.x)  x=1 or 2
					  0:Invalid,
					  Other: Frame ID Number.
					
					  *)No.2 is unavailable when Redundancy is 1+0.
					  *)No.2 is fixed to 0 when Redundancy is 1+0."
		::= { pnEsSysEntry 6 }


-----------------------------------------------
-- pnProvisioningGroup Group Definitions
-----------------------------------------------

 	pnProvCHTable OBJECT-TYPE
		SYNTAX		SEQUENCE OF PnProvCHEntry
		ACCESS		not-accessible
		STATUS		mandatory
		DESCRIPTION	"Prov Ch Table"
		::= { pnProvisioningGroup 1 }

	pnProvCHEntry OBJECT-TYPE
		SYNTAX		PnProvCHEntry
		ACCESS		not-accessible
		STATUS		mandatory
		INDEX		{
						pnProvCHPasoIndex
					}
		::= { pnProvCHTable 1 }

	PnProvCHEntry ::= SEQUENCE {
					  pnProvCHPasoIndex	IpAddress,
					  pnChUsage	OCTET STRING,
					  pnChCondition	OCTET STRING,
					  pnChImpedance	OCTET STRING,
 					}

	pnProvCHPasoIndex OBJECT-TYPE
		SYNTAX		IpAddress 
		ACCESS		read-only
		STATUS		mandatory
		DESCRIPTION	"Pasolink IP Address Index"
		::= { pnProvCHEntry 1 }

	pnChUsage OBJECT-TYPE
		SYNTAX		OCTET STRING (SIZE (48))
		ACCESS		read-only
		STATUS		mandatory
		DESCRIPTION	"CH USAGE(CHxx)
					xx=1-16
					  0:Invalid,
					  1:Not Used,
					  2:Used,
					  3:Used(LAN)
					
					  [Description]
					    Byte 0 = CH01(0:Invalid, 1:Not Used, 2:Used(E1), 3:Used(LAN))
					    Byte 1 = CH02
					    ...
					    Byte 14 = CH15 for E1 interface
					    Byte 15 = CH16 for E1 interface
					TRAP=eventTrapPnCPVCHUsage"
		::= { pnProvCHEntry  2 }

	pnChCondition OBJECT-TYPE
		SYNTAX		OCTET STRING (SIZE (6))
		ACCESS		read-only
		STATUS		mandatory
		DESCRIPTION	"CH CONDITION
					  [Description]
					    Byte 0 = CH USAGE ERROR REORT
					                  0:Invalid, 1:Not Report, 2:Report
					    Byte 1 = AIS ACTIVATION CONDITION
					                  0:Invalid, 1:LOF+HIGH BER 2:LOF
					    Byte 2 = AIS ACTIVATION DELAY --Not Used
					                  0:Invalid, 1:Off, 2:On
					    Byte 3 = AIS GENERATED REPORT
					                  0:Invalid, 1:Not Report, 2:Report
					    Byte 4 = AIS RECEIVED REPORT
					                  0:Invalid, 1:Not Report, 2:Report
					    Byte 5 = AIS RECEIVED CONDITION
					                  0:Invalid, 1:Alarm, 2:Status
					TRAP=eventTrapPnCPVCHCondition"
		::= { pnProvCHEntry  3 }

	pnChImpedance OBJECT-TYPE
		SYNTAX		OCTET STRING (SIZE (10))
		ACCESS		read-only
		STATUS		mandatory
		DESCRIPTION	"E1 PORT IMPEDANCE
					  0:Invalid,
					  1:120[ohm],
					  2:75[ohm]
					
					  [Description]
					    BYTE0 = E1 PORT IMPEDANCE(CH1) (0:Invalid, 1:120[ohm], 2:75[ohm])
					    BYTE1 = E1 PORT IMPEDANCE(CH2)
					    BYTE2 = E1 PORT IMPEDANCE(CH3)
					    BYTE3 = E1 PORT IMPEDANCE(CH4)
					    BYTE4 = E1 PORT IMPEDANCE(CH5-8)
					    BYTE5 = E1 PORT IMPEDANCE(CH9-16)
					
					TRAP=eventTrapPnCPVCHImpedance"
		::= { pnProvCHEntry  4 }

 	pnProvBERThresholdTable OBJECT-TYPE
		SYNTAX		SEQUENCE OF PnProvBERThresholdEntry
		ACCESS		not-accessible
		STATUS		mandatory
		DESCRIPTION	"Prov BER Threshold Table"
		::= { pnProvisioningGroup 3 }

	pnProvBERThresholdEntry OBJECT-TYPE
		SYNTAX		PnProvBERThresholdEntry
		ACCESS		not-accessible
		STATUS		mandatory
		INDEX		{
						pnProvBERThresholdPasoIndex
					}
		::= { pnProvBERThresholdTable 1 }

	PnProvBERThresholdEntry ::= SEQUENCE {
					  pnProvBERThresholdPasoIndex	IpAddress,
					  pnProvBERThreshold	OCTET STRING
 					}

	pnProvBERThresholdPasoIndex OBJECT-TYPE
		SYNTAX		IpAddress 
		ACCESS		read-only
		STATUS		mandatory
		DESCRIPTION	"Pasolink IP Address Index"
		::= { pnProvBERThresholdEntry 1 }

	pnProvBERThreshold OBJECT-TYPE
		SYNTAX		OCTET STRING (SIZE (8))
		ACCESS		read-only
		STATUS		mandatory
		DESCRIPTION	"BER THRESHOLD SETTING

					  
					  [Description]
					    Byte 0 = HIGH BER THRESHOLD
					                (0:INVALID, 1:1E-3, 2:1E-4, 3:1E-5)
					    Byte 1 = HIGH BER THRESHOLD(DIR-B)  --Not used
					                (0:INVALID, 1:1E-3, 2:1E-4, 3:1E-5)
					    Byte 2 = LOW BER THRESHOLD
					                (0:INVALID, 1:1E-6, 2:1E-7, 3:1E-8, 4:1E-9)
					    Byte 3 = LOW BER THRESHOLD(DIR-B)   --Not used
					                (0:INVALID, 1:1E-6, 2:1E-7, 3:1E-8, 4:1E-9)
					    Byte 4 = E-BER(DMR)  --Not used
					                (0:INVALID, 1:1E-3, 2:1E-4, 3:1E-5)
					    Byte 5 = SD(DMR)  --Not used
					                (0:INVALID, 1:1E-6, 2:1E-7, 3:1E-8, 4:1E-9)
					    Byte 6 = E-BER(MUX)  --Not used
					                 (0:INVALID, 1:1E-3, 2:1E-4, 3:1E-5)
					    Byte 7 = SD(MUX)  --Not used
					                (0:INVALID, 1:1E-6, 2:1E-7, 3:1E-8, 4:1E-9)
					TRAP=eventTrapPnCPVBERThreshold"
		::= { pnProvBERThresholdEntry 2 }

 	pnProvSCAssignmentTable OBJECT-TYPE
		SYNTAX		SEQUENCE OF PnProvSCAssignmentEntry
		ACCESS		not-accessible
		STATUS		mandatory
		DESCRIPTION	"Prov SC Assignment Table"
		::= { pnProvisioningGroup 5 }

	pnProvSCAssignmentEntry OBJECT-TYPE
		SYNTAX		PnProvSCAssignmentEntry
		ACCESS		not-accessible
		STATUS		mandatory
		INDEX		{
						pnProvSCAssignmentPasoIndex
					}
		::= { pnProvSCAssignmentTable 1 }

	PnProvSCAssignmentEntry ::= SEQUENCE {
					  pnProvSCAssignmentPasoIndex	IpAddress,
					  pnProvSCAssign	OCTET STRING
 					}

	pnProvSCAssignmentPasoIndex OBJECT-TYPE
		SYNTAX		IpAddress 
		ACCESS		read-only
		STATUS		mandatory
		DESCRIPTION	"Pasolink IP Address Index"
		::= { pnProvSCAssignmentEntry 1 }

	pnProvSCAssign OBJECT-TYPE
		SYNTAX		OCTET STRING (SIZE (8))
		ACCESS		read-only
		STATUS		mandatory
		DESCRIPTION	"SC ASSIGNMENT
					  [Description]
					    Byte 0 = RS-232C-1
					         (0:INVALID, 1:NOT USED, 2:SC1)
					    Byte 1 = RS-232C-2
					         (0:INVALID, 1:NOT USED, 3:SC2)
					    Byte 2 = V11-1
					         (0:INVALID, 1:NOT USED, 2:SC1)
					    Byte 3 = V11-2
					         (0:INVALID, 1:NOT USED, 22:SC3-4)
					    Byte 4 = SC LAN1
					         (0:INVALID, 1:NOT USED, 2:SC1, 10:SC1-2,
					          14:SC1-4)
					    Byte 6 = V11-1 DIRECTION SETTING
					         (0:INVALID, 1:CO-DIRECTIONAL, 2:CONTRA-DIRECTIONAL)
					    Byte 7 = V11-2 DIRECTION SETTING --Not Used
					         (0:INVALID, 2:CONTRA-DIRECTIONAL)
					
					TRAP=eventTrapPnCPVSCAssign"
		::= { pnProvSCAssignmentEntry 2 }

 	pnProvLANPortSetTable OBJECT-TYPE
		SYNTAX		SEQUENCE OF PnProvLANPortSetEntry
		ACCESS		not-accessible
		STATUS		mandatory
		DESCRIPTION	"Prov LAN Port Set Table"
		::= { pnProvisioningGroup 6 }

	pnProvLANPortSetEntry OBJECT-TYPE
		SYNTAX		PnProvLANPortSetEntry
		ACCESS		not-accessible
		STATUS		mandatory
		INDEX		{
						pnProvLANPortSetPasoIndex
					}
		::= { pnProvLANPortSetTable 1 }

	PnProvLANPortSetEntry ::= SEQUENCE {
					  pnProvLANPortSetPasoIndex	IpAddress,
					  pnProvLANPortSet	OCTET STRING
 					}

	pnProvLANPortSetPasoIndex OBJECT-TYPE
		SYNTAX		IpAddress 
		ACCESS		read-only
		STATUS		mandatory
		DESCRIPTION	"Pasolink IP Address Index"
		::= { pnProvLANPortSetEntry 1 }

	pnProvLANPortSet OBJECT-TYPE
		SYNTAX		OCTET STRING (SIZE (36))
		ACCESS		read-only
		STATUS		mandatory
		DESCRIPTION	"LAN PORT SETTING
					  [Description]
					  Byte 0 = SWITCHING FUNCTION
					       (0:INVALID, 1:DISABLED(No Report), 2:ENABLED(Report))
					
					  Byte 1 = SPEED & DUPLEX PORT1
					  Byte 2 = SPEED & DUPLEX PORT2
					  Byte 3 = SPEED & DUPLEX PORT3 --Not used
					  Byte 4 = SPEED & DUPLEX PORT4 --Not used
					  Byte 5 = INTFC(2) SPEED & DUPLEX PORT1 --Not used
					  Byte 6 = INTFC(2) SPEED & DUPLEX PORT2 --Not used
					       (0:INVALID, 1:AUTONEG(AUTO-MDI/MDIX),
					        2:10M-HALF(MDI), 3:10M-FULL(MDI), 
					        4:100M-HALF(MDI), 5:100M-FULL(MDI), 
					        6:10M-HALF(MDIX), 7:10M-FULL(MDIX), 
					        8:100M-HALF(MDIX), 9:100M-FULL(MDIX))
					
					  Byte 7 = FLOW CONTROL PORT1
					  Byte 8 = FLOW CONTROL PORT2
					  Byte 9 = FLOW CONTROL PORT3 --Not used
					  Byte 10 = FLOW CONTROL PORT4 --Not used
					  Byte 11 = INTFC(2) FLOW CONTROL PORT1 --Not used
					  Byte 12 = INTFC(2) FLOW CONTROL PORT2 --Not used
					       (0:INVALID, 1:OFF, 2:ON)
					
					  Byte 13 = COLLISION REPORT PORT1
					  Byte 14 = COLLISION REPORT PORT2
					  Byte 15 = COLLISION REPORT PORT3 --Not used
					  Byte 16 = COLLISION REPORT PORT4 --Not used
					  Byte 17 = INTFC(2) COLLISION REPORT PORT1 --Not used
					  Byte 18 = INTFC(2) COLLISION REPORT PORT2 --Not used
					       (0:INVALID, 1:DISABLED(No Report), 2:ENABLED(Report))
					
					  Byte 19 = LINK LOSS FORWARDING PORT1
					  Byte 20 = LINK LOSS FORWARDING PORT2
					  Byte 21 = LINK LOSS FORWARDING PORT3 --Not used
					  Byte 22 = LINK LOSS FORWARDING PORT4 --Not used
					  Byte 23 = INTFC(2) LINK LOSS FWD PORT1 --Not used
					  Byte 24 = INTFC(2) LINK LOSS FWD PORT2 --Not used
					       (0:INVALID, 1:DISABLED, 2:ENABLED)
					
					  Byte 25 = LOCK SOURCE SETTING --Not used
					       (0:INVALID, 1:INTERNAL CLOCK, 
					        2:DMR -> INTERNAL CLOCK)
					
					  Byte 26 = 2M FRAMING PORT1
					  Byte 27 = 2M FRAMING PORT2 --Not used
					  Byte 28 = 2M FRAMING PORT3 --Not used
					  Byte 29 = 2M FRAMING PORT4 --Not used
					       (0:NOT USED, 1:PCM30, 2:PCM30C, 
					        3:PCM31, 4:PCM31C)
					
					  Byte 30 = PORT1 USAGE
					  Byte 31 = PORT2 USAGE
					  Byte 32 = PORT3 USAGE --Not used
					  Byte 33 = PORT4 USAGE --Not used
					  Byte 34 = INTFC(2) PORT1 USAGE --Not used
					  Byte 35 = INTFC(2) PORT2 USAGE --Not used
					       (0:INVALID, 1:NOT USED, 2:USED)
					TRAP=eventTrapPnCPVLanPortSetting"
		::= { pnProvLANPortSetEntry 2 }

	pnProvTxPowerContTable OBJECT-TYPE
		SYNTAX		SEQUENCE OF PnProvTxPowerContEntry
		ACCESS		not-accessible
		STATUS		mandatory
		DESCRIPTION	"PROV TX Power Cont Table"
		::= { pnProvisioningGroup 8 }

	pnProvTxPowerContEntry OBJECT-TYPE
		SYNTAX		PnProvTxPowerContEntry
		ACCESS		not-accessible
		STATUS		mandatory
		INDEX		{
						pnProvTxPowerContPasoIndex,
						pnProvTxPowerContIndex
					}
		::= { pnProvTxPowerContTable 1 }

	PnProvTxPowerContEntry ::= SEQUENCE {
	                                  pnProvTxPowerContPasoIndex IpAddress,
					  pnProvTxPowerContIndex  INTEGER,
					  pnProvTxPowerContValue  OCTET STRING
					}

	pnProvTxPowerContPasoIndex OBJECT-TYPE
		SYNTAX		IpAddress 
		ACCESS		read-only
		STATUS		mandatory
		DESCRIPTION	"Pasolink IP Address Index"
		::= { pnProvTxPowerContEntry 1 }

	pnProvTxPowerContIndex OBJECT-TYPE
		SYNTAX		INTEGER{
					  no1(1),
					  no2(2)
					}
		ACCESS		read-only
		STATUS		mandatory
		DESCRIPTION	"PROV TX Power Cont Index
					 1:No.1 when EQUIPMENT CONFIG is TERM.
					 2:No.2 when EQUIPMENT CONFIG is TERM."
		::= { pnProvTxPowerContEntry 2 }

	pnProvTxPowerContValue OBJECT-TYPE
		SYNTAX		OCTET STRING (SIZE (9))
		ACCESS		read-only
		STATUS		mandatory
		DESCRIPTION	"TX POWER CTRL

					
					  [Description]
						Byte 0
						MTPC TX POWER (signed char)
						Byte 1
						 ATPC THRESHOLD LEVEL <integral number>
						(signed char)
						Byte 2
						 ATPC THRESHOLD LEVEL <a place of decimal>
						  This value is fixed to 0.
						Byte 3
						 ADDITIONAL ATT
						  (char)
						Byte 4
						 ATPC(MAX)
						  (signed char)
						Byte 5
						ATPC(MIN)
						  (signed char)
						Byte 6
						 HYSTERESIS
						  This is fixed value.
						Byte 7
						 ATPC POWER MODE
						   0:INVALID, 1:HOLD, 2:MAX, 3:MIN 

						Byte 8
						  ODU COMM ALARM MODE
						  This is fixed value.

						*)In case of Byte 0 - 5, the range of each value is difined in the mib of 
						  invTRUProvRangeInfoValue.
					TRAP=eventTrapPnCPVTxPowerContValue"
		::= { pnProvTxPowerContEntry 3 }

 	pnProvSWCondTable OBJECT-TYPE
		SYNTAX		SEQUENCE OF PnProvSWCondEntry
		ACCESS		not-accessible
		STATUS		mandatory
		DESCRIPTION	"Prov SW Cond Table"
		::= { pnProvisioningGroup 9 }

	pnProvSWCondEntry OBJECT-TYPE
		SYNTAX		PnProvSWCondEntry
		ACCESS		not-accessible
		STATUS		mandatory
		INDEX		{
						pnProvSWCondPasoIndex
					}
		::= { pnProvSWCondTable 1 }

	PnProvSWCondEntry ::= SEQUENCE {
					  pnProvSWCondPasoIndex	IpAddress,
					  pnProvSWCondTxRxSW	OCTET STRING,
 					}

	pnProvSWCondPasoIndex OBJECT-TYPE
		SYNTAX		IpAddress 
		ACCESS		read-only
		STATUS		mandatory
		DESCRIPTION	"Pasolink IP Address Index"
		::= { pnProvSWCondEntry 1 }

	pnProvSWCondTxRxSW OBJECT-TYPE
		SYNTAX		OCTET STRING (SIZE (5))
		ACCESS		read-only
		STATUS		mandatory
		DESCRIPTION	"CONDITION for TX/RX SW

					  
					  [Description]
					  Byte 0 = TX SW PRIORITY
					      (0:INVALID, 1:NON PRIORITY, 2:PRIORITY No.1)
					  Byte 1 = RX SW PRIORITY
					      (0:INVALID, 1:NON PRIORITY, 2:PRIORITY No.1)
					  Byte 2 = RX SW MAINTENANCE MODE
					      (0:INVALID, 1:MANUAL, 2:FORCED)
					  Byte 3 = RX SW CONDITION-EARLY WARNING
					      (0:INVALID, 1:INCLUDED EW, 2:EXCLUDED EW)
					TRAP=eventTrapPnCPVSWCondTxRx"
		::= { pnProvSWCondEntry 2 }


	pnProvRelayTable OBJECT-TYPE
		SYNTAX		SEQUENCE OF PnProvRelayEntry
		ACCESS		not-accessible
		STATUS		mandatory
		DESCRIPTION	"Prov Relay Table"
		::= { pnProvisioningGroup 10 }

	pnProvRelayEntry OBJECT-TYPE
		SYNTAX		PnProvRelayEntry
		ACCESS		not-accessible
		STATUS		mandatory
		INDEX		{
						pnProvRelayPasoIndex
					}
		::= { pnProvRelayTable 1 }

	PnProvRelayEntry ::= SEQUENCE {
					  pnProvRelayPasoIndex	IpAddress,
					  pnProvRelayConfigData	OCTET STRING,
					  pnProvRelayClusterAssign	OCTET STRING
 					}

	pnProvRelayPasoIndex OBJECT-TYPE
		SYNTAX		IpAddress 
		ACCESS		read-only
		STATUS		mandatory
		DESCRIPTION	"Pasolink IP Address Index"
		::= { pnProvRelayEntry 1 }

	pnProvRelayConfigData OBJECT-TYPE
		SYNTAX		OCTET STRING (SIZE (48))
		ACCESS		read-only
		STATUS		mandatory
		DESCRIPTION	"RELAY CONFIGURATION CHANGED
					
					  [Description]
					  (Relay x (x:1~6))
					   [START BIT] = 64 * (x - 1)
					
					    Bit (0 + [START BIT]) = MAINT (Remark1)
					    Bit (1 + [START BIT]) = PS ALARM1 (Remark2)
					    Bit (2 + [START BIT]) = PS ALARM2 (Remark2)
					    Bit (3 + [START BIT]) = (FIXED to 0)
					    Bit (4 + [START BIT]) = (FIXED to 0)
					    Bit (5 + [START BIT]) = (FIXED to 0)
					    Bit (6 + [START BIT]) = (FIXED to 0)
					    Bit (7 + [START BIT]) = CPU ALARM (Remark2)
					    Bit (8 + [START BIT]) = ODU ALARM1 (Remark7)
					    Bit (9 + [START BIT]) = ODU ALARM2 (Remark7)
					    Bit (10 + [START BIT]) = IDU ALARM (Remark7)
					    Bit (11 + [START BIT]) = (FIXED to 0)
					    Bit (12 + [START BIT]) = (FIXED to 0)
					    Bit (13 + [START BIT]) = (FIXED to 0)
					    Bit (14 + [START BIT]) = (FIXED to 0)
					    Bit (15 + [START BIT]) = (FIXED to 0)
					    Bit (16 + [START BIT]) = TX POWER ALARM1 (Remark7)
					    Bit (17 + [START BIT]) = TX POWER ALARM2 (Remark7)
					    Bit (18 + [START BIT]) = TX IN LEV ALARM1 (Remark7)
					    Bit (19 + [START BIT]) = TX IN LEV ALARM2 (Remark7)
					    Bit (20 + [START BIT]) = RX LEV ALARM1 (Remark7)
					    Bit (21 + [START BIT]) = RX LEV ALARM2 (Remark7)
					    Bit (22 + [START BIT]) = APC ALARM1 (Remark7)
					    Bit (23 + [START BIT]) = APC ALARM2 (Remark7)
					    Bit (24 + [START BIT]) = IF CABLE SHORT ALARM1 (Remark7)
					    Bit (25 + [START BIT]) = IF CABLE SHORT ALARM2 (Remark7)
					    Bit (26 + [START BIT]) = ODU CPU ALARM1 (Remark7)
					    Bit (27 + [START BIT]) = ODU CPU ALARM2 (Remark7)
					    Bit (28 + [START BIT]) = (FIXED to 0)
					    Bit (29 + [START BIT]) = (FIXED to 0)
					    Bit (30 + [START BIT]) = (FIXED to 0)
					    Bit (31 + [START BIT]) = (FIXED to 0)
					    Bit (32 + [START BIT]) = MOD ALARM1 (Remark7)
					    Bit (33 + [START BIT]) = MOD ALARM2 (Remark7)
					    Bit (34 + [START BIT]) = DEM ALARM1 (Remark7)
					    Bit (35 + [START BIT]) = DEM ALARM2 (Remark7)
					    Bit (36 + [START BIT]) = CH INPUT LOSS (Remark7)
					    Bit (37 + [START BIT]) = CH AIS RECEIVED (Remark7)
					    Bit (38 + [START BIT]) = CH AIS GENERATED (Remark7)
					    Bit (39 + [START BIT]) = CH USAGE ERROR (Remark7)
					    Bit (40 + [START BIT]) = LOW BER ALARM1 (Remark7)
					    Bit (41 + [START BIT]) = LOW BER ALARM2 (Remark7)
					    Bit (42 + [START BIT]) = HIGH BER ALARM1 (Remark7)
					    Bit (43 + [START BIT]) = HIGH BER ALARM2 (Remark7)
					    Bit (44 + [START BIT]) = STM-1 TF ALARM (Remark7) --  Not Used
					    Bit (45 + [START BIT]) = STM-1 SLOS (Remark7) --  Not Used
					    Bit (46 + [START BIT]) = STM-1 RLOS (Remark7) --  Not Used
					    Bit (47 + [START BIT]) = LAN LINK ALARM (Remark7)
					    Bit (48 + [START BIT]) = LOF1 (Remark7)
					    Bit (49 + [START BIT]) = LOF2 (Remark7)
					    Bit (50 + [START BIT]) = X REF ALARM1 (Remark7) --  Not Used
					    Bit (51 + [START BIT]) = X REF ALARM2 (Remark7) --  Not Used
					    Bit (52 + [START BIT]) = X CTRL ALARM1 (Remark7) --  Not Used
					    Bit (53 + [START BIT]) = X CTRL ALARM2 (Remark7) --  Not Used
					    Bit (54 + [START BIT]) = SC LAN LINK ALARM (Remark7) --  Not Used
					    Bit (55 + [START BIT]) = WS INPUT LOSS (Remark7) --  Not Used
					    Bit (56 + [START BIT]) = CLUSTER ALARM1 (Remark6)
					    Bit (57 + [START BIT]) = CLUSTER ALARM2 (Remark5)
					    Bit (58 + [START BIT]) = CLUSTER ALARM3 (Remark4)
					    Bit (59 + [START BIT]) = CLUSTER ALARM4 (Remark3)
					    Bit (60 + [START BIT]) = HK1 OUTPUT (Remark6)
					    Bit (61 + [START BIT]) = HK2 OUTPUT (Remark5)
					    Bit (62 + [START BIT]) = HK3 OUTPUT (Remark4)
					    Bit (63 + [START BIT]) = HK4 OUTPUT (Remark3)
					
					  Remark1 : The value of Relay 1 is fixed to  1. 
					            The value of the other Relay is fixed to 0.
					  Remark2 : The value of Relay 3 is fixed to 1. 
					            The value of the other Relay is fixed to 0.
					  Remark3 : The value of Relay 3 is fixed to 1. 
					            The value of the other Relay is fixed to 0.
					  Remark4 : The value of Relay 4 is fixed to 1. 
					            The value of the other Relay is fixed to 0.
					  Remark5 : The value of Relay 5 is fixed to 1. 
					            The value of the other Relay is fixed to 0.
					  Remark6 : The value of Relay 6 is fixed to 1. 
					            The value of the other Relay is fixed to 0.
					  Remark7 : The value of Relay 1 and Relay 2 is fixed to 0. 
					            The value of the other Relay is 0 and 1.
					
					TRAP=eventTrapPnCPVRelayConfigData"
		::= { pnProvRelayEntry 2 }

	pnProvRelayClusterAssign OBJECT-TYPE
		SYNTAX		OCTET STRING (SIZE (4))
		ACCESS		read-only
		STATUS		mandatory
		DESCRIPTION	"CLUSTER INPUT
					  0:Invalid,
					  1:Disabled,
					  2:Enabled)
					
					  [Description]
					  Byte 0 = CLUSTER1 INPUT (0:Invalid, 1:Disabled, 2:Enabled)
					  Byte 1 = CLUSTER2 INPUT
					  Byte 2 = CLUSTER3 INPUT
					  Byte 3 = CLUSTER4 INPUT
					TRAP=eventTrapPnCPVRelayClusterAssign"
		::= { pnProvRelayEntry 3 }

	pnProvTCNTresholdGroup OBJECT IDENTIFIER
		::= { pnProvisioningGroup 11 }

	pnProvTCNThreshold15minTotalTable OBJECT-TYPE
		SYNTAX		SEQUENCE OF PnProvTCNThreshold15minTotalEntry
		ACCESS		not-accessible
		STATUS		mandatory
		DESCRIPTION	"Prov TCN Threshold 15min Total Table"
		::= { pnProvTCNTresholdGroup 1 }

	pnProvTCNThreshold15minTotalEntry OBJECT-TYPE
		SYNTAX		PnProvTCNThreshold15minTotalEntry
		ACCESS		not-accessible
		STATUS		mandatory
		INDEX		{
						pnProvTCNThreshold15minTotalPasoIndex,
						pnProvTCNThreshold15minTotalWPIndex,
						pnProvTCNThreshold15minTotalORIndex
					}
		::= { pnProvTCNThreshold15minTotalTable 1 }

	PnProvTCNThreshold15minTotalEntry ::= SEQUENCE {
					  pnProvTCNThreshold15minTotalPasoIndex IpAddress,
					  pnProvTCNThreshold15minTotalWPIndex  INTEGER,
					  pnProvTCNThreshold15minTotalORIndex  INTEGER,
					  pnProvTCNThreshold15minTotalValue    OCTET STRING
					}

	pnProvTCNThreshold15minTotalPasoIndex OBJECT-TYPE
		SYNTAX		IpAddress 
		ACCESS		read-only
		STATUS		mandatory
		DESCRIPTION	"Pasolink IP Address Index"
		::= { pnProvTCNThreshold15minTotalEntry 1 }

	pnProvTCNThreshold15minTotalWPIndex OBJECT-TYPE
		SYNTAX		INTEGER{
					  working-MUX(1),
					  protection-MUX(2),
					  working-DMR(3),
					  protection-DMR(4)
					}
		ACCESS		read-only
		STATUS		mandatory
		DESCRIPTION	"TCN 15min Current Total Working/Protection Index
					  1:Working(MUX),--Not Used
					  2:Protection(MUX),--Not Used
					  3:Working(DMR)
					  4:Protection(DMR)--Not Used
					
					"
		::= { pnProvTCNThreshold15minTotalEntry  2 }

	pnProvTCNThreshold15minTotalORIndex OBJECT-TYPE
		SYNTAX		INTEGER{
					  occur(1),
					  recover(2)
					}
		ACCESS		read-only
		STATUS		mandatory
		DESCRIPTION	"TCN Threshold 15min Total Occur/Recover Index
					  1:Occur,
					  2:Recover"
		::= { pnProvTCNThreshold15minTotalEntry  3 }

	pnProvTCNThreshold15minTotalValue OBJECT-TYPE
		SYNTAX		OCTET STRING (SIZE (24))
		ACCESS		read-only
		STATUS		mandatory
		DESCRIPTION	"TCN THRESHOLD 15MIN TOTAL
					
					  [Description]
					  (Byte 0 - Byte 3)   = OFS TCN THRESHOLD TOTAL-15min (0 - 900)
					  (Byte 4 - Byte 7)   = UAS TCN THRESHOLD TOTAL-15min (0 - 900)
					  (Byte 8 - Byte 11)  = ES TCN THRESHOLD TOTAL-15min  (0 - 900)
					  (Byte 12 - Byte 15) = SES TCN THRESHOLD TOTAL-15min (0 - 900)
					  (Byte 16 - Byte 19) = BBE TCN THRESHOLD TOTAL-15min 
					                        PDH(Bit Rate = 10MB)  : 0 - 804600
					                        PDH(Bit Rate = 20MB)  : 0 - 804600
					                        PDH(Bit Rate = 40MB)  : 0 - 804600
					  (Byte 20 - Byte 23) = SEP TCN THRESHOLD TOTAL-15min (0 - 900)
					TRAP=eventTrapPnCPVTCNTreshold15minTotal"
		::= { pnProvTCNThreshold15minTotalEntry 4 }

	pnProvTCNThreshold15minCHTable OBJECT-TYPE
		SYNTAX		SEQUENCE OF PnProvTCNThreshold15minCHEntry
		ACCESS		not-accessible
		STATUS		mandatory
		DESCRIPTION	"PROV TCN Threshold 15min CH Table"
		::= { pnProvTCNTresholdGroup 2 }

	pnProvTCNThreshold15minCHEntry OBJECT-TYPE
		SYNTAX		PnProvTCNThreshold15minCHEntry
		ACCESS		not-accessible
		STATUS		mandatory
		INDEX		{
						pnProvTCNThreshold15minCHPasoIndex,
						pnProvTCNThreshold15minCHIndex,
						pnProvTCNThreshold15minCHORIndex
					}
		::= { pnProvTCNThreshold15minCHTable 1 }

	PnProvTCNThreshold15minCHEntry ::= SEQUENCE {
					  pnProvTCNThreshold15minCHPasoIndex    IpAddress,
					  pnProvTCNThreshold15minCHIndex    INTEGER,
					  pnProvTCNThreshold15minCHORIndex  INTEGER,
					  pnProvTCNThreshold15minCHValue    OCTET STRING
					}

	pnProvTCNThreshold15minCHPasoIndex OBJECT-TYPE
		SYNTAX		IpAddress 
		ACCESS		read-only
		STATUS		mandatory
		DESCRIPTION	"Pasolink IP Address Index"
		::= { pnProvTCNThreshold15minCHEntry 1 }

	pnProvTCNThreshold15minCHIndex OBJECT-TYPE
		SYNTAX		INTEGER{
					  ch-A(1),
					  ch-B(2),
					  ch-C(3),
					  ch-D(4)
					}
		ACCESS		read-only
		STATUS		mandatory
		DESCRIPTION	"TCN 15min Current CH Index
					  1:CH-A,
					  2:CH-B,
					  3:CH-C,
					  4:CH-D
					"
		::= { pnProvTCNThreshold15minCHEntry 2 }

	pnProvTCNThreshold15minCHORIndex OBJECT-TYPE
		SYNTAX		INTEGER{
					  occur(1),
					  recover(2)
					}
		ACCESS		read-only
		STATUS		mandatory
		DESCRIPTION	"TCN Threshold 15min CH Occur/Recover Index
					  1:Occur,
					  2:Recover"
		::= { pnProvTCNThreshold15minCHEntry 3 }

	pnProvTCNThreshold15minCHValue OBJECT-TYPE
		SYNTAX		OCTET STRING (SIZE (24))
		ACCESS		read-only
		STATUS		mandatory
		DESCRIPTION	"This item is not used.
				 TCN THRESHOLD 15MIN CH
					  This value is used by only PDH.
					
					  [Description]
					  (Byte 0 - Byte 3)   = (Fixed to 0)
					  (Byte 4 - Byte 7)   = UAS TCN THRESHOLD CH-15min (0 - 900)
					  (Byte 8 - Byte 11)  = ES TCN THRESHOLD CH-15min  (0 - 900)
					  (Byte 12 - Byte 15) = SES TCN THRESHOLD CH-15min (0 - 900)
					  (Byte 16 - Byte 19) = BBE TCN THRESHOLD CH-15min (0 - 402300)
					  (Byte 20 - Byte 23) = SEP TCN THRESHOLD CH-15min (0 - 900)
					TRAP=eventTrapPnCPVTCNTreshold15minCH"
		::= { pnProvTCNThreshold15minCHEntry 4 }

	pnProvTCNThreshold1dayTotalTable OBJECT-TYPE
		SYNTAX		SEQUENCE OF PnProvTCNThreshold1dayTotalEntry
		ACCESS		not-accessible
		STATUS		mandatory
		DESCRIPTION	"PROV TCN Threshold 1day Total Table"
		::= { pnProvTCNTresholdGroup 3 }

	pnProvTCNThreshold1dayTotalEntry OBJECT-TYPE
		SYNTAX		PnProvTCNThreshold1dayTotalEntry
		ACCESS		not-accessible
		STATUS		mandatory
		INDEX		{
						pnProvTCNThreshold1dayTotalPasoIndex,
						pnProvTCNThreshold1dayTotalWPIndex,
						pnProvTCNThreshold1dayTotalORIndex
					}
		::= { pnProvTCNThreshold1dayTotalTable 1 }

	PnProvTCNThreshold1dayTotalEntry ::= SEQUENCE {
					  pnProvTCNThreshold1dayTotalPasoIndex  IpAddress,
					  pnProvTCNThreshold1dayTotalWPIndex  INTEGER,
					  pnProvTCNThreshold1dayTotalORIndex  INTEGER,
					  pnProvTCNThreshold1dayTotalValue    OCTET STRING
					}

	pnProvTCNThreshold1dayTotalPasoIndex OBJECT-TYPE
		SYNTAX		IpAddress 
		ACCESS		read-only
		STATUS		mandatory
		DESCRIPTION	"Pasolink IP Address Index"
		::= { pnProvTCNThreshold1dayTotalEntry 1 }

	pnProvTCNThreshold1dayTotalWPIndex OBJECT-TYPE
		SYNTAX		INTEGER{
					  working-MUX(1),
					  protection-MUX(2),
					  working-DMR(3),
					  protection-DMR(4)
					}
		ACCESS		read-only
		STATUS		mandatory
		DESCRIPTION	"TCN 1day Current Total Working/Protection Index
					  1:Working(MUX),
					  2:Protection(MUX),
					  3:Working(DMR),
					  4:Protection(DMR)"
					
		::= { pnProvTCNThreshold1dayTotalEntry 2 }


	pnProvTCNThreshold1dayTotalORIndex OBJECT-TYPE
		SYNTAX		INTEGER{
					  occur(1),
					  recover(2)
					}
		ACCESS		read-only
		STATUS		mandatory
		DESCRIPTION	"TCN Threshold 1day Total Occur/Recover Index
					  1:Occur,
					  2:Recover"
		::= { pnProvTCNThreshold1dayTotalEntry 3 }

	pnProvTCNThreshold1dayTotalValue OBJECT-TYPE
		SYNTAX		OCTET STRING (SIZE (24))
		ACCESS		read-only
		STATUS		mandatory
		DESCRIPTION	"TCN THRESHOLD 1DAY TOTAL
					
					  [Description]
					  (Byte 0 - Byte 3) = OFS TCN THRESHOLD TOTAL-1day (0 - 86400)
					  (Byte 4 - Byte 7) = UAS TCN THRESHOLD TOTAL-1day (0 - 86400)
					  (Byte 8 - Byte 11) = ES TCN THRESHOLD TOTAL-1day (0 - 86400)
					  (Byte 12 - Byte 15) = SES TCN THRESHOLD TOTAL-1day (0 - 86400)
					  (Byte 16 - Byte 19) = BBE TCN THRESHOLD TOTAL-1day 
					                        PDH(Bit Rate = 10MB)  : 0 - 77241600
					                        PDH(Bit Rate = 20MB)  : 0 - 77241600
					                        PDH(Bit Rate = 40MB)  : 0 - 77241600
					  (Byte 20 - Byte 23) = SEP TCN THRESHOLD TOTAL-1day (0 - 86400)
					TRAP=eventTrapPnCPVTCNTreshold1dayTotal"
		::= { pnProvTCNThreshold1dayTotalEntry 4 }

	pnProvTCNThreshold1dayCHTable OBJECT-TYPE
		SYNTAX		SEQUENCE OF PnProvTCNThreshold1dayCHEntry
		ACCESS		not-accessible
		STATUS		mandatory
		DESCRIPTION	"PROV TCN Threshold 1day CH Table"
		::= { pnProvTCNTresholdGroup 4 }

	pnProvTCNThreshold1dayCHEntry OBJECT-TYPE
		SYNTAX		PnProvTCNThreshold1dayCHEntry
		ACCESS		not-accessible
		STATUS		mandatory
		INDEX		{
						pnProvTCNThreshold1dayCHPasoIndex,
						pnProvTCNThreshold1dayCHIndex,
						pnProvTCNThreshold1dayCHORIndex
					}
		::= { pnProvTCNThreshold1dayCHTable 1 }

	PnProvTCNThreshold1dayCHEntry ::= SEQUENCE {
					  pnProvTCNThreshold1dayCHPasoIndex    IpAddress,
					  pnProvTCNThreshold1dayCHIndex    INTEGER,
					  pnProvTCNThreshold1dayCHORIndex  INTEGER,
					  pnProvTCNThreshold1dayCHValue    OCTET STRING
					}

	pnProvTCNThreshold1dayCHPasoIndex OBJECT-TYPE
		SYNTAX		IpAddress 
		ACCESS		read-only
		STATUS		mandatory
		DESCRIPTION	"Pasolink IP Address Index"
		::= { pnProvTCNThreshold1dayCHEntry 1 }

	pnProvTCNThreshold1dayCHIndex OBJECT-TYPE
		SYNTAX		INTEGER{
					  ch-A(1),
					  ch-B(2),
					  ch-C(3),
					  ch-D(4)
					}
		ACCESS		read-only
		STATUS		mandatory
		DESCRIPTION	"TCN 1day Current CH Index
					  1:CH-A,
					  2:CH-B,
					  3:CH-C,
					  4:CH-D"
		::= { pnProvTCNThreshold1dayCHEntry 2 }

	pnProvTCNThreshold1dayCHORIndex OBJECT-TYPE
		SYNTAX		INTEGER{
					  occur(1),
					  recover(2)
					}
		ACCESS		read-only
		STATUS		mandatory
		DESCRIPTION	"TCN Threshold 1day CH Occur/Recover Index
					  1:Occur,
					  2:Recover"
		::= { pnProvTCNThreshold1dayCHEntry 3 }

	pnProvTCNThreshold1dayCHValue OBJECT-TYPE
		SYNTAX		OCTET STRING (SIZE (24))
		ACCESS		read-only
		STATUS		mandatory
		DESCRIPTION	"This item is not used.
				 TCN THRESHOLD 1day CH
					  This value is used by only PDH.
					
					  [Description]
					  (Byte 0 - Byte 3)   = (Fixed to 0)
					  (Byte 4 - Byte 7)   = UAS TCN THRESHOLD CH-1day (0 - 900)
					  (Byte 8 - Byte 11)  = ES TCN THRESHOLD CH-1day  (0 - 900)
					  (Byte 12 - Byte 15) = SES TCN THRESHOLD CH-1day (0 - 900)
					  (Byte 16 - Byte 19) = BBE TCN THRESHOLD CH-1day (0 - 402300)
					  (Byte 20 - Byte 23) = SEP TCN THRESHOLD CH-1day (0 - 900)
					TRAP=eventTrapPnCPVTCNTreshold1dayCH"
		::= { pnProvTCNThreshold1dayCHEntry 4 }


	pnProvMDUCondSetTable OBJECT-TYPE
		SYNTAX		SEQUENCE OF PnProvMDUCondSetEntry
		ACCESS		not-accessible
		STATUS		mandatory
		DESCRIPTION	"PROV MDU Cond Set Table"
		::= { pnProvisioningGroup 12 }

	pnProvMDUCondSetEntry OBJECT-TYPE
		SYNTAX		PnProvMDUCondSetEntry
		ACCESS		not-accessible
		STATUS		mandatory
		INDEX		{
						pnProvMDUCondSetPasoIndex
					}
		::= { pnProvMDUCondSetTable 1 }

	PnProvMDUCondSetEntry ::= SEQUENCE {
					  pnProvMDUCondSetPasoIndex  IpAddress,

					  pnEowIFType	INTEGER,
					  pnAlarmCorrelationCapability	OffOnValue
					}

	pnProvMDUCondSetPasoIndex OBJECT-TYPE
		SYNTAX		IpAddress 
		ACCESS		read-only
		STATUS		mandatory
		DESCRIPTION	"Pasolink IP Address Index"
		::= { pnProvMDUCondSetEntry 1 }


















	pnEowIFType OBJECT-TYPE
		SYNTAX		INTEGER (0..2)
		ACCESS		read-only
		STATUS		mandatory
		DESCRIPTION	"EOW2 EXTERNAL SETTING
					  0:Invalid,
					  1:Normal,
					  2:Invert
					TRAP=eventTrapPnCPVEOWIntfcType"
		::= { pnProvMDUCondSetEntry 4 }

	pnAlarmCorrelationCapability OBJECT-TYPE
		SYNTAX		OffOnValue
		ACCESS		read-only
		STATUS		mandatory
		DESCRIPTION	"ALARM CORRELATION CAPABILITY
					 0:Invalid,
					 1:Off,
					 2:On
					TRAP=eventTrapPnCPVAlarmCorrelation"
		::= { pnProvMDUCondSetEntry 5 }

	pnProvPMONSelectTable OBJECT-TYPE
		SYNTAX		SEQUENCE OF PnProvPMONSelectEntry
		ACCESS		not-accessible
		STATUS		mandatory
		DESCRIPTION	"PROV PMON Select Table"
		::= { pnProvisioningGroup 13 }

	pnProvPMONSelectEntry OBJECT-TYPE
		SYNTAX		PnProvPMONSelectEntry
		ACCESS		not-accessible
		STATUS		mandatory
		INDEX		{
						pnProvPMONSelectPasoIndex
					}
		::= { pnProvPMONSelectTable 1 }

	PnProvPMONSelectEntry ::= SEQUENCE {
					  pnProvPMONSelectPasoIndex  IpAddress,
					  pnProvPMONSelect	OCTET STRING
					}

	pnProvPMONSelectPasoIndex OBJECT-TYPE
		SYNTAX		IpAddress 
		ACCESS		read-only
		STATUS		mandatory
		DESCRIPTION	"Pasolink IP Address Index"
		::= { pnProvPMONSelectEntry 1 }

	pnProvPMONSelect OBJECT-TYPE
		SYNTAX		OCTET STRING (SIZE (10))
		ACCESS		read-only
		STATUS		mandatory
		DESCRIPTION	"PMON SELECT
					
					  [Description]
					  Byte 0 = SES COUNT ACTIVATION (1:30[%], 2:15[%])
					  Byte 1 = SES COUNT ACTIVATION(DIR-B) (1:30[%], 2:15[%]) --Not used
					  Byte 2 = PMON E1-A SELECT (0:Not Select, x: CHx(x:1-16))
					  Byte 3 = PMON E1-B SELECT (0:Not Select, x: CHx(x:1-16))
					  Byte 4 = PMON E1-C SELECT (0:Not Select, x: CHx(x:1-16))
					  Byte 5 = PMON E1-D SELECT (0:Not Select, x: CHx(x:1-16))
					  Byte 6 = RX LEVEL TCN THRESHOLD(No.1) integral number
					           (signed char: -99 to -7)
					  Byte 7 = RX LEVEL TCN THRESHOLD(No.1)a place of decimal
					           (0-9)
					  Byte 8 = RX LEVEL TCN THRESHOLD(No.2) integral number
					           (signed char: -99 to -7)
					  Byte 9 = RX LEVEL TCN THRESHOLD(No.2)a place of decimal
					           (0-9)
					
					  *) The values of No.2 side are fixed to 0 when
					     Redundancy is 1+0 TERM.
					TRAP=eventTrapPnCPVPmonSelect"
		::= { pnProvPMONSelectEntry 2 }


-----------------------------------------------
-- pnMaintenanceGroup Group Definitions
-----------------------------------------------


	pnMaintCommonTable OBJECT-TYPE
		SYNTAX		SEQUENCE OF PnMaintCommonEntry
		ACCESS		not-accessible
		STATUS		mandatory
		DESCRIPTION	"MAINT Common Table"
		::= { pnMaintenanceGroup 1 }

	pnMaintCommonEntry OBJECT-TYPE
		SYNTAX		PnMaintCommonEntry
		ACCESS		not-accessible
		STATUS		mandatory
		INDEX		{
						pnMaintCommonPasoIndex
					}
		::= { pnMaintCommonTable 1 }

	PnMaintCommonEntry ::= SEQUENCE {
					  pnMaintCommonPasoIndex	IpAddress,
					  pnMaintMode	OffOnValue,
					  pnMaintTxSWControl	INTEGER,
					  pnMaintRxSWControl	INTEGER,
					  pnMaintLoopback1CH	OCTET STRING,
					  pnMaintLoopback2CH	OCTET STRING,
					  pnMaintDADEAdjust	INTEGER,
					  pnMaintDADEAdjustEnable	INTEGER,
					  pnMaintLANDeviceReset	INTEGER,
					  pnMaintTxSWMode	INTEGER,
					  pnMaintRxSWMode	INTEGER
					}

	pnMaintCommonPasoIndex OBJECT-TYPE
		SYNTAX		IpAddress 
		ACCESS		read-only
		STATUS		mandatory
		DESCRIPTION	"Pasolink IP Address Index"
		::= { pnMaintCommonEntry 1 }

	pnMaintMode OBJECT-TYPE
		SYNTAX		OffOnValue
		ACCESS		read-only
		STATUS		mandatory
		DESCRIPTION	"MAINTENANCE
					  0:Invalid,
					  1:Off,
					  2:On
					TRAP=eventTrapPnCPVMaintMode"
		::= { pnMaintCommonEntry 2 }

	pnMaintTxSWControl OBJECT-TYPE
		SYNTAX		INTEGER (0..3)
		ACCESS		read-only
		STATUS		mandatory
		DESCRIPTION	"This item is not used. 
                                 TX SW MANUAL CONTROL
					  0:Invalid,
					  1:Auto,
					  2:No.1,
					  3:No.2
					TRAP=eventTrapPnCPVMaintTxSWContol"
		::= { pnMaintCommonEntry 3 }

	pnMaintRxSWControl OBJECT-TYPE
		SYNTAX		INTEGER (0..3)
		ACCESS		read-only
		STATUS		mandatory
		DESCRIPTION	"This item is not used. 
                                 RX SW MANUAL CONTROL
					  0:Invalid,
					  1:Auto,
					  2:No.1,
					  3:No.2
					TRAP=eventTrapPnCPVMaintRxSWContol"
		::= { pnMaintCommonEntry 4 }

	pnMaintLoopback1CH OBJECT-TYPE
		SYNTAX		OCTET STRING (SIZE (6))
		ACCESS		read-only
		STATUS		mandatory
		DESCRIPTION	"MAIN CH LOOPBACK-1(CHxx)
					(xx:01-16)
					  0:Off,
					  1:On
					
					  [Description]
					  Bit 0 = MAIN CH LOOPBACK-1(CH01) (0:Off, 1:On)
					  Bit 1 = MAIN CH LOOPBACK-1(CH02)
					  ...
					  Bit 14 = MAIN CH LOOPBACK-1(CH15) for E1 interface
					  Bit 15 = MAIN CH LOOPBACK-1(CH16) for E1 interface
					
					  *) The value of CHxx is fixed to 0, when CHxx Usage is not used. (xx: 01 - 16)
					TRAP=eventTrapPnCPVMaintLoopback1CH"
		::= { pnMaintCommonEntry 6 }

	pnMaintLoopback2CH OBJECT-TYPE
		SYNTAX		OCTET STRING (SIZE (6))
		ACCESS		read-only
		STATUS		mandatory
		DESCRIPTION	"
					MAIN CH LOOPBACK-2(CHxx)
					(xx:01-16)
					  0:Off,
					  1:On
					
					  [Description]
					  Bit 0 = MAIN CH LOOPBACK-2(CH01) (0:Off, 1:On)
					  Bit 1 = MAIN CH LOOPBACK-2(CH02)
					  ...
					  Bit 14 = MAIN CH LOOPBACK-1(CH15) for E1 interface
					  Bit 15 = MAIN CH LOOPBACK-1(CH16) for E1 interface
					
					  *) The value of CHxx is fixed to 0, when CHxx Usage is not used. (xx: 01 - 16)
					TRAP=eventTrapPnCPVMaintLoopback2CH"
		::= { pnMaintCommonEntry 7 }

	pnMaintDADEAdjust OBJECT-TYPE
		SYNTAX		INTEGER (0..3)
		ACCESS		read-only
		STATUS		mandatory
		DESCRIPTION	"This item is not used. 
					DADE ADJUST
					  0:Invalid,
					  1:DADE,
					  2:Off Set DADE,
					  3:DADE OFF
					TRAP=eventTrapPnCPVMaintDADEAdjust"
		::= { pnMaintCommonEntry 10 }

	pnMaintDADEAdjustEnable OBJECT-TYPE
		SYNTAX		INTEGER (0..2)
		ACCESS		read-only
		STATUS		mandatory
		DESCRIPTION	"This item is not used. 
					DADE ADJUST ENABLE
					  0:Invalid,
					  1:Off,
					  2:ON Executing
					TRAP=eventTrapPnCPVMaintDADEAdjustEn"
		::= { pnMaintCommonEntry 11 }

	pnMaintLANDeviceReset OBJECT-TYPE
		SYNTAX		INTEGER (0..7)
		ACCESS		read-only
		STATUS		mandatory
		DESCRIPTION	"This item is not used. 
				LAN DEVICE RESET
					  0:Invalid,
					  1:Not Selected,
					  2:INTFC1(Port1),
					  3:INTFC1(Port2)
					TRAP=eventTrapPnCPVMaintLanDeviceReset"
		::= { pnMaintCommonEntry 12 }

	pnMaintTxSWMode OBJECT-TYPE
		SYNTAX		INTEGER (0..2)
		ACCESS		read-only
		STATUS		mandatory
		DESCRIPTION	"TX SW MODE
					  0:Invalid,
					  1:Auto(No.1),
					  2:Auto(No.2),
					  3:Manual(No.1),
					  4:Manual(No.2)
					TRAP=eventTrapPnCPVMaintTxSWMode"
		::= { pnMaintCommonEntry 16 }

	pnMaintRxSWMode OBJECT-TYPE
		SYNTAX		INTEGER (0..2)
		ACCESS		read-only
		STATUS		mandatory
		DESCRIPTION	"RX SW MODE
					  0:Invalid,
					  1:Auto(No.1),
					  2:Auto(No.2),
					  3:Manual(No.1),
					  4:Manual(No.2)
					TRAP=eventTrapPnCPVMaintRxSWMode"
		::= { pnMaintCommonEntry 17 }

	pnMaintSysTable OBJECT-TYPE
		SYNTAX		SEQUENCE OF PnMaintSysEntry
		ACCESS		not-accessible
		STATUS		mandatory
		DESCRIPTION	"MAINT SYS Table"
		::= { pnMaintenanceGroup 2 }

	pnMaintSysEntry OBJECT-TYPE
		SYNTAX		PnMaintSysEntry
		ACCESS		not-accessible
		STATUS		mandatory
		INDEX		{
						pnMaintSysPasoIndex,
						pnMaintSysIndex
					}
		::= { pnMaintSysTable 1 }

	PnMaintSysEntry ::= SEQUENCE {
					  pnMaintSysPasoIndex              IpAddress,
					  pnMaintSysIndex                  INTEGER,
					  pnMaintSysATPCManualControl      INTEGER,
					  pnMaintSysATPCManualContPower    INTEGER,
					  pnMaintSysTxMuteControl          INTEGER,
					  pnMaintSysTxMuteContReleaseTime  INTEGER,
					  pnMaintSysCW                     INTEGER,
					  pnMaintSysForcedLinearizerCont   INTEGER,
					  pnMaintSysRFShiftFreqSet         DisplayString,
					  pnMaintSysAntennaAlignMode       INTEGER
					}

	pnMaintSysPasoIndex OBJECT-TYPE
		SYNTAX		IpAddress 
		ACCESS		read-only
		STATUS		mandatory
		DESCRIPTION	"Pasolink IP Address Index"
		::= { pnMaintSysEntry 1 }

	pnMaintSysIndex OBJECT-TYPE
		SYNTAX		INTEGER{
					  no1(1),
					  no2(2)
					}
		ACCESS		read-only
		STATUS		mandatory
		DESCRIPTION	"Main Sys Index
					 1:No.1 when EQUIPMENT CONFIG is TERM.
					 2:No.2 when EQUIPMENT CONFIG is TERM."
		::= { pnMaintSysEntry 2 }

	pnMaintSysATPCManualControl OBJECT-TYPE
		SYNTAX		OffOnValue
		ACCESS		read-only
		STATUS		mandatory
		DESCRIPTION	"ATPC MANUAL CONTROL
					TRAP=eventTrapPnCPVMaintATPCManualControl"
		::= { pnMaintSysEntry 3 }

	pnMaintSysATPCManualContPower OBJECT-TYPE
		SYNTAX		INTEGER
		ACCESS		read-only
		STATUS		mandatory
		DESCRIPTION	"ATPC MANUAL POWER[dB]
					TRAP=eventTrapPnCPVMaintATPCManualContPower"
		::= { pnMaintSysEntry 4 }

	pnMaintSysTxMuteControl OBJECT-TYPE
		SYNTAX		OffOnValue
		ACCESS		read-only
		STATUS		mandatory
		DESCRIPTION	"TX MUTE CONTROL
					TRAP=eventTrapPnCPVMaintTxMuteControl"
		::= { pnMaintSysEntry 5 }

	pnMaintSysTxMuteContReleaseTime OBJECT-TYPE
		SYNTAX		INTEGER
		ACCESS		read-only
		STATUS		mandatory
		DESCRIPTION	"TX MUTE OFF TIMER[sec]
					TRAP=eventTrapPnCPVMaintTxMuteContReleaseTime"
		::= { pnMaintSysEntry 6 }

	pnMaintSysCW OBJECT-TYPE
		SYNTAX		OffOnValue
		ACCESS		read-only
		STATUS		mandatory
		DESCRIPTION	"CW CONTROL
					TRAP=eventTrapPnCPVMaintCW"
		::= { pnMaintSysEntry 7 }

	pnMaintSysForcedLinearizerCont OBJECT-TYPE
		SYNTAX		INTEGER (0..2)
		ACCESS		read-only
		STATUS		mandatory
		DESCRIPTION	"LINEARIZER CONTROL
					  0:Invalid,
					  1:Auto,
					  2:Force Reset
					TRAP=eventTrapPnCPVMaintForcedLinearizerCont"
		::= { pnMaintSysEntry 10 }

	pnMaintSysRFShiftFreqSet OBJECT-TYPE
		SYNTAX		DisplayString (SIZE (0..4))
		ACCESS		read-only
		STATUS		mandatory
		DESCRIPTION	"This item is not used.         
					 RF SHIFT FREQUENCY[MHz]
					 This value is only 1008 or 1010
					TRAP=eventTrapPnCPVMaintRFShiftFreqSet"
		::= { pnMaintSysEntry 12 }

	pnMaintSysAntennaAlignMode OBJECT-TYPE
		SYNTAX		OffOnValue
		ACCESS		read-only
		STATUS		mandatory
		DESCRIPTION	"ANTENNA ALIGNMENT MODE
					TRAP=eventTrapPnCPVMaintAntennaAlignMode"
		::= { pnMaintSysEntry 13 }


-----------------------------------------------
-- pnInvEntryGroup Group Definitions
-----------------------------------------------

	pnInvModuleInfoMDUTable OBJECT-TYPE
		SYNTAX		SEQUENCE OF PnInvModuleInfoMDUEntry
		ACCESS		not-accessible
		STATUS		mandatory
		DESCRIPTION	"Module Info MDU Table"
		::= { pnInvEntryGroup 1 }

	pnInvModuleInfoMDUEntry OBJECT-TYPE
		SYNTAX		PnInvModuleInfoMDUEntry
		ACCESS		not-accessible
		STATUS		mandatory
		INDEX		{
						pnInvModuleInfoMDUPasoIndex,
						pnInvModuleInfoMDUIndex
					}
		::= { pnInvModuleInfoMDUTable 1 }

	PnInvModuleInfoMDUEntry ::= SEQUENCE {
					  pnInvModuleInfoMDUPasoIndex  IpAddress,
					  pnInvModuleInfoMDUIndex  INTEGER,
					  pnInvModuleInfoMDUData   OCTET STRING
					}

	pnInvModuleInfoMDUPasoIndex OBJECT-TYPE
		SYNTAX		IpAddress 
		ACCESS		read-only
		STATUS		mandatory
		DESCRIPTION	"Pasolink IP Address Index"
		::= { pnInvModuleInfoMDUEntry 1 }

	pnInvModuleInfoMDUIndex OBJECT-TYPE
		SYNTAX		INTEGER{
					  modem-no1(1),
					  modem-no2(2),
					  ctrl(3),
					  main-work(4)
					}
		ACCESS		read-only
		STATUS		mandatory
		DESCRIPTION	"Module Info MDU Index
					  1:Modem(No.1),
					  2:Modem(No.2),
					  3:CTRL,
					  4:INTFC"
					
		::= { pnInvModuleInfoMDUEntry 2 }

	pnInvModuleInfoMDUData OBJECT-TYPE
		SYNTAX		OCTET STRING (SIZE (56))
		ACCESS		read-only
		STATUS		mandatory
		DESCRIPTION	"Module Info MDU Data
					  [Description]
					  (Byte 0 - Byte 15)  = CODE No. (VALUE(ASC(16))
					  (Byte 16 - Byte 31) = PACKAGE NAME (VALUE(ASC(16))
					  (Byte 32 - Byte 39) = SERIAL No. (VALUE(ASC(8))
					  (Byte 40 - Byte 47) = DATE OF MANUFACTURE (VALUE(ASC(8))
					  (Byte 48 - Byte 55) = H/W VERSION (VALUE(ASC(8))"
		::= { pnInvModuleInfoMDUEntry 3 }

	pnInvModuleInfoTRUTable OBJECT-TYPE
		SYNTAX		SEQUENCE OF PnInvModuleInfoTRUEntry
		ACCESS		not-accessible
		STATUS		mandatory
		DESCRIPTION	"Module Info ODU Table"
		::= { pnInvEntryGroup 2 }

	pnInvModuleInfoTRUEntry OBJECT-TYPE
		SYNTAX		PnInvModuleInfoTRUEntry
		ACCESS		not-accessible
		STATUS		mandatory
		INDEX		{
						pnInvModuleInfoTRUPasoIndex,
						pnInvModuleInfoTRUSysIndex
					}
		::= { pnInvModuleInfoTRUTable 1 }

	PnInvModuleInfoTRUEntry ::= SEQUENCE {
					  pnInvModuleInfoTRUPasoIndex  IpAddress,
					  pnInvModuleInfoTRUSysIndex  INTEGER,
					  pnInvModuleInfoTRUData      OCTET STRING
					}

	pnInvModuleInfoTRUPasoIndex OBJECT-TYPE
		SYNTAX		IpAddress 
		ACCESS		read-only
		STATUS		mandatory
		DESCRIPTION	"Pasolink IP Address Index"
		::= { pnInvModuleInfoTRUEntry 1 }

	pnInvModuleInfoTRUSysIndex OBJECT-TYPE
		SYNTAX		INTEGER{
					  no1(1),
					  no2(2)
					}
		ACCESS		read-only
		STATUS		mandatory
		DESCRIPTION	"Module Info ODU Sys Index
					 1:No.1 when EQUIPMENT CONFIG is TERM.
					 2:No.2 when EQUIPMENT CONFIG is TERM."
		::= { pnInvModuleInfoTRUEntry 2 }

	pnInvModuleInfoTRUData OBJECT-TYPE
		SYNTAX		OCTET STRING (SIZE (60))
		ACCESS		read-only
		STATUS		mandatory
		DESCRIPTION	"Module Info ODU Data
					  [Description]
					  (Byte 0 - Byte 15)  = CODE No. (VALUE(ASC(16))
					  (Byte 16 - Byte 31) = PACKAGE NAME (VALUE(ASC(16))
					  (Byte 32 - Byte 39) = SERIAL No. (VALUE(ASC(8))
					  (Byte 40 - Byte 47) = DATE OF MANUFACTURE (VALUE(ASC(8))
					  (Byte 48 - Byte 55) = H/W VERSION (VALUE(ASC(8))
					  (Byte 56 - Byte 59) = F/W VERSION (VALUE(ASC(4))"
		::= { pnInvModuleInfoTRUEntry 3 }

	pnInvFPGAInfoTable OBJECT-TYPE
		SYNTAX		SEQUENCE OF PnInvFPGAInfoEntry
		ACCESS		not-accessible
		STATUS		mandatory
		DESCRIPTION	"FPGA Info Table"
		::= { pnInvEntryGroup 3 }

	pnInvFPGAInfoEntry OBJECT-TYPE
		SYNTAX		PnInvFPGAInfoEntry
		ACCESS		not-accessible
		STATUS		mandatory
		INDEX		{
						pnInvFPGAInfoPasoIndex,
						pnInvFPGAInfoIndex
					}
		::= { pnInvFPGAInfoTable 1 }

	PnInvFPGAInfoEntry ::= SEQUENCE {
					  pnInvFPGAInfoPasoIndex  IpAddress,
					  pnInvFPGAInfoIndex  INTEGER,
					  pnInvFPGAInfoData   OCTET STRING
					}

	pnInvFPGAInfoPasoIndex OBJECT-TYPE
		SYNTAX		IpAddress 
		ACCESS		read-only
		STATUS		mandatory
		DESCRIPTION	"Pasolink IP Address Index"
		::= { pnInvFPGAInfoEntry 1 }

	pnInvFPGAInfoIndex OBJECT-TYPE
		SYNTAX		INTEGER{
					  modem1(1),
					  modem2(2),
					  ctrl(3),
					  mainWork(4),
					  sfpModule-mainWork(6),
					  ctrlProgramVer(8)
					}
		ACCESS		read-only
		STATUS		mandatory
		DESCRIPTION	"FPGA Info Index
					  1:Modem No.1,
					  2:Modem No.2,
					  3:CTRL,
					  4:INTFC,
					  6:SFP Module(Main - Work),
					  8:CTRL PROGRAM VER
					"
		::= { pnInvFPGAInfoEntry 2 }

	pnInvFPGAInfoData OBJECT-TYPE
		SYNTAX		OCTET STRING (SIZE (128))
		ACCESS		read-only
		STATUS		mandatory
		DESCRIPTION	"FPGA Info Data
					
					  [Description]
					  (Byte 0 - Byte 15)  = FPGA1 CODE No. (VALUE(ASC(16)))
					  (Byte 16 - Byte 31) = FPGA1 NAME     (VALUE(ASC(16)))
					  (Byte 32 - Byte 37) = FPGA1 VERSION  (VALUE(ASC(6)))
					  (Byte 38 - Byte 53) = FPGA2 CODE No. (VALUE(ASC(16)))--Not Used
					  (Byte 54 - Byte 69) = FPGA2 NAME     (VALUE(ASC(16)))--Not Used
					  (Byte 70 - Byte 75) = FPGA2 VERSION  (VALUE(ASC(6)))--Not Used
					  (Byte 76 - Byte 128) = (Fixed to 0)"
		::= { pnInvFPGAInfoEntry 3 }


	pnInvTRUProvRangeInfoTable OBJECT-TYPE
		SYNTAX		SEQUENCE OF PnInvTRUProvRangeInfoEntry
		ACCESS		not-accessible
		STATUS		mandatory
		DESCRIPTION	"TRU(ODU) Prov Range Info Table"
		::= { pnInvEntryGroup 4 }

	pnInvTRUProvRangeInfoEntry OBJECT-TYPE
		SYNTAX		PnInvTRUProvRangeInfoEntry
		ACCESS		not-accessible
		STATUS		mandatory
		INDEX		{
						pnInvTRUProvRangeInfoPasoIndex,

					}
		::= { pnInvTRUProvRangeInfoTable 1 }

	PnInvTRUProvRangeInfoEntry ::= SEQUENCE {
					  pnInvTRUProvRangeInfoPasoIndex  IpAddress,

					  pnInvTRUProvRangeInfoValue   OCTET STRING
					}

	pnInvTRUProvRangeInfoPasoIndex OBJECT-TYPE
		SYNTAX		IpAddress 
		ACCESS		read-only
		STATUS		mandatory
		DESCRIPTION	"Pasolink IP Address Index"
		::= { pnInvTRUProvRangeInfoEntry 1 }

	pnInvTRUProvRangeInfoValue OBJECT-TYPE
		SYNTAX		OCTET STRING (SIZE (32))
		ACCESS		read-only
		STATUS		mandatory
		DESCRIPTION	"ODU Prov Range Info Value
					  [Description]
					  (Byte 0) = ATPC(MAX) (No.1) (VAL(INT))
					  (Byte 1) = ATPC(MIN) (No.1) (VAL(INT))
					  (Byte 2) = MTPC(MAX) (No.1) (VAL(INT))
					  (Byte 3) = MTPC(MIN) (No.1) (VAL(INT))
					  (Byte 4) = RX THRESHOLD LEVEL(MAX) (No.1) integral number(signed char) (VAL(INT))
					  (Byte 5) = RX THRESHOLD LEVEL(MAX) (No.1) a place of decimal(0-9) (VAL(INT))
					  (Byte 6) = RX THRESHOLD LEVEL(MIN) (No.1) integral number(signed char) (VAL(INT))
					  (Byte 7) = RX THRESHOLD LEVEL(MIN) (No.1) a place of decimal(0-9) (VAL(INT))
					  (Byte 8) = ADDITIONAL ATT(MAX) (No.1) (VAL(INT))
					  (Byte 9) = ADDITIONAL ATT(MIN) (No.1) (VAL(INT))
					  (Byte 10) = (Don't care)
					  (Byte 11) = HYSTERESIS(MAX) (No.1) (VAL(INT))
					  (Byte 12) = HYSTERESIS(MIN) (No.1) (VAL(INT))
					  (Byte 13) = BB LNZ POWER(MAX) (No.1) (VAL(INT))
					  (Byte 14) = BB LNZ POWER(MIN) (No.1) (VAL(INT))
					  (Byte 15) = (Don't care)
					  (Byte 16) = ATPC(MAX) (No.2) (VAL(INT))
					  (Byte 17) = ATPC(MIN) (No.2) (VAL(INT))
					  (Byte 18) = MTPC(MAX) (No.2) (VAL(INT))
					  (Byte 19) = MTPC(MIN) (No.2) (VAL(INT))
					  (Byte 20) = RX THRESHOLD LEVEL(MAX) (No.2) integral number(signed char) (VAL(INT))
					  (Byte 21) = RX THRESHOLD LEVEL(MAX) (No.2) a place of decimal(0-9) (VAL(INT))
					  (Byte 22) = RX THRESHOLD LEVEL(MIN) (No.2) integral number(signed char) (VAL(INT))
					  (Byte 23) = RX THRESHOLD LEVEL(MIN) (No.2) a place of decimal(0-9) (VAL(INT))
					  (Byte 24) = ADDITIONAL ATT(MAX) (No.2) (VAL(INT))
					  (Byte 25) = ADDITIONAL ATT(MIN) (No.2) (VAL(INT))
					  (Byte 26) = (Don't care)
					  (Byte 27) = HYSTERESIS(MAX) (No.2) (VAL(INT))
					  (Byte 28) = HYSTERESIS(MIN) (No.2) (VAL(INT))
					  (Byte 29) = BB LNZ POWER(MAX) (No.2) (VAL(INT))
					  (Byte 30) = BB LNZ POWER(MIN) (No.2) (VAL(INT))"

		::= { pnInvTRUProvRangeInfoEntry 2 }

	pnInvTRUFreqInfoTable OBJECT-TYPE
		SYNTAX		SEQUENCE OF PnInvTRUFreqInfoEntry
		ACCESS		not-accessible
		STATUS		mandatory
		DESCRIPTION	"TRU(ODU) Freq Info Table"
		::= { pnInvEntryGroup 5 }

	pnInvTRUFreqInfoEntry OBJECT-TYPE
		SYNTAX		PnInvTRUFreqInfoEntry
		ACCESS		not-accessible
		STATUS		mandatory
		INDEX		{
						pnInvTRUFreqInfoSysIndex
					}
		::= { pnInvTRUFreqInfoTable 1 }

	PnInvTRUFreqInfoEntry ::= SEQUENCE {
					  pnInvTRUFreqInfoPasoIndex  IpAddress,
					  pnInvTRUFreqInfoSysIndex  INTEGER,
					  pnInvTRUFreqInfoValue     OCTET STRING
					}

	pnInvTRUFreqInfoPasoIndex OBJECT-TYPE
		SYNTAX		IpAddress 
		ACCESS		read-only
		STATUS		mandatory
		DESCRIPTION	"Pasolink IP Address Index"
		::= { pnInvTRUFreqInfoEntry 1 }

	pnInvTRUFreqInfoSysIndex OBJECT-TYPE
		SYNTAX		INTEGER{
					  no1(1),
					  no2(2)
					}
		ACCESS		read-only
		STATUS		mandatory
		DESCRIPTION	"TRU Freq Info Sys Index
					 1:No.1 when EQUIPMENT CONFIG is TERM.
					 2:No.2 when EQUIPMENT CONFIG is TERM."
		::= { pnInvTRUFreqInfoEntry 2 }

	pnInvTRUFreqInfoValue OBJECT-TYPE
		SYNTAX		OCTET STRING (SIZE (58))
		ACCESS		read-only
		STATUS		mandatory
		DESCRIPTION	"TRU Freq Info Value
					  [Description]
					  (Byte 0 - Byte 8)   = TX START FREQUNENCY[MHz] (VALUE(ASC 9))
					  (Byte 9 - Byte 17)  = TX STOP FREQUNENCY[MHz]  (VALUE(ASC 9))
					  (Byte 18 - Byte 26) = RX START FREQUNENCY[MHz] (VALUE(ASC 9))
					  (Byte 27 - Byte 35) = RX STOP FREQUNENCY[MHz]  (VALUE(ASC 9))
					  (Byte 36 - Byte 42) = FREQUENCY STEP[MHz]      (VALUE(ASC 7))
					  (Byte 43 - Byte 50) = SHIFT FREQUENCY[MHz]     (VALUE(ASC 8))
					  (Byte 51)           = UPPER/LOWER              (0:LOWER, 1:UPPER)
					  (Byte 52 -Byte 54)  = (Don't care)
					  (Byte 55)           = SUB BAND                 (VALUE(ASC 1))
					  (Byte 56)           = TX/RX INDEPENDENT INFO   (0: TX&RX, 1:TX/RX)
					  (Byte 57)           = (Don't care)
					"
		::= { pnInvTRUFreqInfoEntry 3 }


	pnInvEquipmentSupportabilityTable OBJECT-TYPE
		SYNTAX		SEQUENCE OF PnInvEquipmentSupportabilityEntry
		ACCESS		not-accessible
		STATUS		mandatory
		DESCRIPTION	"Inv Equipment Supportability Table"
		::= { pnInvEntryGroup 6 }

	pnInvEquipmentSupportabilityEntry OBJECT-TYPE
		SYNTAX		PnInvEquipmentSupportabilityEntry
		ACCESS		not-accessible
		STATUS		mandatory
		INDEX		{
						pnInvEquipmentSupportabilityPasoIndex
					}
		::= { pnInvEquipmentSupportabilityTable 1 }

	PnInvEquipmentSupportabilityEntry ::= SEQUENCE {
					  pnInvEquipmentSupportabilityPasoIndex  IpAddress,
					  pnInvEquipmentSupportabilityInfo     OCTET STRING
					}

	pnInvEquipmentSupportabilityPasoIndex OBJECT-TYPE
		SYNTAX		IpAddress 
		ACCESS		read-only
		STATUS		mandatory
		DESCRIPTION	"Pasolink IP Address Index"
		::= { pnInvEquipmentSupportabilityEntry 1 }

	pnInvEquipmentSupportabilityInfo OBJECT-TYPE
		SYNTAX		OCTET STRING (SIZE (6))
		ACCESS		read-only
		STATUS		mandatory
		DESCRIPTION	"Equipment Supportability Info
				 This item is used for only PNMS and PNMT."
		::= { pnInvEquipmentSupportabilityEntry 2 }

	pnInvUpdateInfoTable OBJECT-TYPE
		SYNTAX		SEQUENCE OF PnInvUpdateInfoEntry
		ACCESS		not-accessible
		STATUS		mandatory
		DESCRIPTION	"TRU(ODU) Freq Info Table"
		::= { pnInvEntryGroup 7 }

	pnInvUpdateInfoEntry OBJECT-TYPE
		SYNTAX		PnInvUpdateInfoEntry
		ACCESS		not-accessible
		STATUS		mandatory
		INDEX		{
						pnInvUpdateInfoPasoIndex
					}
		::= { pnInvUpdateInfoTable 1 }

	PnInvUpdateInfoEntry ::= SEQUENCE {
					  pnInvUpdateInfoPasoIndex  IpAddress,
					  pnInvUpdateInfoMainWorkModule	INTEGER,
					  pnInvUpdateInfoSummary	OCTET STRING
					}

	pnInvUpdateInfoPasoIndex OBJECT-TYPE
		SYNTAX		IpAddress 
		ACCESS		read-only
		STATUS		mandatory
		DESCRIPTION	"Pasolink IP Address Index"
		::= { pnInvUpdateInfoEntry 1 }

	pnInvUpdateInfoMainWorkModule OBJECT-TYPE
		SYNTAX		INTEGER (0..255)
		ACCESS		read-only
		STATUS		mandatory
		DESCRIPTION	"INTFC(1) PKG CHANGED
					  0:INVALID, 
					  1:BLANK,
					  2:16xE1 BASIC PKG,
					  3:16xE1 STANDARD PKG(E/W LAN),
					TRAP=eventTrapPnCPVinvUpdateMainWorkModule"
		::= { pnInvUpdateInfoEntry 2 }

	pnInvUpdateInfoSummary OBJECT-TYPE
		SYNTAX		OCTET STRING (SIZE (2))
		ACCESS		read-only
		STATUS		mandatory
		DESCRIPTION	"INVENTORY UPDATE INFO SUMMARY
					
					  [Description]
					  (Bit 0) = CTRL (0:Not Changed, 1:Updated)
					  (Bit 1) = MODEM1
					  (Bit 2) = MODEM2
					  (Bit 3) = INTFC
					  (Bit 5) = TRU1
					  (Bit 6) = TRU2
					  (Bit 7) = CTRL PROGRAM VERSION
					  (Bit 8) = TRU PROVISIONING INFO
					  (Bit 9) = TRU FREQ INFO
					  (Bit 10) = SUPPORTABILITY
					  (Bit 11) = (Fixed to 0)
					  (Bit 12) = (Fixed to 0)
					  (Bit 13) = (Fixed to 0)
					  (Bit 14) = (Fixed to 0)
					  (Bit 15) = (Fixed to 0)
					
					TRAP=eventTrapPnCPVinvUpdateSummary"
		::= { pnInvUpdateInfoEntry 4 }


-----------------------------------------------
-- pnMeteringGroup Group Definitions
-----------------------------------------------

	pnMeteringSysTable OBJECT-TYPE
		SYNTAX		SEQUENCE OF PnMeteringSysEntry
		ACCESS		not-accessible
		STATUS		mandatory
		DESCRIPTION	"Metering Sys Table"
		::= { pnMeteringGroup 1 }

	pnMeteringSysEntry OBJECT-TYPE
		SYNTAX		PnMeteringSysEntry
		ACCESS		not-accessible
		STATUS		mandatory
		INDEX		{
						pnMetSysPasoIndex,
						pnMetSysIndex
					}
		::= { pnMeteringSysTable 1 }

	PnMeteringSysEntry ::= SEQUENCE {
					  pnMetSysPasoIndex           IpAddress,
					  pnMetSysIndex               INTEGER,
					  pnMetSysTxPowerStatus       INTEGER,
					  pnMetSysTxPowerValue        DisplayString,
					  pnMetSysRxLevelStatus       INTEGER,
					  pnMetSysRxLevelValue        DisplayString,
					  pnMetSysPSVoltageStatus     INTEGER,
					  pnMetSysPSVoltageValue      DisplayString,
					  pnMetSysBitErrorRateStatus  INTEGER,
					  pnMetSysBitErrorRateXValue  INTEGER,
					  pnMetSysBitErrorRateYValue  INTEGER
					}

	pnMetSysPasoIndex OBJECT-TYPE
		SYNTAX		IpAddress 
		ACCESS		read-only
		STATUS		mandatory
		DESCRIPTION	"Pasolink IP Address Index"
		::= { pnMeteringSysEntry 1 }

	pnMetSysIndex OBJECT-TYPE
		SYNTAX		INTEGER{
					  no1(1),
					  no2(2)
					}
		ACCESS		read-only
		STATUS		mandatory
		DESCRIPTION	"Meterigy Sys Index
					 1:No.1 when EQUIPMENT CONFIG is TERM.
					 2:No.2 when EQUIPMENT CONFIG is TERM."
		::= { pnMeteringSysEntry 2 }

	pnMetSysTxPowerStatus OBJECT-TYPE
		SYNTAX		INTEGER (0..2)
		ACCESS		read-only
		STATUS		mandatory
		DESCRIPTION	"TX POWER Status
					  0:Invalid(Not obtained, Over range),
					  1:Invalid(Index No.2, when Redundancy is 1+0 term.),
					  2:Valid"
		::= { pnMeteringSysEntry 3 }

	pnMetSysTxPowerValue OBJECT-TYPE
		SYNTAX		DisplayString (SIZE (0..5))
		ACCESS		read-only
		STATUS		mandatory
		DESCRIPTION	"TX POWER [dBm]
					  expression: +/-**.*(5bytes)
					
					  *)This value is not guaranteed when pnMetSysTxPowerStatus is Invalid(0 and 1)."
		::= { pnMeteringSysEntry 4 }

	pnMetSysRxLevelStatus OBJECT-TYPE
		SYNTAX		INTEGER (0..2)
		ACCESS		read-only
		STATUS		mandatory
		DESCRIPTION	"RX Level Status
					  0:Invalid(Not obtained, Over range),
					  1:Invalid(Index No.2, when Redundancy is 1+0 term.),
					  2:Valid"
		::= { pnMeteringSysEntry 5 }

	pnMetSysRxLevelValue OBJECT-TYPE
		SYNTAX		DisplayString (SIZE (0..5))
		ACCESS		read-only
		STATUS		mandatory
		DESCRIPTION	"RX Level [dBm]
					  expression: +/-**.*(5bytes)
					
					  *)This value is not guaranteed when pnMetSysRxLevelStatus is Invalid(0 and 1)."
		::= { pnMeteringSysEntry 6 }

	pnMetSysPSVoltageStatus OBJECT-TYPE
		SYNTAX		INTEGER (0..2)
		ACCESS		read-only
		STATUS		mandatory
		DESCRIPTION	"ODU PS Status
					  0:Invalid(Not obtained, Over range),
					  1:Invalid(Index No.2, when Redundancy is 1+0 term.),
					  2:Valid"
		::= { pnMeteringSysEntry 7 }

	pnMetSysPSVoltageValue OBJECT-TYPE
		SYNTAX		DisplayString (SIZE (0..3))
		ACCESS		read-only
		STATUS		mandatory
		DESCRIPTION	"ODU PS [V]
					  expression: -**(3bytes)
					
					  *)This value is not guaranteed when pnMetSysPSVoltageStasus is Invalid(0 and 1).
					  "
		::= { pnMeteringSysEntry 8 }

	pnMetSysBitErrorRateStatus OBJECT-TYPE
		SYNTAX		INTEGER (0..255)
		ACCESS		read-only
		STATUS		mandatory
		DESCRIPTION	"Bit Error Rate Status
					  0:Invalid,
					  42:Invalid(Equipment Level),
					  127:Calculating,
					  255:latest value
					  *) Index 2 is unavailable."
		::= { pnMeteringSysEntry 9 }

	pnMetSysBitErrorRateXValue OBJECT-TYPE
		SYNTAX		INTEGER (-1..99)
		ACCESS		read-only
		STATUS		mandatory
		DESCRIPTION	"BER (Significand Part)
					  This Value shows significant Value for BER times 10.
					  This stautus is invalid when value is -1.
					
					  (Example)
					   BER = 1.2E-6
					
					   This value is 12."
		::= { pnMeteringSysEntry 10 }

	pnMetSysBitErrorRateYValue OBJECT-TYPE
		SYNTAX		INTEGER (-1..99)
		ACCESS		read-only
		STATUS		mandatory
		DESCRIPTION	"BER (Exponential Part)
					  This Value shows Exponential Part for BER.
					  This stautus is invalid when value is -1.
					
					  (Example)
					   BER = 1.2E-6
					
					   This value is 6."
		::= { pnMeteringSysEntry 11 }


-----------------------------------------------
-- Pasolink NEO GET METERING DATA Table
-----------------------------------------------

	pnGetMeteringInfoData OBJECT IDENTIFIER
 		::= { pnGetMeasurementDataGroup 1 }

	pnGetMeteringInfoDataTable OBJECT-TYPE
		SYNTAX		SEQUENCE OF PnGetMeteringInfoDataEntry
		ACCESS		not-accessible
		STATUS		mandatory
		DESCRIPTION	"Measurement Data Table"
		::= { pnGetMeteringInfoData 1 }
	
	pnGetMeteringInfoDataEntry OBJECT-TYPE
		SYNTAX		PnGetMeteringInfoDataEntry
		ACCESS		not-accessible
		STATUS		mandatory
		DESCRIPTION	"Measurement Table Entry"
		INDEX { pngmiManagerIndex } 
		::= { pnGetMeteringInfoDataTable 1 }

	PnGetMeteringInfoDataEntry ::= SEQUENCE {
		pngmiManagerIndex		IpAddress,
		pngmiRequestID		        INTEGER,
		pngmiTargetPasolink		IpAddress,
		pngmiDataStatus	        	INTEGER	
	}

	pngmiManagerIndex OBJECT-TYPE
		SYNTAX		IpAddress
		ACCESS		read-only
		STATUS		mandatory
		DESCRIPTION	"Upper Manager IpAddress"
		::= { pnGetMeteringInfoDataEntry 1 }

	pngmiRequestID OBJECT-TYPE
		SYNTAX		INTEGER (1..9999)
		ACCESS		read-write
		STATUS		mandatory
		DESCRIPTION	"Request ID"
		::= { pnGetMeteringInfoDataEntry 2 }
		
	pngmiTargetPasolink OBJECT-TYPE
		SYNTAX		IpAddress
		ACCESS		read-write
		STATUS		mandatory
		DESCRIPTION	"Target Pasolink IpAddress"
		::= { pnGetMeteringInfoDataEntry 3 }
	
	pngmiDataStatus OBJECT-TYPE
		SYNTAX		INTEGER (0..3)
		ACCESS		read-only
		STATUS		mandatory
		DESCRIPTION	"Data Status
		                     invalid(0),
		                     ready(1),
		                     wait(2),
	                               fail(3)"
		::= { pnGetMeteringInfoDataEntry 4 }
		
-----------------------------------------------
-- End User MIB Object Definitions
-----------------------------------------------
END
